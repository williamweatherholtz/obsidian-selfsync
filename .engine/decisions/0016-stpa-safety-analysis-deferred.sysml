// =====================================================================
// D0016 — commit to a full STPA safety analysis of the sync system, DEFERRED to an end-of-project
// safety pass. STPA is already first-class in the engine (schema/safety/stpa.sysml, the `stpa`
// skill + SOP, engine reference decision 0008 "STPA yes / HARA-ASIL no", the `safety` viewpoint),
// so this is not a schema/process CHANGE — it is a PROJECT decision to run that method here, with
// the scope + method chain fixed now and the analysis tracked as an open delivery action
// (stpaSafetyAnalysis). Accepted 2026-07-06 by wweatherholtz. No code/schema edit → plain ADR.
// =====================================================================
package ProjectDecision0016 {
    private import EngineElement::*;
    private import EngineWork::*;
    private import EngineVerification::*;

    part d0016 : Decision {
        :>> id = "c0f1a5cc-f104-4a10-9b20-a1b2c3d40f14";
        :>> title = "D0016: run a full STPA on the sync system as an end-of-project safety pass (deferred)";
        :>> createdAt = "2026-07-06";
        :>> createdBy = "wweatherholtz";
        :>> status = DecisionStatus::accepted;
        :>> context = "The use-case layer is deliberately happy-path (owner preference); safety comes from a SEPARATE, systematic hazard analysis, not from enriching use cases. Five adversarial critique rounds + a field data-loss escape (0.10.25) showed the real failure family is a controller acting on a STALE PROCESS MODEL of the server (base store, version cursor, token validity, apiVersion) — precisely what STPA is built to surface. STPA is already engine-native: EngineSafety (schema/safety/stpa.sysml) types Loss / Hazard / SystemSafetyConstraint / the typed control loop (Controller, ProcessModel-with-beliefs, ControlledProcess, ControlAction, Feedback, Sensor, Actuator) / UnsafeControlAction (UcaType: provided | notProvided | wrongTimingOrder | stoppedTooSoonAppliedTooLong) / ControllerConstraint / LossScenario (with causalFactor) / SafetyRequirement; the `stpa` skill carries the SOP; engine reference decision 0008 sets HARA/ASIL intentionally light; the `safety` viewpoint (losses/hazards/UCAs/constraints + verify coverage) is declared (renderer still planned). The owner's stated intent: a proper STPA proceeding FROM a control diagram, near the end of the work, to derive safety requirements from loss scenarios.";
        :>> decision = "Perform a full STPA on the SelfSync sync system as an end-of-project safety pass, tracked as the open delivery action `stpaSafetyAnalysis` (no pass result until performed, so `keel orient` carries it as outstanding). Fix the method chain now: (1) Losses; (2) Hazards, each traced to >=1 Loss, and their inverse System Safety Constraints; (3) the full control structure — controllers, controlled processes, control actions, feedback, sensors/actuators, AND each controller's ProcessModel beliefs (the stale-model failure family is this system's core, so model beliefs explicitly); (4) Unsafe Control Actions via all four UcaType guide words per control action; (5) Loss Scenarios in BOTH classes — (a) why a UCA occurs (flawed controller/process-model) and (b) why a correct control action is not executed / feedback never arrives; (6) mitigating Safety Requirements, each traced UCA->Hazard->Loss and carrying a `verify`-linked Test. Scope is the sync data-safety domain (never silently lose/clobber a note; never act on a degraded/wrong server); the trusted-server model (engine reference decision 0009) bounds it — server-compromise threats stay out of the STPA safety scope. Render it via the declared `safety` viewpoint.";
        :>> rationale = "Deferring is right: STPA is most valuable once the control structure is stable, and running it now would re-derive against a moving design; the end-of-project pass assesses the settled system. Recording the scope + chain NOW prevents the analysis from silently shrinking to a happy-path restatement — the omission that let the 0.10.25 delete-on-absence UCA ship unenumerated. Fixing the method chain guards against the two common STPA shortfalls: skipping the UnsafeControlAction step (jumping control-diagram -> scenarios) and doing only class-(a) loss scenarios. Anchoring on ProcessModel beliefs targets THIS system's demonstrated failure family directly. ALTERNATIVES: enrich use cases to cover safety (REJECTED — happy-path use cases are the owner's preference and are the wrong instrument for hazard analysis); a HARA/ASIL quantitative pass (REJECTED per engine reference decision 0008 — disproportionate for a self-hosted note-sync tool); do STPA now (REJECTED — control structure still settling; wasteful re-derivation). CRITERIA: systematic (full UCA enumeration) x traceable (loss<-hazard<-UCA<-requirement, verify-linked) x proportionate (STPA, not HARA/ASIL) x timely (settled design) x honest (records the full chain so it can't quietly narrow).";
        :>> consequences = "No code/schema/process change now (STPA already engine-native). A new OPEN delivery action `stpaSafetyAnalysis` (method=analysis DoD, no result) makes the pending safety pass visible in `keel orient` as outstanding near-end work. When performed, it authors Loss/Hazard/SystemSafetyConstraint/control-structure/UnsafeControlAction/LossScenario/SafetyRequirement instances (EngineSafety) with the typed edges + verify-linked Tests, and renders through the `safety` viewpoint (whose renderer is still planned — building it may be a prerequisite or a parallel engine task). doc-sync: none (no command/type/skill surface changes; the STPA skill + schema already exist). Complements the tombstone-authoritative-delete fix (the first informally-found UCA) and the data-safety use case ucNeverLoseLocalData, which the STPA will formalize.";
    }

    verification d0016Accept : Test {
        :>> id = "c0f1a5cc-f105-4a10-9b20-a1b2c3d40f15";
        :>> method = VerificationMethod::confirmation;
        :>> procedureText = "wweatherholtz asked whether STPA was already a keel process and, on confirmation that it is engine-native, said 'yes let's record and defer assessing STPA for later' (2026-07-06) — explicitly accepting that we commit to a full STPA (control structure -> UCAs -> loss scenarios -> verify-linked safety requirements) performed as an end-of-project safety pass, recorded now and deferred.";
    }
    part d0016AcceptR1 : TestResult { :>> id = "c0f1a5cc-f106-4a10-9b20-a1b2c3d40f16"; :>> outcome = VerdictKind::pass; :>> judgedAgainst = "85d5ad8"; :>> judgedAt = "2026-07-06"; :>> judgedBy = "wweatherholtz"; }
}
