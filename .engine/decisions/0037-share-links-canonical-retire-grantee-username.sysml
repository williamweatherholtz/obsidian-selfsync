// =====================================================================
// D0037 — DELIVERABLE decision (SelfSync product): make share LINKS the canonical way to grant vault
// access, retire the grantee-username grant path, and let a vault share link ONBOARD a brand-new user
// (create-account-or-login, then accept the share). Directed + accepted 2026-08-03 by wweatherholtz
// ("remove the ability for grantee username. we'll just use share links to canonically accept shares";
// then "make a pathway for users to make an account OR login to redeem a link. account first, then link
// — the vault share link implies both, the account creation link just makes the first"; then, on the
// two flagged consequences, "yes on both. confirm and begin, then carry out to completion"). This is a
// product-behavior decision (no engine schema/process change), so it is NOT a #ProspectiveChange.
// =====================================================================
package ProjectDecision0037 {
    private import EngineElement::*;
    private import EngineWork::*;
    private import EngineVerification::*;
    private import EngineRelationships::*;

    part d0037 : Decision {
        :>> id = "2f9a4d17-6c0b-4e2a-9f13-7a1c2d3e4f50";
        :>> title = "D0037: share-links are the canonical grant path; retire grantee-username; a vault share link onboards a new account";
        :>> createdAt = "2026-08-03";
        :>> createdBy = "wweatherholtz";
        :>> status = DecisionStatus::accepted;
        :>> context = "SelfSync had TWO parallel ways to grant a vault share: (1) grantee-username — an owner/admin types another account's username and a .shares.json Grant is written directly (the ONLY share control in the web admin console, admin_ui.html renderVaults; also in the plugin account modal via plugin.shareVault -> POST /api/admin/shares), deliberately not verifying the grantee exists to avoid a username-enumeration oracle (so a typo creates a dormant grant); and (2) share-links (D0023) — a single-use, expiring, opaque token the recipient redeems while logged in, minting the same kind of Grant bound to the redeemer. Share-links existed only in the server API + the Obsidian plugin, with NO admin-console UI. The owner directed consolidating onto share-links as the canonical accept path and removing grantee-username, because the username path is a worse UX (blind typing, dormant-grant footguns, an enumeration-oracle tension) and having two mechanisms muddies the model. The owner also identified the gap that share-link redemption today requires the recipient to ALREADY have an account and be logged in — and directed closing it: a vault share link should let the recipient create an account OR log in and then accept, in one pathway ('the vault share link implies both'); a separate account-creation link (the existing invite token) 'just makes the first' step. Two consequences were surfaced and explicitly accepted: (a) link-as-invite — a valid vault share link authorizes account creation EVEN WHEN registration is Closed (the single-use, expiring, owner-minted link is itself the authorization); (b) redemption/onboarding happens in the Obsidian plugin (extending the existing redeem modal), not a separate server-hosted web page.";
        :>> decision = "(1) Make share-LINKS the sole owner/admin-facing way to grant a vault share. Retire the grantee-username create path end to end: remove the admin-console grantee input + the client-side fuzzy 'did you mean' guard; remove POST /api/admin/shares (share_create) and GET /api/admin/usernames (its only consumer was the grantee autocomplete); remove the plugin's shareVault (grantee-username) UI + its transport call. KEEP the D0008 ACL (ShareStore Grant/authorized) and the grant-revoke path (DELETE /api/admin/shares / share_delete) — a redeemed link still mints a normal, revocable Grant, so revoke stays needed. (2) Restructure the admin console into a SINGLE 'Sharing' section (not per-vault): a vault DROPDOWN + permission -> Create share link (copyable selfsync-share:// link built from server URL + token); a list of the owner's active links with revoke; a list of redeemed grants with revoke; plus a 'Create account link' = the existing invite token surfaced as a copyable link. (3) Add a link-as-invite ONBOARDING path: a new PUBLIC endpoint POST /api/share-redeem-register { token, username, password } validates the link (peek), creates the account authorized BY the valid link (bypassing Closed registration), atomically claims+grants (single-use; rolls back account+claim on failure), and returns a session token — so one link yields EXACTLY one account + one grant (closing the multi-account hole a peek-only register-then-redeem would open). The existing authed POST /api/share-redeem is unchanged (logged-in redeem). The plugin's redeem modal, when no session exists for that server, offers Log in OR Create account, then redeems. (4) Two other admin-console asks ride the same server release: the registration open/closed control becomes a TOGGLE (was a checkbox); each vault shows a 'last used' time derived from its .sync-index.db server-side mtime (no schema migration — an fs::metadata read; segmented per-vault storage, D0005, so introspection is per vault).";
        :>> rationale = "One canonical, link-based accept path is the modern, lower-footgun model: the recipient proves intent by redeeming, the token is single-use + expiring + owner-scoped + revocable, and there is no blind-typed dormant grant nor an enumeration-oracle tension. Reusing the existing D0023 share-link machinery (ShareLinkStore create/redeem/unredeem/list/revoke/purge, already hardened with single-use claims, rollback, expiry sweep, and delete-remanence purges) means the change is mostly RETIREMENT + a thin onboarding endpoint, not new security primitives. Link-as-invite is sound because the share link IS an authorization artifact minted by the vault owner — semantically an invite scoped to one vault — so honoring it for account creation under Closed registration is consistent with invite tokens, and single-use+expiry bound the exposure. The COMBINED atomic /api/share-redeem-register (vs a peek-based register that leaves the token valid) is chosen specifically so one link cannot be amplified into many accounts. Deriving 'last used' from the .sync-index.db mtime is the honest zero-migration proxy: it is real server-side write activity (covers deletions, not client-spoofable), and per-vault segmented storage makes a central activity table neither available nor desirable (D0005). ALTERNATIVES: (i) keep both grant paths — REJECTED by the owner (two mechanisms muddy the model; username path is the worse UX). (ii) peek-based register-then-separate-redeem — REJECTED: leaves the link valid between register and redeem, letting one invite spawn N accounts. (iii) a server-hosted web redemption page — REJECTED by the owner: the recipient is setting up the plugin anyway, so onboarding lives in the plugin. (iv) add a stamped updated_at via a schema migration for 'last used' — DEFERRED: the .sync-index.db mtime proxy is honest and free; promote to a stamped field only if per-event precision is later needed. CRITERIA: single-canonical-path x reuse-hardened-primitives x atomic-one-link-one-account x honest-zero-migration-metric x onboarding-in-the-plugin.";
        :>> consequences = "PRODUCT behavior changes (a server image redeploy is required, not just a plugin release): the admin console loses the grantee-username share input and gains a single Sharing section (vault dropdown -> share link, active-links + grants with revoke, account-creation link) + per-vault last-used + a registration toggle; the plugin loses its grantee-username share UI and its redeem flow gains create-account-or-login. New public endpoint /api/share-redeem-register; removed endpoints POST /api/admin/shares and GET /api/admin/usernames (DELETE /api/admin/shares kept). CAPABILITY LOSS (accepted): you can no longer pre-share to a not-yet-registered username as a dormant grant — the recipient creates an account (from the link, even under Closed registration) or logs in, then accepts. Server + client tests that asserted the grantee-username create path (server/tests/admin.rs owner_grants_and_revokes_a_share / share_create_does_not_reveal_grantee_existence / the public-surface reachability test; client/e2e-admin/admin.pwspec.ts share-create; the plugin shareVault tests) are updated to the link path; the ShareStore + share-link unit tests (grant via the store) are unaffected. This decision is DELIVERABLE-domain (no engine schema/workflow/process/skill change), so no #ProspectiveChange and no CLAUDE.md change; it is recorded here because §3c/§4 require a recorded rationale + acceptance for a product model change, and it #Resolves the sharing-consolidation issue in .tracking. Delivered across sprints (Phase 1 admin/server, Phase 2 onboarding server+plugin) tracked in .tracking/delivery/delivery.sysml.";
    }

    verification d0037Accept : Test {
        :>> id = "3a0b5e28-7d1c-4f3b-a024-8b2d3e4f5061";
        :>> method = VerificationMethod::confirmation;
        :>> procedureText = "wweatherholtz directed this change in their own words across 2026-08-03: 'remove the ability for grantee username. we'll just use share links to canonically accept shares'; then refined the onboarding — 'make a pathway for users to make an account OR login to redeem a link. account first, then link - the vault share link implies both, the account creation link just makes the first'; then, presented with the two flagged consequences (link-as-invite bypasses Closed registration; redemption happens in the plugin), answered 'yes on both. confirm and begin, then carry out to completion. no need for reviews at this point - i'll check content in testing later.' The specific endpoint/UI design (combined /api/share-redeem-register, single Sharing section, .sync-index.db mtime for last-used) is the AI's implementing design fulfilling those directives.";
    }
    part d0037AcceptR1 : TestResult {
        :>> id = "4b1c6f39-8e2d-4a4c-b135-9c3e4f506172";
        :>> outcome = VerdictKind::pass;
        :>> judgedAgainst = "df13c56";
        :>> judgedAt = "2026-08-03";
        :>> judgedBy = "wweatherholtz";
    }
}
