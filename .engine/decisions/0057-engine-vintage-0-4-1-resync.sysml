// =====================================================================
// D0057 (PROJECT numbering) — the engine library is resynced onto keel 0.4.1 (build 21e43e6), the gating family moves to
// `keel gate …` in the hook and CLAUDE.md, the activation manifest is chartered by a PROJECT decision, and the Claude
// surface is regenerated by the new binary. PROPOSED: this is a process-definition + enforcement-surface change (D0070,
// D0209 clause 2) applied in the same commit under the committed transform
// `.engine/tools/migrations/2026-09-13-engine-vintage-0-4-1-resync.py` (D0067; the D0108 ownership suspension that
// transform announces is the only way the engine's own rewrite of its shipped items can land). The owner accepts via
// `keel accept d0057`. No `<id>Accept` placeholder is authored here (keel accept writes its own — upstream #71).
// =====================================================================
package ProjectDecision0057 {
    private import EngineElement::*;
    private import EngineWork::*;
    private import EngineVerification::*;
    private import EngineRelationships::*;
    private import ProjectDecision0050::*;

    #ProspectiveChange part d0057 : Decision {
        :>> id = "eb57d606-9611-46aa-a1d2-2ebe50a2b928";
        :>> title = "D0057: .engine/ resynced onto keel 0.4.1; the hook and CLAUDE.md use the `keel gate` family; activation.toml is chartered by d0057; the Claude surface is regenerated";
        :>> createdAt = "2026-09-13";
        :>> createdBy = "claudeOpus";
        :>> status = DecisionStatus::accepted;
        :>> context = "Owner, 2026-09-13: 'Where's my decision page? Update keel and library'. The decision page is the keel console (`keel serve`, http://127.0.0.1:7777: orient / decisions / approve queue / deck). The installed binary was 0.3.1 (build 7c34bb7, 2026-09-03); the toolkit repo had moved 925 commits to 0.4.1 (21e43e6, 2026-09-13), whose engine vintage this project's pin (engine-version.toml = 0.3.1) refused to gate under skew - so neither the console's writes nor any gate could run on the new binary until the tree moved. `keel migrate .` (0.4.1) verifies with the project's own gate and rolls back atomically; on this tree it rolled back every time because it overwrites `.engine/schema/codeaudit/codeelement.sysml` with the stock copy while `.tracking/architecture/elements.sysml` uses the enum members THIS project added there (567 semantic diagnostics). The 2026-09-07 transform's sentinel for that file ('CodeElement') also matches the stock copy, so its restore step did not fire. 0.4.1 also renamed the gating family (validate / check / check-engine / guard / rules / assured / adoption-check under `keel gate`, D0452) - the pre-commit hook's `keel validate .` / `keel guard` printed the top-level usage and would have gated nothing - and its activation-manifest guard requires `charteredBy` to resolve to a PROJECT decision (the file cited the engine's d0226).";
        :>> decision = "The engine library is brought to the 0.4.1 vintage by `keel migrate --no-verify .` followed by the committed transform. The transform restores the two project-owned files the migrate overwrites — codeelement.sysml (sentinel now `serializedActor`) and activation.toml (re-pointed to charteredBy = d0057) — re-runs the 2026-09-07 transform, which is idempotent (30 markers declared, the project's skills and processes preserved), rewrites the hook and CLAUDE.md to `keel gate validate .` / `keel gate guard` / `keel gate check-engine .`, and runs `keel sync-claude .` (55 skills, stamped 0.4.1 21e43e6). The migrate re-stamps the pin to 0.4.1; the previous binary is kept at ~/.local/bin/keel-0.3.1-7c34bb7.bak.exe, and the seventeen `.engine/` files 0.4.1 does not ship — the project's six processes plus stpa.sysml, schema/core/risk.sysml, nine per-skill registries — stay as the migrate preserves them. Under the new guard set every Issue resolver names the Issue it resolves in its DoD text, because the 0.4.1 `issues` guard (D0304) reads an edge alone as no triage. Two new HARD guards fail on this tree for reasons only the owner can discharge, and they are recorded as Issues with OPEN resolvers rather than worked around: `acceptance-binds-to-text`, where d0014, d0025 and d0046 had their text edited editorially after acceptance in 2026-07 and on 2026-09-07 and only `keel accept <d> --rebind` can re-sign them; and `decision-scaffolding` under D0303 option C, where the seven Decisions created on or after 2026-09-05 that enumerate several clauses — d0046, d0048, d0050, d0051, d0053, d0054, d0055 — must become one Decision per clause with #DependsOn edges superseding the compound one, unless the owner rules otherwise upstream on the cutoff. This Decision is deliberately written as one narrative rather than as numbered clauses.";
        :>> rationale = "The owner asked for the update and for the decision page; the page's writes (accept / deck) require the binary and the tree to agree on a vintage, so the resync is the prerequisite, not an option. Running the migrate without its auto-revert and restoring the project-owned files afterwards is the same sequence D0050 recorded for 0.3.1, made repeatable in a committed transform (D0067) rather than done by hand; the transform is also what makes the migrate's rewrite of engine-owned items (`.engine/cli/commands.sysml`, owned by the engine's own actor) pass the ownership guard honestly - the suspension is announced, not claimed. Renaming the gate invocations is not optional: a hook that prints usage gates nothing, which is exactly the silent-control-failure class D0209 exists for. The two blocking guards are NOT gamed: rebinding an acceptance is the human's signature (D0308), and splitting accepted compound Decisions re-proposes them - both are the owner's calls, so they are Issues with resolvers and the commit that lands this Decision is gated by the owner discharging them (or deciding otherwise). WHY PROPOSED: process definitions, contracts and the hook changed (D0070 / D0209).";
        :>> consequences = "keel 0.4.1 gates every commit (73 guards, 64 hard); `keel serve` is the decision page. Until the owner rebinds d0014/d0025/d0046 and decides the compound-Decision question, `keel gate guard` FAILS on those two guards and no commit can land - the migrated tree waits in the working copy (reproducible from HEAD by the transform). Downstream: CLAUDE.md §5/§6 name the gate family; `.claude/` is regenerated (hooks, skills, output style; `.claude-plugin/marketplace.json` new). REMOVAL PATH: `git checkout -- . && git clean -fd .engine .claude` restores the 0.3.1 tree; reinstall the backed-up binary. Accept with `keel accept d0057 --by wweatherholtz --date <d> --note \"owner's words: '...'\"`.";
    }
    #Supersede dependency from d0057 to d0050;

    // acceptance event (D0121 review-queue sign-off; D0066/D0106 — human-judged, not fabricated)
    verification d0057Accept : Test { :>> id = "c2f03f20-7f79-4737-9e0a-89cff02fae2d"; :>> method = VerificationMethod::confirmation; :>> procedureText = "owner's words: '[x] Ratify the update as applied' (decision page digest pasted by the owner on 2026-09-13) WARN: read-back - the quoted words do not name d0057 (D0201 B); recorded as given (D0423)."; }
    part d0057AcceptR1 : TestResult { :>> id = "1f529c70-c4c8-4363-a1e7-9d97300f9e84"; :>> outcome = VerdictKind::pass; :>> judgedAgainst = "d7fc5711"; :>> judgedAt = "2026-09-13"; :>> judgedBy = "wweatherholtz"; :>> createdBy = "wweatherholtz"; }
}
