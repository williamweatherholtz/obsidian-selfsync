// D0093 (status: the `status` field below is the truth) — D0093: finding dispositions are collected on a published disposition ledger when the owner is away from the console, and recorded from their pasted digest through the write API
// Recorded via `keel record decision` (D0105 RMWX axis; issue054). Acceptance is a separate explicit
// human gate (method=confirmation, D0106): flip status + add the d0093Accept event on sign-off.
package Decision0093 {
    private import EngineElement::*;
    private import EngineWork::*;
    private import EngineVerification::*;
    private import EngineRelationships::*;

    // #ProspectiveChange (D0070) - this Decision governs a process/schema change; the co-committed
    // change rides the process-change guard's hard lock.
    #ProspectiveChange part d0093 : Decision {
        :>> id = "6a25ca34-73e5-441f-aca1-2d966819ed71";
        :>> title = "D0093: finding dispositions are collected on a published disposition ledger when the owner is away from the console, and recorded from their pasted digest through the write API";
        :>> createdAt = "2026-09-13";
        :>> createdBy = "claudeOpus";
        :>> status = DecisionStatus::accepted;
        :>> context = "Owner, 2026-09-13: 'Accept decisions - I can revert/supersede later as needed. I'm not local, so can't use keel serve'. The authority queue held 208 findings rated Medium or higher with no typed disposition, all of them dated between July and September, and the only surface that collects a D0092 disposition was the console deck at http://127.0.0.1:7777, which needs the owner on the machine that holds the tree. The decision page (D0092) had pointed the disposition rows at that deck rather than itemising them, because the executive-brief contract caps a tab at 450 words and cannot carry 208 rows. `keel render issues --mode review` lists every Issue but offers only the critique verdicts accept and finding, and its Export button downloads a file, which the Artifact sandbox blocks; `keel deck --out` writes the deck as a file but every tap posts to the server. The write path already exists: `keel record review --batch` accepts act, accept-risk and dismiss per element and writes each as a method=confirmation verification carrying disposition : DispositionKind with a #Dispositions edge, in the judge's per-actor critiques file. What was missing was a surface the owner can reach remotely and a channel that carries their words back without paraphrase.";
        :>> decision = "The disposition ledger is a second page under docs/decision-page, built by dispositions.py from the tree alone: the dispositions lens supplies the pending set, each finding's Issue record supplies its title, description, date and field flag, and each #Resolves resolver is read with its recorded verdict so the findings group by what has already happened to them, which is the fact that decides most of them. Each row offers act, accept risk or dismiss with an optional note, each group offers the same three as a whole-group gesture, and the page writes nothing: it composes a plain-text digest naming the tree, the actor and every finding under its verdict with control totals, which the owner copies and pastes into the chat. record_dispositions.py then records that digest verbatim as a Statement, checks every named id against the lens and every count against its list, and writes the dispositions through `keel record review --batch` against the tree the owner saw, each rationale citing the statement and the owner's note. The decision-surfacing skill names this ledger as where findingDisposition rows go when the owner is not at the console; the decision page itself is unchanged. The page is published as its own Artifact and republished at the same path when the pending set changes, under the same state test the decision page uses.";
        :>> rationale = "A disposition is the human's typed judgment (D0092, D0016); the agent may carry it but never choose it, so the surface has to put the choice in front of the owner wherever they are, and the channel back has to carry their exact words, which is what a Statement is for (D0216). Grouping by resolver state is the honest framing: 201 of the 208 findings already have a shipped fix, three are mooted by an accepted Decision and four wait on an open task, so the owner's real question is per group, and a whole-group gesture is one explicit attestation over a named set, batchable as D0019 allows, not an inference. The rendered review view was not extended because its verdicts are critiques, a different record with a different meaning, and a bespoke renderer per view is the render skill's second anti-pattern; this page renders one lens for one purpose, the same way the decision page renders the authority queue. Control totals in the digest and a refusal on any unknown id are the migration discipline applied to a batch write (D0067): counts must balance before anything lands. WHY PROCESS-CHANGE: the decision-surfacing skill gains a step, so the commit carries this marked Decision (D0070).";
        :>> consequences = "The owner can disposition remotely; nothing is recorded until their digest is pasted, and a row left blank stays open in the lens. Dispositions land in .tracking/critiques-wweatherholtz.sysml as the judge's own records, with one Statement holding the digest. The ledger is a UI page, not an executive brief, so the asi-templates brief checker does not apply to it; it shares the brand tokens and fonts. The pending count on the decision page keeps coming from the authority queue and drops as dispositions land. REMOVAL PATH: delete the two scripts and the ledger, and the skill paragraph that names them; the deck at the console remains the local surface. Accept with `keel accept d0093`.";
    }

    // acceptance event (D0121 review-queue sign-off; D0066/D0106 — human-judged, not fabricated)
    verification d0093Accept : Test { :>> id = "e0abbd43-a5d9-44f9-a174-709d359c4b64"; :>> method = VerificationMethod::confirmation; :>> procedureText = "owner's words: '[x] Adopt the remote disposition ledger' (decision page digest pasted by the owner on 2026-09-16) WARN: read-back - the quoted words do not name d0093 (D0201 B); recorded as given (D0423)."; }
    part d0093AcceptR1 : TestResult { :>> id = "44c044d3-943b-4161-b420-aee967235a1b"; :>> outcome = VerdictKind::pass; :>> judgedAgainst = "2d9cfcee"; :>> judgedAt = "2026-09-16"; :>> judgedBy = "wweatherholtz"; :>> createdBy = "wweatherholtz"; }
}
