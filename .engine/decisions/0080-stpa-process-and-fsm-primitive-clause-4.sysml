// =====================================================================
// d0080 (PROJECT numbering) — clause 4 of 5 of D0053 ("D0053: STPA is an activated project process (Steps 1–6) deployed by the safety-analysis skill, and hazard-bearing state is a fsm.ts machine registered on its STPA process model"), recorded as its own Decision per
// D0303 option C (one Decision per clause, #DependsOn between them, the chain superseding the compound one) so the
// decision-scaffolding guard can see which clause an edge charters. The text is the parent's clause VERBATIM; the
// rationale and consequences are the parent's, which the clauses share. Status follows the parent's acceptance path:
// PROPOSED — the owner accepts each clause; the compound d0053 is retired by the #Supersede edge from clause 1.
// =====================================================================
package ProjectDecision0080 {
    private import EngineElement::*;
    private import EngineWork::*;
    private import EngineVerification::*;
    private import EngineRelationships::*;
    private import ProjectDecision0053::*;
    private import ProjectDecision0079::*;

    #ProspectiveChange part d0080 : Decision {
        :>> id = "5d299bf6-8729-427f-b4ec-a91b8d7bb37e";
        :>> title = "D0080 (D0053 clause 4/5): Applied now: resolvefsm (pmResolver), mountfsm + transportstate (pmSyncEngine), connstate linkMachine (pmSessi";
        :>> createdAt = "2026-09-13";
        :>> createdBy = "claudeOpus";
        :>> status = DecisionStatus::accepted;
        :>> context = "Clause 4 of 5 of D0053 (created 2026-09-08, proposed), split out on 2026-09-13 under keel 0.4.1's decision-scaffolding guard (D0303 option C, issue331): a compound Decision hides which clause a chartering edge delivers. The parent's context: Owner, 2026-09-08, after a conflict-resolution flow was rebuilt as a state machine: 'FSM module, used all across the project in places where states that can introduce hazards exist. do we have an activated STPA process with step 1, step 2, etc.?' The facts: STPA ran here as a SKILL (.engine/skills/stpa + references/sop.md, D0016) — the analysis itself is complete in .tracking/safety (5 losses, 10 hazards, 7 controllers, 22 UCAs, 19 scenarios, 25 SRs, every SR #Verify-linked as of e540b786) — but there was no `stpa` PROCESS: no ProcessSteps, no successions, no APPLIES-WHEN, no reanalysis trigger, and `keel activation` listed only the engine's stpa-diagram. Separately the client held five hand-rolled state machines (connstate linkNext, syncengine EngineState, mountfsm, transportstate, and the new resolvefsm), each a pure reducer of its own shape, none built on a shared primitive, none named by the STPA controller or process model it realizes — so 'a state that can introduce a hazard' was a switch statement the safety analysis could not see. The 2026-09-07 incident (a Keep pressed while a 152 s pass was running over the same files, S-20) is exactly a resolver whose process model had no belief about the engine's state.";
        :>> decision = "Applied now: resolvefsm (pmResolver), mountfsm + transportstate (pmSyncEngine), connstate linkMachine (pmSession) are on the primitive with their exported signatures unchanged; syncengine's EngineState is PENDING (issueEngineFsmNotOnPrimitive, engineFsmOnPrimitive).";
        :>> rationale = "Shared with D0053, whose clauses were decided together: A safety analysis is only as good as its visibility into the states that can go wrong. With five reducers of five shapes and no registration, Step 3 could not say which control actions a state transition issues, Step 5 had nothing to hang a reanalysis on, and a new machine (resolvefsm, this week) could be added with no safety question asked at all. One primitive gives every machine the same three properties the analysis needs — a total table (tableCoverage proves nothing throws and nothing invents a state), declared terminal states (the irreversible ones), effects as data (what a transition DOES is enumerable) — and the registration makes the mapping machine <-> controller a fact in the model that a test enforces, not a comment. Making STPA a process rather than a skill matters for the same reason the engine makes everything else a process (D0059): a skill is applied by vigilance, a process has steps a ceremony can point at, an APPLIES-WHEN onboarding can recommend, and a Step 5 trigger that names when the analysis is stale. ALTERNATIVES: (i) leave STPA as a skill and the FSMs as they were — REJECTED, it is exactly the state the owner objected to; (ii) a heavyweight FSM library — REJECTED, the five machines are small pure reducers and the property wanted is uniformity + enumerability, not hierarchical states; ~80 lines of primitive give that; (iii) refactor syncengine now too — REJECTED for this commit: its transitions are interleaved with effects in a class and deserve a behaviour-preserving sprint of their own with a Step 5 reanalysis of c2SyncEngine, so it is registered PENDING with a tracked resolver rather than half-moved. WHY PROPOSED: adding a process definition and a deploying skill is a process/schema-surface change (§3a, §4, D0070); the owner asked the question, the answer is a change to how the project works, and that carries a human signature. THE SPLIT ITSELF: recorded one Decision per clause so that partial delivery is visible to the scaffolding guard and each clause can be chartered, accepted or superseded on its own; the wording is the parent's, unchanged.";
        :>> consequences = "Those of D0053 that this clause carries: `keel activation` lists stpa as an always-on project process; process-skill and process-applicability guards pass (safety-analysis names the process file; APPLIES-WHEN present). fsm.test + fsm-conformance.test run in the client suite (912 -> 924 tests at introduction). control-structure.sysml carries the STPA-FSM registrations; the safety model gains c8ConflictResolver (+ pmResolver, 3 control actions, 1 feedback, 3 UCAs, 3 constraints, 1 scenario, 2 SRs, all typed, SR-26/27 #Verify-linked to passed DoDs). Open follow-up: engineFsmOnPrimitive (syncengine on the primitive + the PENDING flip). REMOVAL PATH: `git revert` of the commit restores the skill-only STPA and the hand-rolled reducers; the safety-model additions are plain items and edges and would revert with it. Accept with `keel accept d0053 --by wweatherholtz --note ... --date ...` from the owner's own terminal.";
    }
    #DependsOn dependency from d0080 to d0079;

    // acceptance event (D0121 review-queue sign-off; D0066/D0106 — human-judged, not fabricated)
    verification d0080Accept : Test { :>> id = "63d01374-a6e3-45ec-bf57-0de0a5754588"; :>> method = VerificationMethod::confirmation; :>> procedureText = "owner's words: '[x] Accept all 34 clause records' (decision page digest pasted by the owner on 2026-09-13) WARN: read-back - the quoted words do not name d0080 (D0201 B); recorded as given (D0423)."; }
    part d0080AcceptR1 : TestResult { :>> id = "dd3a0a81-7b21-40d9-97aa-d8c820a9603e"; :>> outcome = VerdictKind::pass; :>> judgedAgainst = "d7fc5711"; :>> judgedAt = "2026-09-13"; :>> judgedBy = "wweatherholtz"; :>> createdBy = "wweatherholtz"; }
}
