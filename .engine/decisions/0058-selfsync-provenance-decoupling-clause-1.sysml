// =====================================================================
// d0058 (PROJECT numbering) — clause 1 of 3 of D0046 ("D0046: decouple SelfSync's provenance from obsidian-livesync — delete the 5 orphan pre-rewrite tags, rename the retired 'new-livesync' working name in build identifiers, and state independent-implementation provenance"), recorded as its own Decision per
// D0303 option C (one Decision per clause, #DependsOn between them, the chain superseding the compound one) so the
// decision-scaffolding guard can see which clause an edge charters. The text is the parent's clause VERBATIM; the
// rationale and consequences are the parent's, which the clauses share. Status follows the parent's acceptance path:
// PROPOSED — the owner accepts each clause; the compound d0046 is retired by the #Supersede edge from clause 1.
// =====================================================================
package ProjectDecision0058 {
    private import EngineElement::*;
    private import EngineWork::*;
    private import EngineVerification::*;
    private import EngineRelationships::*;
    private import ProjectDecision0046::*;

    part d0058 : Decision {
        :>> id = "deb7581e-4eaf-4d6e-9cb7-e454860d27aa";
        :>> title = "D0058 (D0046 clause 1/3): Three coordinated actions, all owner-approved before execution. DELETE the five orphan tags 0.1.0-0.5.0 from o";
        :>> createdAt = "2026-09-13";
        :>> createdBy = "claudeOpus";
        :>> status = DecisionStatus::accepted;
        :>> context = "Clause 1 of 3 of D0046 (created 2026-09-07, accepted), split out on 2026-09-13 under keel 0.4.1's decision-scaffolding guard (D0303 option C, issue331): a compound Decision hides which clause a chartering edge delivers. The parent's context: The owner observed that the public repository (williamweatherholtz/obsidian-selfsync, public since 2026-07-04) reported 38 CONTRIBUTORS and read this as external traction. Investigation showed it was not: the repo has 0 stars, 0 forks, 0 watchers, 0 pull requests, 0 issues, and GitHub reports fork=false with no parent. `git shortlog -sne HEAD` returns ONE human author (wweatherholtz, 615 commits); the two additional graph entries are Claude Co-Authored-By trailers. The remaining ~35 authors were reachable ONLY through five orphan tags (0.1.0 through 0.5.0), which sat on the PRE-REWRITE history — an ancestry descending 1475-1497 commits to vrtmrz/obsidian-livesync's 2021-10-12 initial commit. The project was squashed to a fresh root (98948a58, 286 files / 29022 insertions) early on 2026-07-04 and every release from 0.6.0 forward is that clean 615-commit line, but those five tags were never deleted, and GitHub's contributor graph walks ALL refs including tags. Two consequences followed. (1) The contributor count materially misrepresented the project. (2) Those tags still PUBLISHED upstream material — tag 0.5.0's tree carried upstream type stubs under obsolete/_types/src/lib/src/ — while carrying no LICENSE at all at that point (`git show 0.5.0:LICENSE` was empty), under a repo whose current LICENSE names only the owner. Separately, the retired working name 'new-livesync' was still baked into build identifiers: the Rust crate (package + lib + bin), client/package.json, three TypeScript class names across 10 files, server/Dockerfile, and several live docs — residue that reads as a livesync lineage to anyone browsing the repo. The owner stated the ground truth plainly: livesync inspired the problem statement and nothing more — 'In no way does this rely on livesync other than a way to do some of these ideas poorly.' Verification supports that: client dependencies are qrcode-generator alone (no pouchdb, no couchdb, no octagonal-wheels), the server is an independent Rust implementation (D0005 chose a custom server over CouchDB), current HEAD's tree contains no upstream source, and both wire-signature artifacts contain zero crate-name references. PROVENANCE CORRECTION (recorded 2026-09-07, same sitting): the 'no upstream source' clause above is WRONG and is corrected here rather than rewritten. A complete audit (the earlier sweep was truncated by a head -40 and missed it) found TWO files that ARE derived from obsidian-livesync: client/e2e-obsidian/helpers/obsidian.ts and helpers/obsidianFunctions.ts, both self-declaring 'Ported from origin/test_real_obsidian' and confirmed authored by vorotamoroz on 2026-05-11/14, with ~50 percent of our code lines identical (including waitForCDP's signature and the global app type declaration). The original check was filename- and dependency-based, so it could not see a file whose own header declared the derivation. Scope: NEITHER file is bundled into the built plugin, so nothing SHIPPED contains upstream code, but both are distributed in repo source, so upstream's MIT notice-retention duty applies to them. Tracked as issueForkedE2eHelpersUnattributed, awaiting an owner choice between attributing them and re-implementing them; the README 'Prior art' wording is to be revisited under whichever path is chosen. This does NOT disturb the tag deletion or the naming rename, whose bases are independent of this clause.";
        :>> decision = "Three coordinated actions, all owner-approved before execution. DELETE the five orphan tags 0.1.0-0.5.0 from origin and locally — the full set not descended from the squashed root, chosen over the owner's initial count of four after the discrepancy was surfaced rather than guessed (keeping 0.1.0 would have left the entire upstream ancestry reachable and achieved nothing).";
        :>> rationale = "Shared with D0046, whose clauses were decided together: The tags had to go because a git ref that pins 1497 unrelated commits and ~35 unrelated authors into a public repo makes the repository assert something false about its own authorship, and because those same refs were the only thing still publishing upstream source from this repo. Deleting them is the narrowest action that fixes both at once — it removes the upstream code and the misattribution together, without touching a single commit on main. The full five were taken rather than four because the goal is a property of the ref set, not a count: any surviving pre-rewrite tag keeps the whole ancestry reachable, so a partial deletion would have looked done while changing nothing. NO upstream MIT notice was added, and this is the substantive licensing call: MIT's notice-retention obligation attaches to copies of the covered work, and once the tags are gone this repo contains none — asserting a livesync copyright in NOTICE would state a derivation that does not exist, which is a different misrepresentation in the opposite direction and would muddy the provenance the owner asked to clarify. Credit therefore belongs as prior-art attribution in prose, where it is true and useful, not as a copyright notice. The naming rename matters because build identifiers are what a reader greps: a crate literally named new-livesync-server is read as lineage regardless of what the README says, so leaving it would have left the decoupling half-done. It went through a committed codemod rather than hand-edits because it touched 115 sites across 25 files, which is exactly the silent-miss class D0067 exists to gate — the reconciliation caught nothing wrong here, but the counts BALANCING is the evidence, not luck. Critically, the bare legacy plugin id 'new-livesync' was EXCLUDED from the rename: configsync.ts LEGACY_SELF_IDS uses it to exclude the FORMER plugin folder's data.json — this device's server URL and credentials — from config sync, so renaming it would have reintroduced a credential-leak path. Every codemod rule matches a strictly longer string, so the bare id is preserved by construction, and a post-check asserts its count is unchanged (36 -> 36). THE SPLIT ITSELF: recorded one Decision per clause so that partial delivery is visible to the scaffolding guard and each clause can be chartered, accepted or superseded on its own; the wording is the parent's, unchanged.";
        :>> consequences = "Those of D0046 that this clause carries: Five tags deleted from origin and locally; `git shortlog -sne --all` now returns exactly one author, and the ~1497 upstream commits are unreachable (GitHub's contributor graph should settle to 3 — the owner plus two Claude trailer identities — on reindex). Tag deletion on a remote is NOT reversible from the remote side; it was executed only after explicit owner approval naming the set. The Rust binary is now selfsync-server, so server/Dockerfile and Cargo.lock changed with it; the wire signature is UNAFFECTED (verified: both wire-signature.json artifacts contain no crate-name reference), so no client/server compatibility gate moves and no forced redeploy follows from the rename itself. Three TypeScript types are renamed (SelfSyncPlugin, SelfSyncSettings, SelfSyncSettingTab). One OPEN issue's description (issuePatternUntaggedShouldAdopt) had its stale NewLiveSyncSettings symbol updated so the refactor target it names remains actionable — a forward-looking work description, not an attestation. Dated plan documents under docs/design/plans/ were left as written: their claims are true for their dates, and rewriting them would falsify the record. Verified green at this change: server cargo test 234 passed / 0 failed, clippy -D warnings clean, client tsc clean, client vitest 830 passed / 2 skipped (unchanged from the 1.30.0 baseline, so the rename altered no behavior), production build clean, keel validate 14 files clean, keel guard ALL PASS. Two pre-existing observations surfaced but deliberately NOT fixed here as out of scope: client/package.json is at version 1.22.0 while manifest.json is at 1.30.0, and the NoteConflictModal performance defects that opened this session remain open.";
    }
    #Supersede dependency from d0058 to d0046;

    // acceptance event (D0121 review-queue sign-off; D0066/D0106 — human-judged, not fabricated)
    verification d0058Accept : Test { :>> id = "c434d44f-f76f-4b43-8c72-b50b3672abcf"; :>> method = VerificationMethod::confirmation; :>> procedureText = "owner's words: '[x] Accept all 34 clause records' (decision page digest pasted by the owner on 2026-09-13) WARN: read-back - the quoted words do not name d0058 (D0201 B); recorded as given (D0423)."; }
    part d0058AcceptR1 : TestResult { :>> id = "98a6a4fb-5e44-4faa-a365-c1ab18310975"; :>> outcome = VerdictKind::pass; :>> judgedAgainst = "d7fc5711"; :>> judgedAt = "2026-09-13"; :>> judgedBy = "wweatherholtz"; :>> createdBy = "wweatherholtz"; }
}
