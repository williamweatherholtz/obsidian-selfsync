// =====================================================================
// D0021 — split the ADMIN surface onto its own optional private bind address, and harden the admin
// portal. The server can bind /admin + /api/admin/* to a SEPARATE port (ADMIN_BIND_ADDR) so a
// reverse proxy exposes only the public sync/login port; the admin surface stays localhost/VPN.
// Because the admin surface is then private, several portal features that were unsafe on a public
// oracle become safe: grantee autocomplete (fuzzy match against real usernames), and per-user admin
// promotion. Plus: registration as a toggle (not a button), owner self-service vault-delete in "My
// vaults", and a deliberate client "re-create this vault from this device" prompt (deleted-vault
// semantics = keep today's no-loss behavior, made an explicit user action). Deliverable
// (SelfSync server + plugin) change. Accepted 2026-07-08 by wweatherholtz via the design questions.
// =====================================================================
package ProjectDecision0021 {
    private import EngineElement::*;
    private import EngineWork::*;
    private import EngineVerification::*;

    part d0021 : Decision {
        :>> id = "c0f1a5cc-f140-4a10-9b20-a1b2c3d40f50";
        :>> title = "D0021: private admin bind address + admin-portal hardening";
        :>> createdAt = "2026-07-08";
        :>> createdBy = "wweatherholtz";
        :>> status = DecisionStatus::accepted;
        :>> context = "Today one axum Router on one port serves everything: the /admin HTML page, /api/admin/* (BOTH server-admin functions — accounts/registration/invites — AND owner self-service — a user's own vaults + shares), /api/login, /api/register, and all sync routes + the WS. A self-hoster wanting to expose sync through a reverse proxy has no way to keep the admin surface off the public internet short of hand-written proxy path rules (fragile — one misconfig exposes account management). Admin identity is hardcoded is_server_admin(user)=(user==SYNC_USER): the single bootstrap account, with no way to grant admin to another user. Sharing takes a raw grantee string and 400s 'no such account' on a miss — a blind match that both frustrates typos and (on a public surface) is an account-enumeration oracle (issueShareEnumeration, accept-risk). Registration is toggled by a button; per-vault delete lives only in the admin repair panel (admin-only); and a device still syncing a DELETED vault 404s with a message but has no one-tap way to re-adopt.";
        :>> decision = "(1) SPLIT — SAFE BY DEFAULT (opt-out, per owner 2026-07-08): by DEFAULT the /admin page + /api/admin/* bind ONLY to a private, LOCALHOST-only admin address (ADMIN_BIND_ADDR, defaulting to 127.0.0.1 on the public port + 1), and the public BIND_ADDR serves sync + /api/login + /api/register + /health only — so a naive deploy never exposes account management. An operator must DELIBERATELY opt out to merge admin onto the public port: ADMIN_BIND_ADDR=merge (or setting it equal to the public BIND_ADDR) serves both on one port for a trusted/all-in-one setup. (This changes the default for existing single-port deployers — they set ADMIN_BIND_ADDR=merge to keep one port; documented in the upgrade note. Acceptable pre-1.0 for a security-positive default the owner requested.) app() splits into a public router + an admin router; main spawns two servers when the addresses differ. (2) ADMIN SET: replace the hardcoded single admin with a persisted admin set — the bootstrap SYNC_USER is always admin and cannot be demoted; a server-admin can grant/revoke admin on other accounts via POST/DELETE /api/admin/users/:name/admin; is_server_admin consults the set. (3) FUZZY GRANTEE: because the admin surface is now private, expose a username list to the (authenticated) admin page for grantee AUTOCOMPLETE + a client-side fuzzy match, and keep the server-side exists() check — re-dispositioning issueShareEnumeration (the oracle concern was PUBLIC-surface-specific). (4) REGISTRATION TOGGLE: render the open/closed state as a toggle switch, same PUT underneath. (5) OWNER DELETE: an owner-scoped delete of their OWN vault in the 'My vaults' panel (typed confirmation), alongside the existing admin any-vault delete. (6) DELETED-VAULT: keep today's no-data-loss behavior (404 + 'local files untouched'; a re-created same-name vault repopulates from a device's local copy under tombstone-authoritative delete) and ADD a deliberate 'Re-create this vault from this device' action in the plugin so repopulation is an explicit user choice, not silent.";
        :>> rationale = "A separate PORT (not proxy path rules) is the robust isolation: the admin surface is not merely hidden but not BOUND on the public interface, so no proxy misconfiguration can expose account management — defense in depth, and it matches the operator's mental model ('expose one port, not the other'). SAFE BY DEFAULT (owner's explicit call): the split is the DEFAULT and admin is localhost-only, so the failure mode of forgetting to configure it is SECURE (admin unreachable off-host) rather than exposed — strictly better than an opt-in split, whose naive-deploy failure mode leaks account management. The single-binary/simple-Docker thesis (D0054) is preserved via the explicit ADMIN_BIND_ADDR=merge opt-out for trusted/all-in-one deploys. WHOLE-page split (vs. keeping owner self-service public) was chosen because for a self-hoster the operator IS the owner, so putting share-management behind the private port is no loss and avoids a finer, leakier routing split — and it is precisely what makes the fuzzy-grantee autocomplete safe (a username list on a private surface is not a public enumeration oracle, so issueShareEnumeration's accept-risk premise no longer holds). A persisted admin SET is the minimal way to delegate operation without sharing the bootstrap credential. For the DELETED-VAULT question the owner chose KEEP-AND-PROMPT over permanent-tombstone or a grace-period block: the asymmetry favors it — the current behavior already loses NO client data (a device's local copy repopulates a re-created vault), and the only gap is that repopulation was implicit; a one-tap 're-create from this device' makes it deliberate without the complexity + new failure modes of server-side deletion tombstones or name-reservation windows (which a self-hoster who just wants to reset a vault would find surprising). ALTERNATIVES CONSIDERED: (a) reverse-proxy path-blocking of /admin on one port — DECLINED (fragile; a misconfig exposes admin; not defense-in-depth). (b) split server-admin private but keep owner self-service public — DECLINED by the owner (keeps the enumeration oracle public, finer routing split, little benefit when operator==owner). (c) permanent delete via a server-side deleted-vault tombstone — DECLINED (complexity + new failure modes for a case the no-loss keep-and-prompt already handles). (d) block same-name re-create for a grace period — DECLINED (surprising for a deliberate reset; the prompt makes intent explicit instead).";
        :>> consequences = "Tracked as three delivery actions: adminSplitDeploy (the default-on two-router/two-server split — admin localhost-only by default, ADMIN_BIND_ADDR override + =merge opt-out — plus docs/deploy example + an UPGRADE note that existing single-port deployers set ADMIN_BIND_ADDR=merge), adminPortalEnhancements (persisted admin set + promote/revoke endpoints + is_server_admin via the set; registration toggle; grantee autocomplete + fuzzy match; owner self-service vault delete), and deletedVaultRecreatePrompt (the plugin 'Re-create this vault from this device' action on a 404). Re-dispositions issueShareEnumeration (accept-risk → resolved by the private surface). doc-sync: the deployment doc must document ADMIN_BIND_ADDR + the reverse-proxy pattern (expose the public port, keep admin private), and CLAUDE.md/README admin notes updated. Server-side changes deploy on redeploy; the client prompt ships as a plugin release. Each action lands with tests (server unit/integration for the split routing + admin set + owner-delete; client for the re-create action).";
    }

    verification d0021Accept : Test {
        :>> id = "c0f1a5cc-f141-4a10-9b20-a1b2c3d40f51";
        :>> method = VerificationMethod::confirmation;
        :>> procedureText = "wweatherholtz accepted (2026-07-08) via the design questions: admin split = 'Whole admin page → private port' (owner self-service goes private too), REFINED by a follow-up instruction '#1 should be opt-out — safe split by default' → the split is DEFAULT-ON with admin localhost-only and an explicit ADMIN_BIND_ADDR=merge opt-out; and deleted-vault semantics = 'Keep today's behavior + a clearer prompt' (no-loss repopulation made a deliberate 're-create from this device' action, over permanent-tombstone or grace-period-block). The portal items (registration toggle, promote-to-admin, fuzzy grantee autocomplete, owner delete in My vaults) were proposed and accepted as the design.";
    }
    part d0021AcceptR1 : TestResult { :>> id = "c0f1a5cc-f142-4a10-9b20-a1b2c3d40f52"; :>> outcome = VerdictKind::pass; :>> judgedAgainst = "5577631"; :>> judgedAt = "2026-07-08"; :>> judgedBy = "wweatherholtz"; }
}
