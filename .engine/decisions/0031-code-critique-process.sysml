// =====================================================================
// D0031 — Adopt the Antagonistic Code Critique as a first-class engine Process + deploying skill.
// Cements the recurring adversarial code-critique-round activity (round1/round2/round6 + the R+1 pass)
// that had NO skill (a D0040 gap) so it stopped leaking into conversation history where it can't be
// enforced, reviewed, or improved. Accepted 2026-07-19 by wweatherholtz.
// =====================================================================
package ProjectDecision0031 {
    private import EngineElement::*;
    private import EngineWork::*;
    private import EngineVerification::*;

    #ProspectiveChange part d0031 : Decision {
        :>> id = "0d310a1c-7e34-4b55-9a11-2f3c4d5e6a31";
        :>> title = "D0031: adopt Antagonistic Code Critique as a recorded engine process + deploying skill (independent critics, verify-before-record, findings-as-Issues)";
        :>> createdAt = "2026-07-19";
        :>> createdBy = "wweatherholtz";
        :>> status = DecisionStatus::accepted;
        :>> context = "Adversarial CODE critique — independent multi-lens review that hunts real runtime defects in the deliverable source — is this project's most productive quality activity (it drove round1/round2/round6 and the R+1 pass, which found a HIGH mass-delete-remote data-loss vector plus seven more real defects, all fixed). But it had NO skill: element-critique explicitly EXCLUDES routine code review (it critiques tracked Need/SystemRequirement/Decision elements as method=critique verifications), architectural-critique stress-tests the ENGINE + its processes, and function-audit is a per-function idiom/design line-audit with @audit-hash markers — none covers a cross-subsystem adversarial code bug-hunt. So the method lived in conversation history, where it cannot be enforced, reviewed, or improved (the exact D0040 failure mode: a recurring task executed without a skill). The R+1 pass also established the method's defining disciplines — (a) INDEPENDENCE: each critic runs in fresh context (a subagent), never the author, so it truly tries to BREAK the code (the D0080 independent-critic principle applied to code); (b) VERIFY-BEFORE-RECORD: every candidate finding is re-checked against the actual code + tests before it becomes an Issue (this session caught a false 'dead code' claim — a plausible-but-wrong finding recorded as real is the failure mode); (c) COMPUTE-DON'T-ATTEST: a finding is a concrete file:line + failure scenario, a fix carries a fail-first regression, a cleared area is stated as cleared.";
        :>> decision = "Adopt Antagonistic Code Critique as a first-class, recorded engine Process (.engine/processes/code-critique.sysml) with a deploying `code-critique` skill (D0059). The 5-step method: (1) scope the target + choose distinct adversarial lenses (default data-integrity/durability, security/authz, concurrency/races, correctness/protocol; prioritized by keel arch criticality); (2) dispatch one INDEPENDENT critic per lens in fresh context, each instructed to BREAK the code and report only real defects with file:line + mechanism + a concrete failure scenario + severity + confidence (a false positive is worse than silence); (3) VERIFY-BEFORE-RECORD — the mandatory gate — re-check every candidate against the code + its tests/guards, discarding what is already covered / misread / irreproducible, and dedupe across critics; (4) record each CONFIRMED finding as a severity-carrying tracked Issue (D0077, #Resolves from a fixing action) — findings are ISSUES, NOT method=critique verifications, because the code is not a tracked #Verify element (that is element-critique's lane); (5) fix highest-severity-first, each with a FAIL-FIRST regression, validate green + reverify, triaging anything too large to an OPEN follow-on (honest, tracked). Independence + verify-before-record are PROCESS rules (no new guard: findings ride the existing D0077 Issue loop, and the critic-independence guard remains scoped to method=critique verifications on tracked elements).";
        :>> rationale = "D0040 (a recurring task without a skill leaks process knowledge into unenforceable conversation history) + D0059 (every process needs a deploying skill or it is inert) require this: code critique is demonstrably recurring and demonstrably high-value. The R+1 pass proved both the value (a real HIGH finding surfaced after mutation testing + function audits had already run) and the disciplines that make it trustworthy (independent critics + verify-before-record separate real defects from plausible noise). Recording it as a process+skill — not conversation habit — makes the method repeatable, improvable, and honest, and fills the last obvious gap in the deliverable's quality toolkit alongside function-audit (D0028), architecture-audit (D0029), and property-based/mutation testing (D0030).";
        :>> consequences = "New: .engine/processes/code-critique.sysml, .engine/skills/code-critique/SKILL.md (+ the skills-registry entry). No schema change, no new guard (findings are ordinary Issues under D0077; independence + verify-before-record are process disciplines the skill encodes). Neighbouring critique/audit skills gain an explicit 'NOT this skill' boundary vs code-critique. #ProspectiveChange: prior outputs stay valid; no reprocessing is forced. The R+1 pass that motivated this decision is retro-covered by the method (its findings were recorded exactly as the process now prescribes).";
    }

    verification d0031Accept : Test {
        :>> id = "0d31acc7-2b33-4c44-9d55-6e7f80912331";
        :>> method = VerificationMethod::confirmation;
        :>> procedureText = "wweatherholtz directed on 2026-07-19, after the critique R+1 pass closed: 'go ahead and make the code critique skill, and record a proper workflow process using this skill.' — an explicit instruction to adopt the code-critique skill + its process definition as a recorded engine workflow.";
    }
    part d0031AcceptR1 : TestResult { :>> id = "0d31ac00-ab22-4c33-9d44-5e6f70819331"; :>> outcome = VerdictKind::pass; :>> judgedAgainst = "b105b98"; :>> judgedAt = "2026-07-19"; :>> judgedBy = "wweatherholtz"; }
}
