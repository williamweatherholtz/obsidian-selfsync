// =====================================================================
// d0066 (PROJECT numbering) — clause 1 of 8 of D0050 ("D0050: resync .engine/ onto the keel 0.3.1 vintage wholesale under a committed transform, re-applying this project's additions by name — supersedes D0048's deferral"), recorded as its own Decision per
// D0303 option C (one Decision per clause, #DependsOn between them, the chain superseding the compound one) so the
// decision-scaffolding guard can see which clause an edge charters. The text is the parent's clause VERBATIM; the
// rationale and consequences are the parent's, which the clauses share. Status follows the parent's acceptance path:
// PROPOSED — the owner accepts each clause; the compound d0050 is retired by the #Supersede edge from clause 1.
// =====================================================================
package ProjectDecision0066 {
    private import EngineElement::*;
    private import EngineWork::*;
    private import EngineVerification::*;
    private import EngineRelationships::*;
    private import ProjectDecision0050::*;

    #ProspectiveChange part d0066 : Decision {
        :>> id = "37d1c8a3-163c-4223-986e-2ce874e02db3";
        :>> title = "D0066 (D0050 clause 1/8): Run `keel migrate .` to the 0.3.1 stock tree";
        :>> createdAt = "2026-09-13";
        :>> createdBy = "claudeOpus";
        :>> status = DecisionStatus::accepted;
        :>> context = "Clause 1 of 8 of D0050 (created 2026-09-07, proposed), split out on 2026-09-13 under keel 0.4.1's decision-scaffolding guard (D0303 option C, issue331): a compound Decision hides which clause a chartering edge delivers. The parent's context: D0048 (same day) reconciled this project with the keel 0.3.1 binary ADDITIVELY and deferred `keel migrate` because a first attempt clobbered .engine/schema/core/relationships.sysml with the stock copy - 25 metadata def declarations cut to 18, the markers D0045 deliberately added deleted, marker-vocabulary 0 -> 228 violations - while the migrate dry-run had reported 0 blockers. That left issueEngineVintageGateDrift open with the resync as its remaining DoD clause, and the owner then directed 'continue through entire backlog. quality first'. The state of the tree: 260 engine files at a July-2026 vintage under a binary that ships 549, so every control, process, skill, contract and reference decision added between D0107 and D0294 was absent here - among them parser-coverage, evidence-cited, identity-well-formed, ownership, duplicate-identity, base-first-justification and the per-skill registry (D0222). This project's own engine content, which any resync must carry: six processes (architecture-audit, code-critique, functional-decoupling, mutation-testing, property-based-testing, release-versioning), eight skills registered for them, the eleven D0045 markers, schema/codeaudit/codeelement.sysml, contracts/reverify.toml and deliverable-manifest.txt. The resync was rehearsed against a scratch `keel init` tree so the stock shape of every file was known before the live run.";
        :>> decision = "Run `keel migrate .` to the 0.3.1 stock tree.";
        :>> rationale = "Shared with D0050, whose clauses were decided together: The gate that actually runs on every commit - the pre-commit hook, CI, the owner's terminal - is keel 0.3.1, and a binary reading an engine tree six weeks older than itself enforces an unknown mixture: guards whose contracts and schema types are missing pass vacuously or fail on shape rather than substance, which is exactly how issueEngineVintageGateDrift arose. D0048 bought a green gate cheaply and honestly said the resync was deferred, but a project that stays on a vintage its binary no longer ships has no path to any control added since, and the first thing the resync surfaced - a governance lens reading a false zero for the life of the record - shows what that costs. The clobber hazard D0048 rolled back from is real and is handled here by re-application BY NAME under an idempotent, control-totalled transform, not by avoiding the migration: what the stock files overwrite is known (the scratch init), what this project adds is enumerated, and the counts must balance before the commit. ALTERNATIVES: (i) stay additive per D0048 - REJECTED, it leaves the project unable to receive any control the binary adds and leaves the open DoD open indefinitely; (ii) pin an older keel that matches the July tree - REJECTED, the hook, CI and the owner all run 0.3.1, so pinning recreates the two-binary drift that caused the incident; (iii) migrate by hand without a committed transform - REJECTED, D0067 requires a committed transform with reconciled totals for a change of this size, and the ownership guard's only exemption for crossing engine-owned files is a co-committed transform under .engine/tools/migrations/; (iv) CHOSEN. WHY PROPOSED rather than self-accepted: this rewrites process and schema definitions (§3a, §4, §2.5) across 549 files, and the process-change keystone exists precisely so a change of that reach carries a human signature. THE SPLIT ITSELF: recorded one Decision per clause so that partial delivery is visible to the scaffolding guard and each clause can be chartered, accepted or superseded on its own; the wording is the parent's, unchanged.";
        :>> consequences = "Those of D0050 that this clause carries: CONTROL TOTALS (pre -> post): engine files 260 -> 559 (the 557 the resync produced plus this decision record and the transform); AISkill registrations 35 -> 52 (27 stock per-skill + 8 project + the new stock skills), no id lost; metadata def declarations: the 11 D0045 markers re-added, `Changes` retired, 17 engine + 10 project = 27; viewpoints 20 -> 32; parser-coverage skipped 81 -> 7; #Covers AST edges 0 -> 74; project processes 6 -> 6 with 29 successions replacing 35 `order` attributes. GATES under keel 0.3.1 by exit code: validate 0, check-engine 0, guard ALL PASS; the 90 first-green warnings are read and actioned or accepted as listed in the decision. issueEngineVintageGateDrift's resolver (engineVintageResync) records this progress and PASSES only when this decision is accepted - owner acceptance is its first DoD clause. issueNestedCoversEdgesSkipped is recorded and resolved by coversEdgesHoisted; the sitting-coverage lens now counts covering reviews. Carried upstream to the keel toolkit: a nested dependency statement passes `keel check` clean while being skipped; `keel migrate --dry-run` reports 0 blockers for a change that deletes project schema additions. REMOVAL PATH: `git revert` of the resync commit restores the D0048 tree exactly (nothing in .tracking/, client/ or server/ depends on the new vintage except the hoisted #Covers block, which parses in both). Acceptance: `keel accept d0050 --by wweatherholtz --note ... --date ...` from the owner's own terminal - refused from an agent session by design.";
    }
    #Supersede dependency from d0066 to d0050;

    // acceptance event (D0121 review-queue sign-off; D0066/D0106 — human-judged, not fabricated)
    verification d0066Accept : Test { :>> id = "cf3d4ba5-bb7b-4b8a-9b1e-97d8e5cf1c13"; :>> method = VerificationMethod::confirmation; :>> procedureText = "owner's words: '[x] Accept all 34 clause records' (decision page digest pasted by the owner on 2026-09-13) WARN: read-back - the quoted words do not name d0066 (D0201 B); recorded as given (D0423)."; }
    part d0066AcceptR1 : TestResult { :>> id = "f619f835-629d-40d4-ae3d-8969696ae62a"; :>> outcome = VerdictKind::pass; :>> judgedAgainst = "d7fc5711"; :>> judgedAt = "2026-09-13"; :>> judgedBy = "wweatherholtz"; :>> createdBy = "wweatherholtz"; }
}
