// =====================================================================
// D0042 — client<->server compatibility via a DERIVED wire-contract SIGNATURE (replaces the single
// hand-bumped API_VERSION integer + exact-match lockstep). Owner-directed research + owner-accepted
// (2026-08-11, "yes proceed and I agree"). Deliverable-domain PRODUCT behaviour change (no engine
// schema/process change) -> NOT a #ProspectiveChange; same class as D0037-D0041.
// =====================================================================
package ProjectDecision0042 {
    private import EngineElement::*;
    private import EngineWork::*;
    private import EngineVerification::*;
    private import EngineRelationships::*;

    part d0042 : Decision {
        :>> id = "f4d105ba-3a8c-448b-acbc-bb3e156184d7";
        :>> title = "D0042: check client<->server compatibility by a canonical wire-contract SIGNATURE derived from the server's serialized types, diffed field-by-field at the handshake (breaking -> refuse with the specific reason, additive/bugfix -> proceed), and gated in CI against unreviewed contract drift";
        :>> createdAt = "2026-08-11";
        :>> createdBy = "wweatherholtz";
        :>> status = DecisionStatus::accepted;
        :>> context = "Compatibility today is a single hand-bumped integer: server `pub const API_VERSION: u32 = 1` and client `CLIENT_API_VERSION = 1`, exchanged via `status().apiVersion` and checked by `versionVerdict` with EXACT equality (serverApiVersion === clientApiVersion) — any difference is incompatible, fail-closed lockstep. Two problems: (1) it is DOCUMENTATION-CENTERED — a human must remember to bump the integer AND remember whether a change was actually breaking; the number can silently lie about the wire contract (a well-documented failure mode: semver is frequently violated in practice). (2) it is MAXIMALLY STRICT and unhelpful — it cannot 'allow a bugfix' because it has no notion of one, and on mismatch it says only 'v1 vs v2', never WHAT differs. The owner asked to research the landscape (semver vs a diffable API list vs hashing interface signatures) wanting: don't reject on bugfixes, do reject on major/minor-class (breaking) changes, and something CI-worthy rather than documentation-centered — ideally identifying the interface SIGNATURE and telling which side expects what. Research surveyed: runtime semver with directional compatibility (schema-registry BACKWARD/FORWARD/FULL framing); contract-first breaking-change linters (buf breaking, oasdiff, GraphQL Inspector); single-source-of-truth generation from Rust types (schemars -> serde-accurate JSON Schema; ts-rs -> TypeScript); and interface fingerprinting/hashing. KEY FINDING that shaped the design: a HASH detects THAT the contract changed, never WHETHER the change is breaking (deciding semantic compatibility is undecidable in general — Rice's theorem); a naive 'require equal hashes' is STRICTER than today, rejecting bugfixes too. The useful primitive is not a hash but the STRUCTURED signature — comparing structures (not digests) classifies each delta and explains itself. Owner selected (via two decision prompts) BOTH-CI-and-runtime placement and hash-in-poll-plus-lazy-full-fetch as the wire strategy, then accepted the consolidated design.";
        :>> decision = "Derive the wire contract from the server's own serialized types and make the SIGNATURE (not a version integer, not a bare hash) the authority. (1) SOURCE OF TRUTH: `schemars` on the server produces a serde-accurate JSON Schema of the wire request/response types; a normalization pass reduces it to a canonical SIGNATURE — per endpoint {method, path}, the request and response field structure (name -> {type, required}), keys sorted, docs/examples stripped, stable-serialized — hashed to `schemaHash`. The client's embedded signature is GENERATED from the same committed artifact, so a client and server from one release are structurally identical by construction. (2) RUNTIME HANDSHAKE (both-directions, hash-in-poll + lazy full fetch): the server includes `schemaHash` in /status; the client compares it to its embedded hash — match -> proceed at ~zero cost every poll; differ -> the client fetches the full signature from a /schema endpoint, diffs field-by-field against its embedded copy, and produces typed, DIRECTIONAL deltas that ARE the verdict. Breaking (a response field the client reads is removed / retyped / newly-required; an endpoint the client needs is absent; a request field is rejected only under deny_unknown_fields) -> REJECT sync with a message naming the specific field/endpoint and direction ('the server no longer provides response.cursor that this client requires'). Additive (a new optional field, a new endpoint) or identical -> PROCEED — so a bugfix (zero deltas) is never rejected. The integer apiVersion is kept only as a cosmetic human-readable label in logs/UI; the signature diff is the authority. (3) FAIL CLOSED: if the client cannot obtain or parse the server signature — a server too old to expose /schema (no schemaHash), or a fetch/parse failure — treat the peer as incompatible and refuse, with actionable 'upgrade your server' guidance (preserving today's fail-closed posture). (4) CI HONESTY GATE (build-time): a change to the server's wire types regenerates the committed signature artifact; CI fails when the committed signature does not match the types, forcing every wire-contract change to be an intentional, reviewed diff — converting 'trust the human to bump' into 'the human cannot forget'. EXPECTED USE CASES (see .tracking/business/usecases.sysml): ucIncompatibleServerRefused (a field client meeting a breaking server is refused WITH the specific reason + upgrade guidance; additive proceeds; old/unreachable-schema server fails closed) and ucBugfixStillSyncs (a patch release with no wire change has an identical signature hash and syncs with zero friction).";
        :>> rationale = "This gives the owner exactly the split they asked for, grounded in the research: semver's virtue (a human-legible breaking/additive judgment) without its vice (the number can lie), because the STRUCTURE — derived from the actual types — is the ground truth, and a hash's virtue (cheap CI-automatable change-detection) without its vice (a hash cannot tell breaking from additive, and would reject bugfixes) by using the hash only as a cheap change-TRIGGER over the poll and the full structured diff for the verdict. 'Bugfix accepted' falls out for free: a bugfix produces zero structural deltas -> identical hash -> proceed; a breaking change produces a removed/retyped/now-required delta -> reject — with no reliance on anyone bumping a number. The 'insight' the owner wanted ('server expects X OR client expects Y') is a byproduct of diffing structures instead of digests, and is DIRECTIONAL because breaking-ness is not symmetric (a dropped response field starves the reader; an added one is ignored). Deriving the contract from the serde types (schemars) is the single-source-of-truth move that removes the documentation-centered fragility, and the CI gate makes contract drift un-shippable without review. ALTERNATIVES: (i) keep the single integer + exact-match — REJECTED (documentation-centered; over-strict; no insight; the owner's core objection). (ii) runtime semver comparison alone (reject on major/minor, allow patch) — INSUFFICIENT as the sole mechanism: still trusts a hand-set number that studies show is frequently wrong, and gives no field-level insight; semver kept only as a cosmetic label. (iii) a bare hash of the interface ('handshake signature') as the gate — REJECTED: a hash is a pure change-detector, STRICTER than today (flips on bugfixes), and cannot say what differs — the owner's own refinement ('cleaner … and can probably provide insight') is precisely the move from hash to structured signature. (iv) a full contract-linter toolchain (buf/oasdiff/GraphQL Inspector) — deferred: valuable for per-change classification but heavy for a handful of endpoints; the structured field-diff covers the need now and the schemars artifact leaves that door open. (v) full signature on every status poll — declined for steady-state cost; lazy full fetch on hash-mismatch chosen. (vi) drop the integer entirely — declined; kept as a glanceable log/UI label.";
        :>> consequences = "AUTHORIZES a new Need (nProtocolCompat), two use cases (ucIncompatibleServerRefused, ucBugfixStillSyncs), and four SystemRequirements (srWireSignature, srCompatVerdict, srCompatFailClosed, srContractDriftGate) in .tracking/. IMPLEMENTATION SURFACE (a later delivery sprint): server — add schemars to the wire request/response types, a canonicalize+hash step, `schemaHash` in the /status payload, and a /schema endpoint returning the full canonical signature; commit the generated signature artifact + a CI check that fails on drift. Client — embed the release's canonical signature + its hash (generated from the same artifact), compare the hash from status, on mismatch fetch /schema and run a directional field-by-field diff, replace versionVerdict's exact-integer check with the signature verdict (breaking -> refuse + specific reason; additive/identical -> proceed; keep apiVersion as a label), and fail closed when the signature is unavailable/unparseable; surface the specific incompatibility in the honest-status card. BEHAVIOUR CHANGE: a bugfix release (no wire change) now syncs across a client/server version skew instead of being refused by exact-match; a breaking change is refused with a specific, actionable reason instead of an opaque 'v1 vs v2'; a server too old to expose the signature is treated as incompatible (fail closed). ROLLOUT WRINKLE: the first server carrying the /schema endpoint + schemaHash must ship before/with clients that expect it — until a server exposes schemaHash the client fails closed. This is a SHARED SERVER-SHAPE change: it ships as BOTH a plugin release AND a server-image publish (the self-hoster must redeploy the server image), and the full server+client test suites run (not just the plugin build). No engine schema/workflow/process/skill change => no #ProspectiveChange, no CLAUDE.md change.";
    }

    verification d0042Accept : Test {
        :>> id = "bde295aa-be93-488f-902c-4915effe2248";
        :>> method = VerificationMethod::confirmation;
        :>> procedureText = "The AI researched the client<->server compatibility landscape at the owner's request (semver, contract-first breaking-change linters, single-source-of-truth generation from Rust types, and interface fingerprinting/hashing), establishing that a hash detects change but not breaking-ness and that the useful primitive is a STRUCTURED signature derived from the serde types. The owner selected placement (both CI + runtime) and wire strategy (hash-in-poll + lazy full fetch) via two decision prompts, then replied 'yes proceed and I agree' (2026-08-11) to the consolidated design (schemars-derived canonical signature; directional field-by-field diff as the accept/reject authority with bugfixes proceeding and breaking changes refused with a specific reason; fail-closed on unavailable signature; CI drift gate) — an explicit acceptance authorizing this decision and the Need/use-case/SR foundation it records.";
    }
    part d0042AcceptR1 : TestResult {
        :>> id = "7e0ac919-4d96-4409-80b9-8af218b94f94";
        :>> outcome = VerdictKind::pass;
        :>> judgedAgainst = "48ccc06";
        :>> judgedAt = "2026-08-11";
        :>> judgedBy = "wweatherholtz";
    }
}
