// =====================================================================
// D0018 — adopt PER-VAULT SQLite (WAL) as the server index, behind a narrow swappable IndexStore
// seam. Replaces the hand-rolled full-JSON-snapshot + append-only-journal index. This is a
// DELIVERABLE architecture change (the SelfSync server's persistence), not an engine-schema change.
// Resolves the Round-7 resource/scale findings that are storage-format-dependent (RS-2/5/6/7) and
// hardens against index corruption. Accepted 2026-07-07 by wweatherholtz. Migration is gated +
// sequenced (tracked: sqliteMigration).
// =====================================================================
package ProjectDecision0018 {
    private import EngineElement::*;
    private import EngineWork::*;
    private import EngineVerification::*;

    part d0018 : Decision {
        :>> id = "c0f1a5cc-f110-4a10-9b20-a1b2c3d40f20";
        :>> title = "D0018: per-vault SQLite (WAL) index behind a swappable IndexStore seam";
        :>> createdAt = "2026-07-07";
        :>> createdBy = "wweatherholtz";
        :>> status = DecisionStatus::accepted;
        :>> context = "The server has no database: per-(user,vault) it keeps an in-RAM Index {version, files, deletions, chunk_refs} persisted as a hand-rolled full-JSON snapshot (.sync-index.json) + an append-only journal (.sync-index.log), beside a content-addressed chunk store + a bind-mount mirror. The Round-7 resource/scale critique found this doesn't scale: every write deep-clones the whole index (RS-2), changes(since) is an O(files+tombstones) linear scan run every 4s per device (RS-5), compaction re-serializes the whole index every 500 mutations (RS-6), and cold-open deserializes + replays + walks the whole blob store (RS-7). Separately, the JSON has no page checksums and no schema migration, so bit-rot / a struct change / a bad restore -> whole-vault ERROR, and the recovery path itself can drop tombstones -> resurrection (RC-1). The owner asked whether a Postgres preference was wrong, wanting a modular backend, and observed the DB is 'the source of sync, but not the source of truth'.";
        :>> decision = "Adopt SQLite in WAL mode, ONE small database file PER (user,vault) sitting in that vault's dir beside .chunks/, as the server index. Put persistence behind a narrow IndexStore seam (a small module/trait: load, apply-put, apply-del, file_meta, changes(since), version, verify/gc, snapshot/migrate — the operations the vault needs) so the engine is swappable in principle. Implement ONLY SQLite behind it now. A one-time migration reads any existing .sync-index.json + journal on first open and populates the SQLite DB (never fabricating data); the chunk store + bind-mount mirror are unchanged. The content stays content-addressed + replicated (the source of truth); the DB is coordination state (source of sync).";
        :>> rationale = "The owner's Postgres preference is the correct DEFAULT for most server apps but is overridden by THIS product's constraints. SelfSync exists to escape LiveSync's #1 complaint — CouchDB setup/hosting friction — so requiring a networked DB reintroduces exactly that (a second service to run/secure/version/pool/monitor/back up, a second failure domain, a second app<->DB version-skew axis) against the single-binary Docker thesis (D0054 friction-is-the-#1-risk). Postgres's real wins (high concurrent-write throughput, one shared store at large multi-tenant scale, ops ecosystem) are for a deployment shape SelfSync does not target; its write pattern is per-vault, low-contention, modest. The owner's 'sync-not-truth' insight is decisive: the NOTES survive a total index loss (reindex rebuilds from chunks/mirror), so the DB's durability stakes are low -> prefer the simplest, most operable engine. SQLite is a single file: backup = copy the volume (as today), restore = drop it back — the owner's own maintainability point, correct. WAL + per-page checksums + ACID make corruption a near-non-event (the owner's worry, handled) and turn 'reindex from scratch' into a rare fallback. Per-vault (not one shared DB) preserves the existing isolation + directory + backup model and avoids single-DB contention. The narrow seam honors the modular-backend instinct WITHOUT building a second untested backend (YAGNI): a trait spanning embedded-single-writer SQLite AND networked-pooled Postgres is either leaky or a lowest-common-denominator that underuses both, so building the Postgres impl before a Postgres USER exists is speculative generality that would carry test burden + constrain the SQLite path. ALTERNATIVES CONSIDERED: (a) Postgres as default/required engine — DECLINED (operational friction vs the single-binary thesis; wins are for a non-target shape; a networked second failure domain for coordination metadata that reconstructs from content). (b) In-place hardening of the hand-rolled JSON index (add page checksums + a version index + incremental snapshot + LRU) — DECLINED (reinvents SQLite badly, 4+ bespoke mechanisms to build+test that SQLite gives for free). (c) No index / derive everything from the content store — REJECTED as impossible (version continuity, tombstones, and path->chunk maps are irreducible coordination state that exists nowhere else). (d) One server-wide SQLite DB instead of per-vault — DEFERRED/not chosen (per-vault preserves isolation + the beside-the-chunks backup story + avoids cross-vault write contention; a single shared DB is the shape one would revisit only under Postgres). DEFERRED DECISIONS: a Postgres backend implementation is DEFERRED behind the IndexStore seam until a real large-multi-tenant deployment needs it — the seam makes that a bounded future task, not a rewrite; and formalizing the seam as a fully generic trait vs a single well-bounded module is left to implementation (lean minimal). CRITERIA: operable (single file, volume-copy backup) x corruption-resistant (WAL+checksums+ACID) x scale-agnostic for the target (indexed queries + row writes) x single-binary preserved (embedded, no service) x modular (swappable seam) x proportionate (no speculative Postgres impl).";
        :>> consequences = "A gated, sequenced migration (tracked: sqliteMigration, open): (1) add an embedded SQLite dependency (rusqlite, bundled) + the IndexStore module/trait; (2) design the schema (files, deletions, chunk_refs, version, + a history/horizon table for RC-1/historyRebase) with the right indexes (version) and WAL; (3) port Vault persistence onto IndexStore (commit/delete become row writes — no whole-index clone; changes(since) becomes an indexed query; no full snapshot; bounded cold-open); (4) a one-time forward migration from .sync-index.json + journal on first open (read old format -> populate DB, honest — never fabricated), leaving the chunk store + mirror untouched; (5) tests (unit + the sync/e2e suites green on the new store). Resolves RS-2/5/6/7 (re-pointed to sqliteMigration) and materially reduces the corruption blast radius; enables the historyRebase horizon as a table. RS-1 (handle eviction), RS-3 (incremental reconcile), RS-4 (base-text cap) are storage-INDEPENDENT and proceed separately under scaleHardening (RS-3 first, ahead of the migration, for the mobile win). doc-sync when it lands: update the backend description in CLAUDE.md + .engine docs (the index is now SQLite, not JSON+journal). Order of work: storage-independent RS-1/3/4 first, then the SQLite migration.";
    }

    verification d0018Accept : Test {
        :>> id = "c0f1a5cc-f111-4a10-9b20-a1b2c3d40f21";
        :>> method = VerificationMethod::confirmation;
        :>> procedureText = "wweatherholtz, weighing a Postgres preference vs a modular backend and observing 'the db is the source of sync, but not the source of truth', accepted (2026-07-07): 'let's proceed with the per-vault sqlite approach as indicated' + 'note alternatives, as well as declined or deferred decisions' — accepting per-vault SQLite (WAL) behind a swappable IndexStore seam, Postgres declined-as-default + deferred behind the seam, in-place JSON hardening declined, one-server-wide-DB deferred.";
    }
    part d0018AcceptR1 : TestResult { :>> id = "c0f1a5cc-f112-4a10-9b20-a1b2c3d40f22"; :>> outcome = VerdictKind::pass; :>> judgedAgainst = "0c23566"; :>> judgedAt = "2026-07-07"; :>> judgedBy = "wweatherholtz"; }
}
