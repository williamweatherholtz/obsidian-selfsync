// D0102 (PROPOSED — NOT YET ACCEPTED) — E2EE clause 4 of 6 - a per-vault keyring sidecar, created atomically with the vault
// Recorded via `keel record decision` (engine D0105 RMWX axis; issue054). Acceptance is a separate explicit
// human gate (method=confirmation, engine D0106): flip status + add the d0102Accept event on sign-off.
package Decision0102 {
    private import EngineElement::*;
    private import EngineWork::*;
    private import EngineVerification::*;
    private import EngineRelationships::*;

    part d0102 : Decision {
        :>> id = "589da583-12d1-4cd1-96d9-51271460a818";
        :>> title = "E2EE clause 4 of 6 - a per-vault keyring sidecar, created atomically with the vault";
        :>> createdAt = "2026-11-10";
        :>> createdBy = "ai";
        :>> status = DecisionStatus::proposed;
        :>> context = "Clause 4 of 6 of D0097. POST /api/vaults returns a bare status with no id (server/src/vaults.rs:15-41). The index meta table is integer-valued only (server/src/index_store.rs:47). The round-1 draft created the vault and then PUT a keyring, and a panelist showed the gap accepts plaintext.";
        :>> decision = "A per-vault sidecar .keyring.json holds version, vault_id, the KDF parameters and salt, the check value and the wrapped VK. The server stores the client's bytes verbatim, and the audit entry for creation carries the creator and the encrypted flag. POST /api/vaults takes an optional keyring field and writes the vault and its keyring in one call, under the per-key open lock, with create_new on the sidecar. A racing second create gets 409. CURRENT_SCHEMA bumps to 4 for every vault, the v2 and v3 convention, so a rolled-back pre-E2EE binary refuses any vault the E2EE server opened with the existing 503 and never serves frames to an old client. A new AppState::create_vault takes the per-key open lock, inserts the tombstone for the name, creates the user directory and the vault directory where AlreadyExists is the 409 and the 409 arm removes the tombstone it inserted, writes and fsyncs the sidecar with create_new, and only then clears the tombstone, opens the vault and publishes the handle, all in one hold. It inlines the open and the cache insert, because the mutex is not re-entrant. So no request reaches a cached handle before the sidecar exists, and a sidecar failure removes the directory under the lock and leaves the tombstone set, so a parked open on a never-purged name gets NotFound. The index meta table gains encrypted=1. The flag derives from the sidecar whenever an index with zero files and deletions rows opens or rebuilds with a sidecar present, in Vault::open and in reindex alike, before any row is stored, and there is no other flag write. A fresh index is one whose DB file was absent or just quarantined before open, or that has zero files and deletions rows. So the reindex an operator runs on a warm handle after restoring the sidecar produces a flagged handle, never a plaintext one with frame rows. The server's encrypted test reads the flag, never the sidecar. Vault::open refuses with a distinct path-free 503 when encrypted=1 and no .keyring.json exists, naming the sidecar to restore, delete-from-plugin for a vault that never synced, and /admin as the operator route. It refuses with a second body when .keyring.json exists on a non-fresh index without the flag. It reads the magic of every mirror file first. All SSE1 means the index is stale and the body says move it aside and what that costs. None means the keyring is stale and the body says move it aside. Mixed gives a third body with both counts that chooses no remedy, and the first 20 paths go to the server log so the body stays under the client cap (amended at E2). No mirror file gives a body naming both remedies, and a failed file walk gives a body naming no remedy. The client shows every 503 body verbatim through the existing status path. A rebuild with no sidecar and a frame-stream file whose chunks are not in the store aborts with a named reason and stays ERROR (D0103). isNonGatingEndpoint and TYPE_ROLES are extended with the two GET keyring routes and the keyring type, so a new plugin keeps syncing a plaintext vault on an old server. GET keyring exists on the own-vault route and the owner-qualified route and needs a Read grant. It answers 200 with the sidecar bytes, 404 when the vault is absent or the handle is plaintext with no sidecar, and the refusal-one 503 when the handle is encrypted and the sidecar is gone. The handler reads the sidecar and the in-memory handle field only, never ensure_ready, so a corrupt vault still answers and both cache states converge on one body. A cold cache gets the handle through Vault::open first. The Vault keeps a named abort reason after a failed rebuild, cleared on the next successful rebuild, and a handle that holds the no-sidecar reason answers the same 503. vault_open_error gains a mapping that routes both refusals to 503 with their own bodies. The client decides on 200 alone, and a 404 falls through to status, which tells plaintext from deleted and from an old server. So a pinned device never deletes a vault on a 404. There is no PUT keyring and no DELETE keyring in v1. The keyring dies with the vault. After creation the client reads GET keyring and pins only when the returned vault_id is the one it sent. On 404, which means an old server, it deletes the vault, discards the generated VK and names the minimum server version. The vault_id is distinct from the salt because a later re-wrap may rotate the salt. The audit entry for creation carries the encrypted flag. A lost keyring has no in-place recovery. The Blocked card names the reason and points at delete-then-create, the delete action and the create dialog of D0109. The delete action carries the warning that every share grant and share link is purged, so the owner re-shares afterwards, and the card points at it. Backups must include the dotfiles .keyring.json, .sync-index.db, .version-hwm and .chunks, and docs/deployment.md says so.";
        :>> rationale = "Atomic creation leaves no window in which an encrypted vault accepts plaintext. A sidecar fits the existing .version-hwm pattern (server/src/vault.rs:279-292). The owner-qualified route is what every shared-vault call uses, so a collaborator can join. The post-creation read fails closed on a server that ignored the field. ALTERNATIVES: (i) create then PUT keyring - rejected, the gap accepts plaintext and a crash leaves a plaintext vault. (ii) a keyring field on status - rejected, an old client would ignore it and an old server would not refuse. (iii) a per-vault schema target - rejected, it makes schema_version mean table shape or encrypted, and the v2 and v3 bumps already refuse rollback for every vault. (iv) a re-enrol arm that purges and re-creates - rejected, it duplicates the delete action and the create dialog and launches a purge from a Blocked card.";
        :>> consequences = "CreateVaultRequest gains an optional keyring field, additive on the wire. Two new GET routes. The plugin gains an owner-scoped 'Delete this vault on the server' action, which the migration of D0109 uses. Password change and rotation need a later re-wrap route and are tracked follow-ups.";
    }
    #DerivedFrom dependency from d0102 to us013;
    #DependsOn dependency from d0102 to d0099;
}
