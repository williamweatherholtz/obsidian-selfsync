// =====================================================================
// D0039 — COMPOSED (nested) VAULTS architecture: data-only, directional "Mounts". Owner-directed
// 2026-08-07 ("proceed with the composition/nesting architecture, FSM modeling, and planning" →
// "accept and proceed"). Realizes nComposedVaults. Full design: docs/design/specs/
// 2026-08-07-composed-vaults-spike.md. Deliverable-domain PRODUCT architecture (no engine schema/
// process change), so NOT a #ProspectiveChange — the SAME class as D0037/D0038.
// =====================================================================
package ProjectDecision0039 {
    private import EngineElement::*;
    private import EngineWork::*;
    private import EngineVerification::*;
    private import EngineRelationships::*;

    part d0039 : Decision {
        :>> id = "8c1d2e3f-4a5b-4c6d-9e7f-0a1b2c3d4e5f";
        :>> title = "D0039: composed vaults via data-only directional Mounts (multi-scope reconcile), bidirectional-in-v1";
        :>> createdAt = "2026-08-07";
        :>> createdBy = "wweatherholtz";
        :>> status = DecisionStatus::accepted;
        :>> context = "The owner has long wanted to COMPOSE vaults — a shared PART of one vault appearing inside another, directionally (their personal vault pulls in their ASI notes; the ASI vault does not pull in personal), so the data lives side by side and search/links/Dataview work across it. No Obsidian plugin does this cleanly today (vaults are isolated; symlinks/submodules are fragile). SelfSync is uniquely positioned because it already maps a whole local vault <-> a server vault, so 'a subfolder <-> a shared server vault' is a natural extension of the existing reconcile engine. The owner's key scoping insight: composition must be DATA-ONLY (notes/attachments), never config/plugins — because when two vaults compose, WHICH vault owns a plugin's settings is indeterminate, so config is deliberately out of scope. Across a design discussion the owner resolved the pivotal forks: direction is PER-MOUNT (pull|sync, default pull); granularity is MODULAR sub-folder mapping (a subfolder of the source <-> a local subfolder; compose several); and bidirectional editing is v1 TABLE-STAKES (not a read-only-only first ship). This Decision records acceptance of the architecture proposed in the spike spec, authorizing implementation.";
        :>> decision = "Adopt the MOUNTS model. A Mount = { source:{owner, vaultId, sourcePath}, mountPoint, direction } binds a SUBFOLDER of a source server-vault S to a LOCAL subfolder of the primary vault, syncing DATA ONLY, in a per-mount direction (pull = S->local read-only; sync = bidirectional). Composition is modular — a vault carries several mounts. Realized as a MULTI-SCOPE reconcile: the client runs the primary scope (whole local vault MINUS every mount point <-> primary server vault, config opt-in as today) PLUS one scope per mount, each REUSING the existing engine (reconcile, base store, conflict machinery, connection FSM) with three additions: (1) a two-sided prefix-translating IO adapter (MountedIo) mapping S:/<sourcePath>/** <-> local <mountPoint>/**; (2) a data-only accepts() filter (reject .obsidian/** both directions); (3) the direction (pull reuses the read-only-vault path; sync is the normal scoped reconcile). The load-bearing invariant is the BOUNDARY: the primary scope excludes every mount point so a mounted file never double-syncs to the primary vault. Each mount has its own persisted base store, cursor, and subscription; same server + token (cross-server is out of scope). Each mount is an independent lifecycle FSM (Detached/Mounting/Live/Syncing/Diverged/Offline/Unmounting/Failed); the one status light is a fold over the primary + all mounts. Build order: read-only mount FIRST (safest slice, never mutates S) to validate the engine, then bidirectional before the v1 release (Phases 1-3), then UI, then edges — each phase with its own independent security critique (composition moves data across vault boundaries and can delete). Defaults for the two minor open questions: a non-empty mount point MERGES (first-contact reconcile); unmount KEEPS the files as plain-local by default (with an explicit remove option) — never a silent delete.";
        :>> rationale = "REUSING the existing reconcile engine (scoped + two-sided-prefixed + config-stripped) is what makes a feature this ambitious tractable: no new sync core, no new conflict model, no new durability story — the mount is 'sync a vault into a subfolder instead of as the whole vault, data-only', so it inherits the tested chunk store, base/three-way-merge, delete-rate guard, and connection FSM. DATA-ONLY is not a limitation to lift later but the design's keystone — it removes the intractable 'whose config wins' problem, so composition stays well-defined. DIRECTIONAL + per-mount is the safety + flexibility the owner asked for: pull-only can never mutate the source (Personal pulling ASI is risk-free), while sync is available where wanted. READ-ONLY-FIRST build order means the engine is proven against a source that is never written before any push path exists. The BOUNDARY exclusion is the one place a bug would corrupt/duplicate data, so it is called out as the load-bearing invariant to guard + test hardest. ALTERNATIVES: (i) OS symlinks / git submodules — REJECTED: fragile, Obsidian mis-handles symlinks, no conflict handling, not cross-device. (ii) A single merged super-vault — REJECTED: loses directionality + the modular per-piece control + would entangle config. (iii) Cross-server mounts in v1 — DEFERRED: adds multi-token auth for no near-term need. (iv) Read-only-only v1 — REJECTED by the owner (bidirectional is table-stakes). (v) Config composition — permanently OUT (indeterminate ownership). CRITERIA: reuse-the-engine x data-only-well-defined x directional-safety x boundary-provable x per-phase-critique.";
        :>> consequences = "AUTHORIZES the composed-vaults epic (a multi-phase, multi-release build — the largest feature on the roadmap): the mount data model + boundary/overlap guards + two-sided MountedIo (Phase 1), the pull mount engine + per-mount FSM + aggregate status (Phase 2), bidirectional sync + scoped conflict/delete (Phase 3, v1 ships here), mount-management UI (Phase 4), and edges — offline/backoff, access-revoked/S-deleted->Failed, unmount cleanup, whole-share->mount migration (Phase 5). Each phase is a sprint with its own independent security critique. NEW per-device settings.mounts (not synced — composition is a local choice, like the primary target) + per-mount base stores. OUT OF SCOPE (v1): config/plugin composition (permanent), nested/overlapping mounts, cross-server mounts, and per-user personal config scope (the separate nPerUserConfigScope spike). No engine schema/workflow/process/skill change (deliverable-domain) => no #ProspectiveChange, no CLAUDE.md change; the spike spec (docs/design/specs/2026-08-07-composed-vaults-spike.md) is the living design record.";
    }

    verification d0039Accept : Test {
        :>> id = "9d2e3f40-5b6c-4d7e-af80-1b2c3d4e5f60";
        :>> method = VerificationMethod::confirmation;
        :>> procedureText = "wweatherholtz directed 'proceed with the composition/nesting architecture, FSM modeling, and planning' (2026-08-07); after the AI produced the spike spec (Mounts model, multi-scope reconcile, per-mount FSM, phased plan) and surfaced the pivotal forks, the owner resolved them (per-mount direction; modular sub-folder mapping; bidirectional-in-v1) and directed 'accept and proceed'. This Decision records that explicit acceptance of the architecture, authorizing the phased implementation.";
    }
    part d0039AcceptR1 : TestResult {
        :>> id = "a0e3f405-6c7d-4e8f-b091-2c3d4e5f6071";
        :>> outcome = VerdictKind::pass;
        :>> judgedAgainst = "9e5545d";
        :>> judgedAt = "2026-08-07";
        :>> judgedBy = "wweatherholtz";
    }
}
