// D0103 (PROPOSED — NOT YET ACCEPTED) — E2EE server - frame checks, 403 guard, mirror trailer, reindex
// Recorded via `keel record decision` (engine D0105 RMWX axis; issue054). Acceptance is a separate explicit
// human gate (method=confirmation, engine D0106): flip status + add the d0103Accept event on sign-off.
package Decision0103 {
    private import EngineElement::*;
    private import EngineWork::*;
    private import EngineVerification::*;
    private import EngineRelationships::*;

    part d0103 : Decision {
        :>> id = "bb1360bf-cff9-4d28-8815-5d3c1af70c07";
        :>> title = "E2EE server - frame checks, 403 guard, mirror trailer, reindex";
        :>> createdAt = "2026-11-10";
        :>> createdBy = "ai";
        :>> status = DecisionStatus::proposed;
        :>> context = "Clause 5 of 6 of D0097. The server writes a plaintext mirror and rebuilds a corrupt index from it (server/src/vault.rs:104-123, 464-482). The commit guard aborts when the reassembled bytes exceed req.size (vault.rs:606-617). An old client maps an unknown 4xx to a slow retry and a 403 to a blocked link (client/src/connstate.ts:90-124).";
        :>> decision = "For a vault whose handle is flagged encrypted (D0102): PUT chunk also needs a well-formed frame, else 422. The commit guard accumulates plaintext length from the frame headers. The commit handler refuses an empty chunk list, keeps the raw byte bound of body length against size plus 68 per listed chunk, and adds the plaintext sum. Final checks: the plaintext sum equals size, sha256 of the body equals hash, cid is present. The mirror holds the frame stream followed by a trailer SSEM plus cid. One function write_mirror_for appends the trailer at all three write sites: commit, the self-heal and reindex re-materialisation. Every rebuild-from-disk (the corrupt-index rebuild, the missing-chunk fallthrough and an unindexed disk file) splits a mirrored file by frame headers and takes cid from the trailer. The rebuilt row equals the committed row. An indexed file whose mirror does not parse stays lost, which aborts reindex unless force. An unindexed file that does not parse is foreign: warn and skip, never abort, never moved. force keeps its one meaning, drop lost rows. A rebuild-from-disk runs a three-condition scan as a pre-pass before any store write, and aborts the reindex with a named reason when the conditions hold: no sidecar, a file that parses as a complete frame stream with every ct_len in 48 to 65584 and the trailer at the end, and not every CDC chunk hash of that file already in the store. The reason lists the first 20 paths with a count and the exit: restore .keyring.json, or move the files out of vault/ and reindex. The vault stays ERROR, and force does not override it, so a dotfile-skipping restore never serves frames as content, and a plaintext vault with a frame-shaped committed file still reindexes. The named abort reason clears on the next rebuild that succeeds, and a zero-row rebuild with the sidecar back derives the flag before it stores a row (D0102). A fresh or quarantined rebuild with a sidecar aborts on a file that does not parse as a frame stream, with its paths, because write_mirror_for wrote every mirror file. foreign stays the class for a healthy reindex. The self-heal compares the mirror length with the body length plus 36. A FromRequestParts extractor E2eeHeader reads x-selfsync-e2ee, and every sync handler passes it into scoped(). scoped() checks it after authorized() and vault_exists(), so a non-grantee still gets the bare 403 and the audit line. A grantee without the header on a keyring vault gets HTTP 403, and the body names the cause. GET keyring is the only exemption inside scoped(). The WebSocket, DELETE /api/vault, admin and share-link routes never pass through scoped().";
        :>> rationale = "Frame validation on PUT stops a buggy or old client from writing plaintext into an encrypted vault. The trailer lets a keyless reindex rebuild a row. Every client accepts that row. Three panelists found that missing. A check inside scoped() runs after authorization, so it leaks neither existence nor encryption to a non-grantee and skips no audit line. A layer before authorization would do both. A route-list test keeps a new handler honest. 403 blocks an old client. Its card shows the fixed text 'Access to this vault was removed', and the body reaches only the plugin log, which the docs state. 428 would retry forever. ALTERNATIVES: (i) 428 - rejected, the old client classifies it as degraded and retries. (ii) a router layer before authorization - rejected, it leaks vault existence and skips the audit. (iii) a route list alone - rejected, the next route inherits nothing. (iv) disable the mirror for encrypted vaults - rejected, it drops reindex-from-disk.";
        :>> consequences = "The host-filesystem edit feature of the mirror is unavailable for an encrypted vault, and docs/deployment.md says so. A test iterates the signed route list and asserts that every handler threads the extractor or is on the exemption list, and that the 403 body does not match the client's password-change regex. The wire signature is regenerated, additive only.";
    }
    #DerivedFrom dependency from d0103 to us013;
    #DependsOn dependency from d0103 to d0101;
    #DependsOn dependency from d0103 to d0102;
}
