// =====================================================================
// D0026 — Test coverage and pass-state are COMPUTED facts, not authored attestations. Coverage is
// measured by the tools (vitest v8 / cargo llvm-cov), gated by a hard ratcheting FLOOR (a constraint),
// trended as a computed Indicator, and the full "are all tests green + floors met" verdict is a
// REPRODUCIBLE gate (reverify.toml) that CI and `keel reverify` recompute at HEAD. Delivery DoDs stop
// carrying prose pass-claims the gate can recompute. Accepted 2026-07-14 by wweatherholtz.
// =====================================================================
package ProjectDecision0026 {
    private import EngineElement::*;
    private import EngineWork::*;
    private import EngineVerification::*;

    part d0026 : Decision {
        :>> id = "0d260a1c-7e34-4b55-9a11-2f3c4d5e6a26";
        :>> title = "D0026: coverage + test-pass are computed & gated (ratcheting floor + Indicator + reproducible gate), never prose-attested";
        :>> createdAt = "2026-07-14";
        :>> createdBy = "wweatherholtz";
        :>> status = DecisionStatus::accepted;
        :>> context = "The deliverable (SelfSync: Rust server + TS plugin) kept shipping MEDIUM+ defects that INDEPENDENT critique passes discovered — repeatedly, across multiple passes — which is the signature of a gate that does not actually verify what it claims. A three-front test audit (client / server / e2e) found the root cause is structural, not a shortage of tests: (1) NO coverage is measured anywhere — client vitest had no coverage provider, server had no llvm-cov/tarpaulin — so gaps were invisible and every gap was found by a human, not a metric; (2) the strongest suites did not gate — client CI ran unit tests but never built the server binary, so the real-server integration specs (`describe.skipIf(!canRun)`) SILENTLY SKIPPED in CI; (3) tests are a reactive regression graveyard added per-past-finding at the pure/unit level, while the imperative edges and concurrent-orchestration layers where MEDIUM+ bugs originate (client transport.ts / the 4 untested UI modules / real modal action bodies spied away; server api.rs [0 tests] / ws.rs [no WebSocket test at all] / concurrent-commit CAS race / DoS bounds) were untested; (4) some tests gave FALSE confidence (a promise-swallowing https test whose assertion may never run; a sharing test asserting only `!= 403`; modal tests asserting calls to vi.fn() stubs). Separately, the user identified an authoring drift: delivery DoD `procedureText` fields carried PROSE pass-claims like 'CLIENT GREEN (vitest 335 passed)'. That is an attestation of a COMPUTABLE fact — the §2.1 anti-pattern (author irreducible facts + recorded judgments; everything derivable is a view). The user's directive: 'I want calculated coverage, not attested coverage. Record facts, calculate viewpoints of the facts. \"Are we passing all tests\" should have a record at a point in time — an immutable fact like a Need/Decision — but computed, not prose.'";
        :>> decision = "Test coverage and test-pass state are COMPUTED and GATED, never authored as prose. Concretely: (A) COVERAGE IS MEASURED — client via `@vitest/coverage-v8` (`vitest run --coverage`), server via `cargo llvm-cov`; both emit machine-readable summaries. (B) THE FLOOR IS A CONSTRAINT (D0088), distinct from the measured value: a HARD RATCHETING minimum (per the user's choice of the strictest option) enforced in CI — a run below any floor FAILS. The floor VALUE is authored (it is an irreducible threshold decision); the coverage VALUE is computed and never stored. Floors ratchet only UPWARD: raise once the measured number clears a higher bar; never lower a floor to make a red run pass. (C) COVERAGE-OVER-TIME IS A COMPUTED INDICATOR (D0089/D0090, method=computed, repo-derived) — client and server line-coverage as monitored measures viewed via `keel indicators`, informing by direction, no stored datapoints. (D) THE FULL GATE IS REPRODUCIBLE — `.engine/contracts/reverify.toml` is extended from server-tests-only to the WHOLE deliverable gate (server `cargo test` + clippy, client `vitest run --coverage` with floors, and — where a built binary is present — the integration specs), so `keel reverify` and CI recompute 'all green + floors met' at HEAD; the point-in-time `TestResult` (who/when/at-commit) remains the immutable observation, but stops carrying prose the gate can recompute. (E) STALENESS IS COMPUTED — `.engine/deliverable-manifest.txt` maps verification tasks to their deliverable-source files so `keel suspect` flags a verification suspect when its source drifts (previously empty → nothing was ever flagged). (F) CI ACTUALLY RUNS THE GATE — the client job builds the server binary FIRST so the integration specs RUN instead of skipping, and the harness treats a missing binary as a HARD FAILURE under CI (env `SELFSYNC_REQUIRE_E2E=1`) rather than a silent skip. (G) A `test-authoring` SKILL (D0059) encodes the standard so it recurs: every fix ships a FAIL-FIRST regression test; test the real code path, not a mock of it; cover negative/failure/property/edge cases (empty, binary, EOL, connection error, read-only, concurrent/delta, deletion, CAS/version, oversized/DoS, expired/revoked/replayed); no promise-swallowing or `!= 403`-style tautologies; no asserting on stubs that replace the code under test.";
        :>> rationale = "This is a D0047 correction: a recurring process gap (critiques repeatedly finding MEDIUM+ defects) MUST become a permanent automated guard, not manual vigilance. The engine's own invariant (§2.1: text is truth, everything derivable is a view; §2.6: constraint vs indicator) dictates the SHAPE: coverage is derivable from source + tests + git, so it must be COMPUTED, and the enforced floor is exactly the 'constraint = CI-enforced predicate' layer. A ratcheting floor (the user's explicit choice over advisory-first or critical-only) is what converts 'we should test more' — which failed — into a mechanical block that cannot silently erode. Making the reverify gate the WHOLE deliverable gate (not server-only) means the recorded pass-state is honest-by-recomputation, which is precisely the user's 'calculated, not attested' requirement; it also removes the incentive to write prose DoDs. Fixing the silent-skip is the highest-leverage single change: the suites most able to catch sync defects were present but non-gating, so the codebase got the reassurance of a green CI without the verification. The skill exists because a standard applied by vigilance is applied inconsistently — the same failure mode we are correcting.";
        :>> consequences = "Client: `@vitest/coverage-v8` dev-dep + a `coverage` block with thresholds in vitest.config.ts (the stale 'CI doesn't run tests' comment removed); `npm run test:cov` script. Server: `cargo llvm-cov` in CI (taiki-e/install-action) with `--fail-under-lines`; documented for local use. CI (.github/workflows/ci.yml): the client-tests job builds the server binary before `npm test` so integration specs run; a coverage floor gate is added on both sides; the e2e harness throws instead of skipping when `SELFSYNC_REQUIRE_E2E=1`. `.engine/contracts/reverify.toml` extended to the full gate. `.engine/deliverable-manifest.txt` populated (verification-task → source map). New computed coverage Indicators in .tracking. New `test-authoring` skill under .engine/skills/ + its process. Going forward, delivery DoD `procedureText` names the reproducible gate rather than quoting counts; existing prose DoDs are legacy (not retro-rewritten — this decision supersedes the PRACTICE, and reverify recomputes their truth on drift). Phase 3 (real-Obsidian Playwright+CDP e2e) is explicitly DEFERRED per the user; this decision covers Phases 0–2 (the gate + client-edge + server-concurrency hardening). No schema/core change — the Indicator/constraint/view machinery already exists; this instantiates it for the deliverable's tests.";
    }

    verification d0026Accept : Test {
        :>> id = "0d26acc7-2b33-4c44-9d55-6e7f80912326";
        :>> method = VerificationMethod::confirmation;
        :>> procedureText = "wweatherholtz directed the comprehensive-testing work ('more comprehensive tests … string [strong] unit tests, integration tests, and more e2e (playwright?) … the fact that each critique pass almost always discovers MEDIUM+ issues … indicates our architecture is not being strict … come up with a plan and implement'), chose the HARD RATCHETING FLOOR gate option, chose DEFER Phase 3 / do Phases 0–2, and gave the defining constraint on HOW test state is recorded: 'I DON'T want prose saying our coverage is good, I want computable tests … I don't want artifact attestation that indicates passing tests. Record facts, calculate viewpoints of the facts. And \"are we passing all tests\" should only have a record at a point in time, but it's an immutable fact like a need, decision, etc. is … I want calculated coverage … agreed with the CI rigor.'";
    }
    part d0026AcceptR1 : TestResult { :>> id = "0d26ac00-ab22-4c33-9d44-5e6f70819326"; :>> outcome = VerdictKind::pass; :>> judgedAgainst = "901368e"; :>> judgedAt = "2026-07-14"; :>> judgedBy = "wweatherholtz"; }
}
