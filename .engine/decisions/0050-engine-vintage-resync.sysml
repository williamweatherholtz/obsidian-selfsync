// =====================================================================
// D0050 (PROJECT numbering) — resync .engine/ onto the keel 0.3.1 engine vintage WHOLESALE, under a
// committed transform that re-applies this project's own additions BY NAME, and retire D0048's deferral.
// PROPOSED, not yet accepted: a 549-file process/schema-definition change is §3a/§4 territory and the
// D0070 process-change keystone demands a #ProspectiveChange Decision with a HUMAN signature. The AI
// performed the resync and authored this record; acceptance is the owner's, via `keel accept d0050`.
// =====================================================================
package ProjectDecision0050 {
    private import EngineElement::*;
    private import EngineWork::*;
    private import EngineVerification::*;
    private import EngineRelationships::*;

    #ProspectiveChange part d0050 : Decision {
        :>> id = "94df355a-cf92-4fb1-a0ee-70f3df044473";
        :>> title = "D0050: resync .engine/ onto the keel 0.3.1 vintage wholesale under a committed transform, re-applying this project's additions by name — supersedes D0048's deferral";
        :>> createdAt = "2026-09-07";
        :>> createdBy = "claudeOpus";
        :>> status = DecisionStatus::proposed;
        :>> context = "D0048 (same day) reconciled this project with the keel 0.3.1 binary ADDITIVELY and deferred `keel migrate` because a first attempt clobbered .engine/schema/core/relationships.sysml with the stock copy - 25 metadata def declarations cut to 18, the markers D0045 deliberately added deleted, marker-vocabulary 0 -> 228 violations - while the migrate dry-run had reported 0 blockers. That left issueEngineVintageGateDrift open with the resync as its remaining DoD clause, and the owner then directed 'continue through entire backlog. quality first'. The state of the tree: 260 engine files at a July-2026 vintage under a binary that ships 549, so every control, process, skill, contract and reference decision added between D0107 and D0294 was absent here - among them parser-coverage, evidence-cited, identity-well-formed, ownership, duplicate-identity, base-first-justification and the per-skill registry (D0222). This project's own engine content, which any resync must carry: six processes (architecture-audit, code-critique, functional-decoupling, mutation-testing, property-based-testing, release-versioning), eight skills registered for them, the eleven D0045 markers, schema/codeaudit/codeelement.sysml, contracts/reverify.toml and deliverable-manifest.txt. The resync was rehearsed against a scratch `keel init` tree so the stock shape of every file was known before the live run.";
        :>> decision = "SPLIT 2026-09-13 under D0303 option C (keel 0.4.1 decision-scaffolding): this compound Decision is superseded by one Decision per clause - d0066 through d0073 (8 clauses, #DependsOn-chained, d0066 #Supersede-s this one) - and each clause's text lives there VERBATIM and unchanged. This field is now the pointer; the original compound wording is in git history at 0ae356f8 (the text any earlier acceptance was bound to). The rationale and consequences below are unchanged.";
        :>> rationale = "The gate that actually runs on every commit - the pre-commit hook, CI, the owner's terminal - is keel 0.3.1, and a binary reading an engine tree six weeks older than itself enforces an unknown mixture: guards whose contracts and schema types are missing pass vacuously or fail on shape rather than substance, which is exactly how issueEngineVintageGateDrift arose. D0048 bought a green gate cheaply and honestly said the resync was deferred, but a project that stays on a vintage its binary no longer ships has no path to any control added since, and the first thing the resync surfaced - a governance lens reading a false zero for the life of the record - shows what that costs. The clobber hazard D0048 rolled back from is real and is handled here by re-application BY NAME under an idempotent, control-totalled transform, not by avoiding the migration: what the stock files overwrite is known (the scratch init), what this project adds is enumerated, and the counts must balance before the commit. ALTERNATIVES: (i) stay additive per D0048 - REJECTED, it leaves the project unable to receive any control the binary adds and leaves the open DoD open indefinitely; (ii) pin an older keel that matches the July tree - REJECTED, the hook, CI and the owner all run 0.3.1, so pinning recreates the two-binary drift that caused the incident; (iii) migrate by hand without a committed transform - REJECTED, D0067 requires a committed transform with reconciled totals for a change of this size, and the ownership guard's only exemption for crossing engine-owned files is a co-committed transform under .engine/tools/migrations/; (iv) CHOSEN. WHY PROPOSED rather than self-accepted: this rewrites process and schema definitions (§3a, §4, §2.5) across 549 files, and the process-change keystone exists precisely so a change of that reach carries a human signature.";
        :>> consequences = "CONTROL TOTALS (pre -> post): engine files 260 -> 559 (the 557 the resync produced plus this decision record and the transform); AISkill registrations 35 -> 52 (27 stock per-skill + 8 project + the new stock skills), no id lost; metadata def declarations: the 11 D0045 markers re-added, `Changes` retired, 17 engine + 10 project = 27; viewpoints 20 -> 32; parser-coverage skipped 81 -> 7; #Covers AST edges 0 -> 74; project processes 6 -> 6 with 29 successions replacing 35 `order` attributes. GATES under keel 0.3.1 by exit code: validate 0, check-engine 0, guard ALL PASS; the 90 first-green warnings are read and actioned or accepted as listed in the decision. issueEngineVintageGateDrift's resolver (engineVintageResync) records this progress and PASSES only when this decision is accepted - owner acceptance is its first DoD clause. issueNestedCoversEdgesSkipped is recorded and resolved by coversEdgesHoisted; the sitting-coverage lens now counts covering reviews. Carried upstream to the keel toolkit: a nested dependency statement passes `keel check` clean while being skipped; `keel migrate --dry-run` reports 0 blockers for a change that deletes project schema additions. REMOVAL PATH: `git revert` of the resync commit restores the D0048 tree exactly (nothing in .tracking/, client/ or server/ depends on the new vintage except the hoisted #Covers block, which parses in both). Acceptance: `keel accept d0050 --by wweatherholtz --note ... --date ...` from the owner's own terminal - refused from an agent session by design.";
    }

    // D0048 chose the additive route and deferred the wholesale resync; this decision performs it.
    #Supersede dependency from d0050 to d0048;
}
