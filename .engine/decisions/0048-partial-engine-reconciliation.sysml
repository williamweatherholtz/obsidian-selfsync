// =====================================================================
// D0048 (PROJECT numbering) — reconcile this project with the keel binary that actually gates it by
// the NARROWEST additive route (add the CLI facts + their schema, correct the stale lens-command
// names), and RECORD why the wholesale `keel migrate` was attempted, rolled back, and deferred: it
// overwrites engine-shipped schema files with stock versions and discards this project's deliberate
// additions to them. Owner directed "run keel migrate first, then commit clean" (2026-09-07); the
// migrate itself proved unsafe, so the intent (a green gate) was met by a different route and the
// hazard is recorded here rather than re-discovered. Adds .engine/ schema, so §4 applies.
// =====================================================================
package ProjectDecision0048 {
    private import EngineElement::*;
    private import EngineWork::*;
    private import EngineVerification::*;
    private import EngineRelationships::*;

    #ProspectiveChange part d0048 : Decision {
        :>> id = "3aa944bf-a839-4a6c-9049-a0414983c049";
        :>> title = "D0048: reconcile with keel 0.3.1 additively (CLI facts + cli schema + lens-command doc-sync) instead of `keel migrate`, which clobbers project additions to engine-shipped schema";
        :>> createdAt = "2026-09-07";
        :>> createdBy = "wweatherholtz";
        :>> status = DecisionStatus::accepted;
        :>> context = "Installing the git hooks (issueHooksNotInstalled) made a real gate run here for the first time in ~6 weeks, and it immediately failed. Two causes had hidden the drift: no hook was active (a machine-global core.hooksPath pointed at a directory that does not exist, so git silently ran nothing), and CLAUDE.md section 5 documented the validator as a local Windows release-build path that does not exist in this repo — so a 6-week-old sibling checkout's keel had been run by hand instead of the keel 0.3.1 on PATH. Every recent 'keel guard ALL PASS' record was therefore that stale binary's verdict, and D0046 plus the provenanceDecoupling DoD now carry explicit GATE CORRECTIONs saying so. Under 0.3.1 the tree showed five failing guards: evidence-cited (2 — this sitting's own AI-judged method=test results lacked the `// RAN:` receipt the newer engine requires), viewpoint-renderer (9 — declared renderers named per-lens verbs that 0.3.1 no longer dispatches), tool-reference (1 — the engine-triage skill pointed at .engine/tools/triage_reminder.py, which does not exist and never did: CLAUDE.md itself says that hook is still sprint30), sprint-closure (1 — tracked as issueMootedTaskUnstamped, resolved separately), and cli-surface-declared (1 — .engine/cli/commands.sysml absent). The owner chose to run `keel migrate` and then commit clean. `keel migrate --dry-run` looked benign: 481 .engine/ files, 0 blockers, nothing outside .engine/. The real run was NOT benign. It refuses a dirty tree (correctly), so the sitting's work was stashed first; afterwards `keel validate` FAILED where it had passed, and two guards that had been GREEN went red — marker-vocabulary with 228 violations and attribute-vocabulary with 1216. Cause: migrate replaced .engine/schema/core/relationships.sysml with the binary's stock copy, dropping it from 25 `metadata def` declarations to 18 — deleting the 7 markers D0045 had deliberately added (the STPA edges such as #LeadsTo) to satisfy an earlier guard. The migration was rolled back (nothing had been committed, so `git checkout -- . && git clean -fd` restored HEAD exactly; D0045's 25 markers verified intact) and the stash restored.";
        :>> decision = "SPLIT 2026-09-13 under D0303 option C (keel 0.4.1 decision-scaffolding): this compound Decision is superseded by one Decision per clause - d0061 through d0065 (5 clauses, #DependsOn-chained, d0061 #Supersede-s this one) - and each clause's text lives there VERBATIM and unchanged. This field is now the pointer; the original compound wording is in git history at f8e83508 (the text any earlier acceptance was bound to). The rationale and consequences below are unchanged.";
        :>> rationale = "The additive route was chosen because it reaches the same place — validate, guard and check-engine all green under the binary that gates commits — while changing 5 engine files instead of 481, and without touching a single file this project has customized. That matters more than tidiness here: the wholesale migrate DEMONSTRATED that it silently reverts project decisions, so running it to satisfy a gate would trade one dishonest state (a stale gate) for a worse one (a green gate whose greenness came from deleting D0045). Rolling it back rather than patching forward was right for the same reason: 481 files of stock engine mixed with hand-re-applied customizations cannot be reviewed, and migrate's own refusal-on-dirty-tree exists precisely because a half-migrated tree is indistinguishable afterwards. Deferring the resync is honest incompleteness rather than debt hidden in prose: the tree is now truthfully green on the guards that run, and the vintage gap is a tracked Issue with a named DoD, which is what D0098's honest-state-not-self-assurance principle asks for. The `// RAN:` receipts were added rather than argued with, because the guard is right — an AI-judged pass with no re-derivable command is a testimony, not a test, and that is exactly the failure mode that let a stale binary's ALL PASS stand unexamined. Two things were deliberately NOT done: the migrate hazard was not worked around by force (no --no-verify, no editing the guard), and no `keel migrate` was re-run to cherry-pick files out of it — the scratch `keel init` gives the same content with no risk to this tree.";
        :>> consequences = "keel validate = 0, keel guard = 0 (63 checks pass, no failures), keel check-engine = 0 — all three verified by exit code, not by piped output (an earlier check in this sitting read `tail`'s exit status through a pipe and briefly mistook a masked result for a pass; the re-runs captured the real codes). Five .engine files change: two added (cli/commands.sysml, schema/cli/cli.sysml), three edited (views/viewpoint-registry.sysml, skills/engine-triage/SKILL.md, decisions/0040 typo). Adding engine schema makes this a process-definition change, so this Decision is the D0070 record. The pre-commit hook now genuinely gates every commit with the PATH binary, so the stale-validator class cannot recur silently. STILL OPEN and tracked: issueEngineVintageGateDrift (the 481-file resync plus re-applying D0045 and the attribute-vocabulary declarations) and 19 unread non-blocking warnings across viewpoint-renderer, manifest-coverage, verification-trace, parser-coverage, base-first-justification and control-event-coverage — non-blocking by design (D0098) but explicitly NOT read yet, which is itself part of that Issue's DoD. An upstream observation worth carrying to the toolkit: `keel migrate` should either merge project additions into shipped schema files or refuse and name them, rather than overwriting silently — its dry-run reported 0 blockers for a change that deleted a project decision's effect.";
    }

    verification d0048Accept : Test {
        :>> id = "14b42af3-a1ae-46e0-9c0d-05105152c0ad";
        :>> method = VerificationMethod::confirmation;
        :>> procedureText = "Presented with four pre-existing guard failures blocking every commit, the owner chose 'Run keel migrate first, then commit clean' over bypassing with SKIP_KEEL or holding (2026-09-07). The migrate was attempted as directed and rolled back when it regressed D0045's marker declarations (keel validate went from pass to fail; marker-vocabulary 0 -> 228 violations). The owner's stated INTENT — end with a clean, genuinely-green gate rather than a bypass — is what this decision delivers by the additive route; the deviation from the literal instruction is recorded here rather than silently taken, and the deferred resync is tracked as issueEngineVintageGateDrift. The owner's standing directive from the same message governs the residue: 'don't allow technical debt to exist - if something is wrong, make a backlog item for it or fix it immediately if it's trivial' (project D0047).";
    }
    part d0048AcceptR1 : TestResult {
        :>> id = "e7ee7879-77b9-4319-a8a3-7f2a7019eb66";
        :>> outcome = VerdictKind::pass;
        :>> judgedAgainst = "5e01b211";
        :>> judgedAt = "2026-09-07";
        :>> judgedBy = "wweatherholtz";
    }
}
