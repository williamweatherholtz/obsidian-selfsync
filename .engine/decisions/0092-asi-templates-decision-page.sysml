// =====================================================================
// D0092 (PROJECT numbering) — the asi-templates unit (v3) is installed from the portable-content library and the
// decision-surfacing process publishes this project's standing decision page on its executive-brief surface. PROPOSED:
// installing a unit adds a process definition and a skill (D0070 keystone), so the commit carries this
// #ProspectiveChange Decision. The owner accepts via `keel accept d0092`. Written as one clause (D0303 option C).
// =====================================================================
package ProjectDecision0092 {
    private import EngineElement::*;
    private import EngineWork::*;
    private import EngineVerification::*;
    private import EngineRelationships::*;

    #ProspectiveChange part d0092 : Decision {
        :>> id = "eba7789c-1ad7-4a71-a4b0-46908c7be3d3";
        :>> title = "D0092: the decision page is the asi-templates executive brief, built from the tree and republished at one Artifact path whenever the authority queue changes";
        :>> createdAt = "2026-09-13";
        :>> createdBy = "claudeOpus";
        :>> status = DecisionStatus::accepted;
        :>> context = "Owner, 2026-09-13: 'I means decisions page from asi-template skill.' The decision-surfacing process (D0269/D0359) says the page is the channel and prose is not: the pending set is READ from `keel show authority-queue`, compared with the last published set, and when it moved the page is rebuilt on the asi-templates executive-brief surface and republished at the same Artifact URL; when it did not move, nothing is said. This project had the process definition (the 0.4.1 migrate brought asi-templates.sysml) but not the unit's files - brand tokens, the exec-summary template, the checker, the exec-summary test suite - so the surface could not be built here; the toolkit's exhibit builders and brief checker were run from the sibling checkout. `keel show status` listed the unit as available, not installed.";
        :>> decision = "The asi-templates unit v3 is installed into this project from the machine-local library (`keel process import ~/.keel/library/asi-templates --update --assume-local-base .`: brand/, templates/, tests/exec_summary, the asi-templates skill and process), and the standing decision page is produced by the committed builder docs/decision-page/build.py, which reads every number it shows from the tree (the authority queue, the commit delta since the last closeOut, the decision files, the manifest, the binary's version report) into docs/decision-page/facts.json, renders one tab per ask with the two logic exhibits the surface requires, holds the brief contract under the toolkit's check_templates.py --brief, and writes docs/decision-page/index.html for publication as an Artifact whose URL and published id set are recorded in .keel/decision-page.toml for the next state test; the exhibit geometry probe (fit_check, headless Chromium via Python playwright) is not installed on this machine, so the page states that its exhibits are unmeasured rather than claiming a fit.";
        :>> rationale = "A decision the human cannot find is not a decision they were asked to make, and a queue restated in prose every turn stops being read - the process exists between those two failures, and it needs a surface with a contract a checker can hold (answer first, one tab per ask, no record ids in the reader's prose, every number computed, a do-nothing course, a falsifier, the terse ceiling). Installing the unit rather than copying files keeps the surface under library stewardship, so a brand or template change arrives by `keel library sync` + import, not by hand. Building from the tree rather than typing numbers is what lets the page be republished on every queue change without drifting from the model; committing the builder makes the page regenerable, so the HTML is a derived view (#View in spirit), not authored truth. Running the checker from the sibling toolkit checkout is an honest interim: this project's copy of check_templates.py predates the --brief flag, and duplicating the toolkit's exec_brief builders here would fork them; the builder imports them from the toolkit path and fails loudly if it is absent. WHY PROPOSED: a unit install adds a process and a skill (D0070).";
        :>> consequences = "brand/, templates/exec-summary, tests/exec_summary and the asi-templates skill live in this repository under the unit's install record; the process-skill and activation guards read the unit as chartered; docs/decision-page/ holds the builder, the facts it read and the last page; .keel/decision-page.toml (machine-local) holds the published id set and URL. Each later queue change: rebuild, check, republish the same file path, rewrite the toml, say one line. REMOVAL PATH: `keel process remove asi-templates` plus deleting docs/decision-page/ and the toml; the console deck (`keel serve`) carries the same pending decisions regardless. Accept with `keel accept d0092 --by wweatherholtz --date <d> --note \"owner's words: '...'\"`.";
    }

    // acceptance event (D0121 review-queue sign-off; D0066/D0106 — human-judged, not fabricated)
    verification d0092Accept : Test { :>> id = "3375eb23-bda0-493e-a5e7-172d434101b7"; :>> method = VerificationMethod::confirmation; :>> procedureText = "owner's words: '[x] Adopt this page as the decision channel' (decision page digest pasted by the owner on 2026-09-13) WARN: read-back - the quoted words do not name d0092 (D0201 B); recorded as given (D0423)."; }
    part d0092AcceptR1 : TestResult { :>> id = "fc9422f5-caa4-4c18-b576-58b70dd6b681"; :>> outcome = VerdictKind::pass; :>> judgedAgainst = "d7fc5711"; :>> judgedAt = "2026-09-13"; :>> judgedBy = "wweatherholtz"; :>> createdBy = "wweatherholtz"; }
}
