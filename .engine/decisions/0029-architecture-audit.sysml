// =====================================================================
// D0029 — Adopt a reusable, keel-backed PROGRAMMATIC ARCHITECTURE AUDIT capability: a new optional engine
// schema module (EngineCodeAudit) defining a CodeElement registry, a criticality metric (risk-class ×
// Need-trace, computed), a descriptive DesignPattern catalog, captured STPA control-structure INPUTS, and
// codeHash drift unified with the D0028 // @audit-hash markers — deployed by the `architecture-audit` skill
// + process. PRIMARY lens reframed after critique to invariant-safety + coupling (patterns are descriptive,
// NOT a compliance gate). Designed + accepted 2026-07-18 by wweatherholtz (design spec + "proceed").
// =====================================================================
package ProjectDecision0029 {
    private import EngineElement::*;
    private import EngineWork::*;
    private import EngineVerification::*;

    #ProspectiveChange part d0029 : Decision {
        :>> id = "0d290a1c-7e34-4b55-9a11-2f3c4d5e6a29";
        :>> title = "D0029: reusable programmatic architecture-audit capability (EngineCodeAudit schema module + criticality + descriptive patterns + STPA inputs + drift; architecture-audit skill/process)";
        :>> createdAt = "2026-07-18";
        :>> createdBy = "wweatherholtz";
        :>> status = DecisionStatus::accepted;
        :>> context = "After two rounds of the D0028 function-audit, the owner asked to CEMENT a reusable architecture-audit process through keel: catalogue the project's authored code elements as a new SysML type; rank each by the risk it accepts (judged against Needs); assess design-pattern paradigm/compliance and combine/split opportunities; capture STPA control-structure relationships; then restructure toward clean patterns. The premise was stress-tested at the owner's request. The critique found 'design-pattern compliance ranked by criticality' a WEAK primary lens: patterns are a means not an end (grading compliance invites cargo-culting); every real defect this codebase has caught (CRLF merge, false-absence delete, config-list disable, missing dir-fsync, coalesce-stale size gate) was an invariant/edge-case/data-flow bug a pattern audit would miss; architecture quality lives mostly in the RELATIONSHIPS (coupling, dependency direction) not per-element structure; and refactoring TOWARD patterns (combine-to-match) is itself an anti-pattern. The owner accepted the reframe and directed: STPA is INPUT-CAPTURE only now (defer analysis to a later STPA process for debugging); patterns kept as a descriptive tag used heavily in audits; capture the high-value structural signals (afferent/efferent coupling, distance-from-main-sequence) for holistic use in the later improvement pass. Design recorded in docs/design-history/2026-07-18-architecture-audit-design.md and approved ('proceed').";
        :>> decision = "Adopt the architecture-audit capability. (1) A NEW optional engine schema module EngineCodeAudit (.engine/schema/codeaudit/codeelement.sysml) — imports schema/core, kept SEPARATE so core stays frozen; generic software-architecture vocabulary (CodeElement, RiskClass, InvariantSafety, StpaRole, RestructureAction, DesignPattern), not any deliverable's domain vocabulary, so it is reusable engine infrastructure. (2) CodeElement AUTHORED attributes: id/file/name/kind, codeHash (the SAME audit_hash.py value D0028 stamps in-code), riskClass(+rationale), invariantSafety(+notes) [PRIMARY lens], an OPTIONAL descriptive `pattern` tag [never a compliance gate], stpaRole + actions [captured STPA inputs], restructure(+rationale). Edges: #DependsOn (Need-trace + coupling), #Controls/#Feedback (STPA inputs), #Restructure. (3) COMPUTED VIEWS (never authored, invariant 2): criticality = risk-class tier bumped by high-severity Need-trace; coupling Ca/Ce/instability/distance; drift = codeHash vs the live @audit-hash. (4) A declared, downstream-overridable DesignPattern catalog (.engine/docs/design-patterns.md) tiered high-correctness / concurrency / GoF-subset. (5) The `architecture-audit` process + skill drive the 8-step authoring; keel `arch` view commands (elements/criticality/coupling/drift/stpa-inputs/coverage) are the FOLLOW-ON Rust build in sysmlv2-ai-toolkit. (6) PRIMARY lens = invariant-safety + coupling; patterns descriptive; restructure only when it demonstrably lowers coupling or closes a defect class (caution is the default, with objective exemption criteria).";
        :>> rationale = "The registry + criticality + codeHash-drift backbone is valuable regardless of lens (what exists, how risky, has it changed since audited) and it makes audits COMPOUND + drift-aware. Reframing the primary lens to invariant-safety + coupling targets the failure modes this codebase actually has, and demoting patterns to a descriptive vocabulary avoids the cargo-cult trap while keeping their descriptive power. Authored-facts + computed-views (no code parser in keel) honors 'text is truth, everything derivable is a view' and keeps keel out of deliverable-source parsing (two-models line). A new optional module (like EngineSafety) keeps schema/core frozen. Capturing STPA inputs now (analysis deferred) is exactly the 'record what IS, reference the process to decide what to DO' invariant. Recording it as a Decision + skill/process (not conversation habit) is what D0040/D0059 require of a recurring capability.";
        :>> consequences = "New: .engine/schema/codeaudit/codeelement.sysml, .engine/processes/architecture-audit.sysml, .engine/skills/architecture-audit/ (+ registry entry), .engine/docs/design-patterns.md, docs/design-history/2026-07-18-architecture-audit-design.md, and .tracking/architecture/elements.sysml SEEDED with elements already audited in rounds 1-2 (proves the model end-to-end). keel validate + guard stay green (keel parses the module-defined type generically, as it does EngineSafety). FOLLOW-ON (planned, not this Decision): the keel `arch` Rust view commands in sysmlv2-ai-toolkit; then the full file-by-file per-element audit; then the separate STPA analysis process consuming the captured inputs. #ProspectiveChange: outputs chartered before this stay valid; no reprocessing forced.";
    }

    verification d0029Accept : Test {
        :>> id = "0d29acc7-2b33-4c44-9d55-6e7f80912329";
        :>> method = VerificationMethod::confirmation;
        :>> procedureText = "wweatherholtz brainstormed the design in-session (choosing authored-registry + keel-views, risk-class × Need-trace criticality, invariant-safety + coupling as the primary lens with patterns descriptive, STPA input-capture with analysis deferred), reviewed the recorded design spec (docs/design-history/2026-07-18-architecture-audit-design.md), and approved with 'proceed' on 2026-07-18.";
    }
    part d0029AcceptR1 : TestResult { :>> id = "0d29ac00-ab22-4c33-9d44-5e6f70819329"; :>> outcome = VerdictKind::pass; :>> judgedAgainst = "17b25f6"; :>> judgedAt = "2026-07-18"; :>> judgedBy = "wweatherholtz"; }
}
