// =====================================================================
// d0061 (PROJECT numbering) — clause 1 of 5 of D0048 ("D0048: reconcile with keel 0.3.1 additively (CLI facts + cli schema + lens-command doc-sync) instead of `keel migrate`, which clobbers project additions to engine-shipped schema"), recorded as its own Decision per
// D0303 option C (one Decision per clause, #DependsOn between them, the chain superseding the compound one) so the
// decision-scaffolding guard can see which clause an edge charters. The text is the parent's clause VERBATIM; the
// rationale and consequences are the parent's, which the clauses share. Status follows the parent's acceptance path:
// PROPOSED — the owner accepts each clause; the compound d0048 is retired by the #Supersede edge from clause 1.
// =====================================================================
package ProjectDecision0061 {
    private import EngineElement::*;
    private import EngineWork::*;
    private import EngineVerification::*;
    private import EngineRelationships::*;
    private import ProjectDecision0048::*;

    #ProspectiveChange part d0061 : Decision {
        :>> id = "eb10238a-4888-4b10-8f55-69563cdbb348";
        :>> title = "D0061 (D0048 clause 1/5): Reject the wholesale resync for now and reconcile ADDITIVELY, taking only what the gate actually requires: add";
        :>> createdAt = "2026-09-13";
        :>> createdBy = "claudeOpus";
        :>> status = DecisionStatus::accepted;
        :>> context = "Clause 1 of 5 of D0048 (created 2026-09-07, accepted), split out on 2026-09-13 under keel 0.4.1's decision-scaffolding guard (D0303 option C, issue331): a compound Decision hides which clause a chartering edge delivers. The parent's context: Installing the git hooks (issueHooksNotInstalled) made a real gate run here for the first time in ~6 weeks, and it immediately failed. Two causes had hidden the drift: no hook was active (a machine-global core.hooksPath pointed at a directory that does not exist, so git silently ran nothing), and CLAUDE.md section 5 documented the validator as a local Windows release-build path that does not exist in this repo — so a 6-week-old sibling checkout's keel had been run by hand instead of the keel 0.3.1 on PATH. Every recent 'keel guard ALL PASS' record was therefore that stale binary's verdict, and D0046 plus the provenanceDecoupling DoD now carry explicit GATE CORRECTIONs saying so. Under 0.3.1 the tree showed five failing guards: evidence-cited (2 — this sitting's own AI-judged method=test results lacked the `// RAN:` receipt the newer engine requires), viewpoint-renderer (9 — declared renderers named per-lens verbs that 0.3.1 no longer dispatches), tool-reference (1 — the engine-triage skill pointed at .engine/tools/triage_reminder.py, which does not exist and never did: CLAUDE.md itself says that hook is still sprint30), sprint-closure (1 — tracked as issueMootedTaskUnstamped, resolved separately), and cli-surface-declared (1 — .engine/cli/commands.sysml absent). The owner chose to run `keel migrate` and then commit clean. `keel migrate --dry-run` looked benign: 481 .engine/ files, 0 blockers, nothing outside .engine/. The real run was NOT benign. It refuses a dirty tree (correctly), so the sitting's work was stashed first; afterwards `keel validate` FAILED where it had passed, and two guards that had been GREEN went red — marker-vocabulary with 228 violations and attribute-vocabulary with 1216. Cause: migrate replaced .engine/schema/core/relationships.sysml with the binary's stock copy, dropping it from 25 `metadata def` declarations to 18 — deleting the 7 markers D0045 had deliberately added (the STPA edges such as #LeadsTo) to satisfy an earlier guard. The migration was rolled back (nothing had been committed, so `git checkout -- . && git clean -fd` restored HEAD exactly; D0045's 25 markers verified intact) and the stash restored.";
        :>> decision = "Reject the wholesale resync for now and reconcile ADDITIVELY, taking only what the gate actually requires: add .engine/cli/commands.sysml and the .engine/schema/cli/cli.sysml that defines its CliCommand/CliEffect/CliStability types — both are NEW files in this tree, so nothing is overwritten; they were extracted from a `keel init` into a scratch directory rather than by migrating this tree.";
        :>> rationale = "Shared with D0048, whose clauses were decided together: The additive route was chosen because it reaches the same place — validate, guard and check-engine all green under the binary that gates commits — while changing 5 engine files instead of 481, and without touching a single file this project has customized. That matters more than tidiness here: the wholesale migrate DEMONSTRATED that it silently reverts project decisions, so running it to satisfy a gate would trade one dishonest state (a stale gate) for a worse one (a green gate whose greenness came from deleting D0045). Rolling it back rather than patching forward was right for the same reason: 481 files of stock engine mixed with hand-re-applied customizations cannot be reviewed, and migrate's own refusal-on-dirty-tree exists precisely because a half-migrated tree is indistinguishable afterwards. Deferring the resync is honest incompleteness rather than debt hidden in prose: the tree is now truthfully green on the guards that run, and the vintage gap is a tracked Issue with a named DoD, which is what D0098's honest-state-not-self-assurance principle asks for. The `// RAN:` receipts were added rather than argued with, because the guard is right — an AI-judged pass with no re-derivable command is a testimony, not a test, and that is exactly the failure mode that let a stale binary's ALL PASS stand unexamined. Two things were deliberately NOT done: the migrate hazard was not worked around by force (no --no-verify, no editing the guard), and no `keel migrate` was re-run to cherry-pick files out of it — the scratch `keel init` gives the same content with no risk to this tree. THE SPLIT ITSELF: recorded one Decision per clause so that partial delivery is visible to the scaffolding guard and each clause can be chartered, accepted or superseded on its own; the wording is the parent's, unchanged.";
        :>> consequences = "Those of D0048 that this clause carries: keel validate = 0, keel guard = 0 (63 checks pass, no failures), keel check-engine = 0 — all three verified by exit code, not by piped output (an earlier check in this sitting read `tail`'s exit status through a pipe and briefly mistook a masked result for a pass; the re-runs captured the real codes). Five .engine files change: two added (cli/commands.sysml, schema/cli/cli.sysml), three edited (views/viewpoint-registry.sysml, skills/engine-triage/SKILL.md, decisions/0040 typo). Adding engine schema makes this a process-definition change, so this Decision is the D0070 record. The pre-commit hook now genuinely gates every commit with the PATH binary, so the stale-validator class cannot recur silently. STILL OPEN and tracked: issueEngineVintageGateDrift (the 481-file resync plus re-applying D0045 and the attribute-vocabulary declarations) and 19 unread non-blocking warnings across viewpoint-renderer, manifest-coverage, verification-trace, parser-coverage, base-first-justification and control-event-coverage — non-blocking by design (D0098) but explicitly NOT read yet, which is itself part of that Issue's DoD. An upstream observation worth carrying to the toolkit: `keel migrate` should either merge project additions into shipped schema files or refuse and name them, rather than overwriting silently — its dry-run reported 0 blockers for a change that deleted a project decision's effect.";
    }
    #Supersede dependency from d0061 to d0048;

    // acceptance event (D0121 review-queue sign-off; D0066/D0106 — human-judged, not fabricated)
    verification d0061Accept : Test { :>> id = "e78d55a5-40a6-44c1-a965-edbe7eaf58c2"; :>> method = VerificationMethod::confirmation; :>> procedureText = "owner's words: '[x] Accept all 34 clause records' (decision page digest pasted by the owner on 2026-09-13) WARN: read-back - the quoted words do not name d0061 (D0201 B); recorded as given (D0423)."; }
    part d0061AcceptR1 : TestResult { :>> id = "9f34865b-2f8f-468a-a4b7-6690723efb2f"; :>> outcome = VerdictKind::pass; :>> judgedAgainst = "d7fc5711"; :>> judgedAt = "2026-09-13"; :>> judgedBy = "wweatherholtz"; :>> createdBy = "wweatherholtz"; }
}
