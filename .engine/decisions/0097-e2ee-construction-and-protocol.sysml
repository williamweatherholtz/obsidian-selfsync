// D0097 (PROPOSED — NOT YET ACCEPTED) — E2EE construction - vault key under an Argon2id KEK, deterministic AES-GCM frames, keyring, downgrade guard
// Recorded via `keel record decision` (engine D0105 RMWX axis; issue054). Acceptance is a separate explicit
// human gate (method=confirmation, engine D0106): flip status + add the d0097Accept event on sign-off.
package Decision0097 {
    private import EngineElement::*;
    private import EngineWork::*;
    private import EngineVerification::*;
    private import EngineRelationships::*;

    part d0097 : Decision {
        :>> id = "d99c9cf8-0680-4b66-bb75-515678d73686";
        :>> title = "E2EE construction - vault key under an Argon2id KEK, deterministic AES-GCM frames, keyring, downgrade guard";
        :>> createdAt = "2026-11-10";
        :>> createdBy = "ai";
        :>> status = DecisionStatus::proposed;
        :>> context = "The chunk pipeline is content-addressed. A chunk's address is sha256 of its bytes (client/src/chunker.ts:17-20, server/src/chunkstore.rs:77-82). The server reassembles and checks sha256 of the whole file at commit (server/src/vault.rs:618). The client reconciles by comparing three hash strings (client/src/reconcile.ts:19-21). Reindex re-chunks the mirror with a CDC chunker (vault.rs:464-473). Any encryption must keep dedup, keep reconcile, and keep reindex. It must not let an old client write plaintext into an encrypted vault or ciphertext into a user's local vault. The comparison in docs/design/specs/2026-11-10-e2ee-design.md section 5 measured the first draft against published practice and changed it in fourteen rows. The references were Obsidian Sync, Cryptomator, Standard Notes 004, Bitwarden, Proton, DupLESS, the partitioning-oracle paper and OWASP.";
        :>> decision = "KEYS. A separate encryption password, never sent to the server. Argon2id (64 MiB, t=3, p=1, parameters stored with the record) with a 16-byte per-vault salt derives a KEK. A random 32-byte vault key VK is wrapped by the KEK with AES-256-GCM, a random nonce and a 32-byte zero commitment pad. HKDF-SHA256 derives from VK: k_enc, k_iv, k_id, k_check. CHUNKS. Each plaintext chunk from the existing chunker is encrypted with AES-256-GCM under k_enc. The synthetic IV is HMAC-SHA256(k_iv, plaintext)[0..12]. A 32-byte zero pad goes in front of the plaintext. The AAD is 'selfsync/e2ee/v1' plus the vault id. The frame is magic SSE1, iv, ct_len, ciphertext with tag. The chunk address is sha256 of the frame, so dedup is unchanged. FILE IDENTITY. FileMeta.hash becomes HMAC-SHA256(k_id, plaintext file). FileMeta.size stays the plaintext size. KEYRING. A per-vault sidecar .keyring.json holds kdf parameters, salt, the wrapped VK and a check value. GET keyring (Read grant, 404 means not encrypted) and PUT keyring (owner, create-once) are additive endpoints. SERVER. For a vault with a keyring: PUT chunk also needs a well-formed frame. Commit checks size from frame headers and skips the whole-file sha256. The mirror holds the frame stream. Reindex splits by frame headers. Every vault-scoped request must carry the header x-selfsync-e2ee: 1, or it is answered with HTTP 428. CLIENT. One seam, ContentCodec, with a PlainCodec that reproduces today's bytes and an E2eeCodec. WebCrypto AES-GCM and HKDF. Argon2id from the audited pure-JS library noble-hashes.";
        :>> rationale = "A random VK under a password-derived KEK makes a password change a 32-byte re-wrap and makes sharing a key hand-over. That is the Bitwarden, Proton and Standard Notes shape. A keyed synthetic IV keeps content-addressed dedup. It leaks only chunk equality within one vault, because the IV key is secret. This is the DupLESS answer to the known weakness of plain convergent encryption. The zero pad makes AES-GCM key-committing for the cost of 32 bytes per chunk. It closes the partitioning-oracle attack that targets password-derived keys. A keyed file identity lets the client detect chunk substitution, truncation or reorder by the server. Per-chunk content addresses cannot, because the server knows every frame hash. The frame is self-delimiting without the key. The server can validate, size and reindex without decrypting. The header guard fails closed for a pre-E2EE client at its first changes call, in the spirit of D0042. AES-256-GCM through WebCrypto is native on Electron and on both mobile WebViews. No WASM, bundle or CSP exposure follows. ALTERNATIVES: (i) XChaCha20-Poly1305 via a JS library - rejected, no runtime advantage here and a new dependency on the hot path. (ii) random nonces per chunk - rejected, every edit would re-upload every chunk. (iii) per-chunk AAD binding to the file - rejected, it breaks cross-file dedup and makes a rename a full re-upload. (iv) hash-wasm for Argon2id - rejected for v1 because WebAssembly instantiation under Obsidian's renderer CSP is unverified. The KDF runs once per device enrolment, so pure JS is fast enough.";
        :>> consequences = "Server gains a keyring sidecar, two endpoints, a frame parser, an encrypted-vault branch in put_chunk, commit and reindex, and the 428 guard. The wire signature is regenerated and the change is additive. Client gains client/src/e2ee with the codec, the KDF, the keyring wrap and unwrap, and incremental keyed identity. It gains one dependency, noble-hashes. Every identity computation in reconcile and sync routes through the codec. A plaintext vault runs the PlainCodec and is byte-for-byte unchanged. The Argon2id memory parameter is an open point for the owner. Lower it to 32 MiB if a real phone needs more than about eight seconds.";
    }
    #DerivedFrom dependency from d0097 to us013;
}
