// =====================================================================
// D0019 — bound tombstone growth + fix the corrupt-reindex resurrection (RC-1) with a HISTORY
// HORIZON, not an arbitrary cap. The server exposes a `history_floor` (the version at/above which
// deletion history is COMPLETE); a rebuild-from-disk (corrupt) reindex — which cannot recover
// tombstones — raises the floor to the current version, declaring "deletion history was reset
// here". A client that detects the reset (floor advanced past the one it last synced, or a version
// rewind) does a CONSERVATIVE reconcile: it NEVER deletes a local file without a real tombstone
// (keep + push), and surfaces ONE BATCHED notice listing the kept/re-uploaded files so the user can
// review — resurrection becomes an explicit, visible, user-correctable event instead of a silent
// data-integrity bug. This is a DELIVERABLE (SelfSync sync-safety) change. Accepted 2026-07-07 by
// wweatherholtz via the design questions. Tracked: historyRebase.
// =====================================================================
package ProjectDecision0019 {
    private import EngineElement::*;
    private import EngineWork::*;
    private import EngineVerification::*;

    part d0019 : Decision {
        :>> id = "c0f1a5cc-f120-4a10-9b20-a1b2c3d40f30";
        :>> title = "D0019: history-horizon (keep+push+batched-notify below the floor), not a tombstone cap";
        :>> createdAt = "2026-07-07";
        :>> createdBy = "wweatherholtz";
        :>> status = DecisionStatus::accepted;
        :>> context = "Deletion is tombstone-authoritative (0.10.25): a client deletes a local file ONLY when the server holds a real deletion tombstone; mere absence -> keep + push (this is the fix that stopped a wrong/fresh/restored server from wiping a vault). Round 6 removed the arbitrary MAX_TOMBSTONES cap because silently dropping the oldest tombstones made a long-offline client read a genuine deletion as absence-without-tombstone and RESTORE it (fleet-wide resurrection). Two open consequences remained: issueUnboundedTombstones (Low — the deletions set now grows without bound; each is tiny, a path + a u64) and issueCorruptReindexResurrection (HIGH, RC-1 — a parse-corrupt index opens empty and reindex rebuilds files from disk but CANNOT recover tombstones, so changes(0) reports zero deletes and a long-offline client resurrects its since-deleted files; the documented repair itself induces the resurrection). Tombstones cannot be reconstructed from disk, so a corrupt reindex IS a deletion-history reset. The new per-vault SQLite index (D0018) already carries a `history_floor` meta cell, so the horizon is a cheap read.";
        :>> decision = "Introduce a HISTORY HORIZON. The server tracks `history_floor` = the version at/above which deletion history is complete (genesis = 1). A reindex that REBUILDS FROM DISK (the corrupt/empty-index case, where tombstones are gone) raises `history_floor` to the current max version; a HEALTHY reindex preserves tombstones and leaves the floor untouched. `history_floor` is exposed in the changes response. The CLIENT tracks the floor it last synced at; it detects a deletion-history RESET when the server's `history_floor` advanced past that stored floor OR the server version rewound below the client's cursor. On a reset reconcile the client stays CONSERVATIVE: it keeps every local file that is absent-without-tombstone and pushes it back (never deletes without a tombstone — the tombstone-authoritative rule already guarantees this), collects those kept files, and after the pass surfaces ONE BATCHED, dismissible notice ('the server's deletion history was reset; N files here weren't on the server and were kept + re-uploaded — delete any that were removed elsewhere: …'), then advances its stored floor. Scope now = the corrupt-reindex floor + the client horizon (closes RC-1, HIGH). A deliberate operator tombstone-PRUNE (raise the floor + drop old tombstones to bound growth) is DEFERRED.";
        :>> rationale = "The north star is preventing INDUCED, user-perceived DATA LOSS. In the below-floor ambiguity (a local file absent from the server could be a pruned deletion OR a file this device never synced), the two failure modes are asymmetric: treating it as deleted risks DELETING a legitimately-new file (real data loss); treating it as kept risks RESURRECTING an already-deleted file (annoyance, not loss — nothing is destroyed). So the data-safety-preserving action is unambiguously KEEP + push, which the tombstone-authoritative rule already does. The only real defect in RC-1 is that this resurrection is SILENT; the fix is therefore to DETECT the reset and NOTIFY, converting a silent integrity bug into a visible, user-correctable event. Batched (not per-file) keeps it usable on a large reset and on mobile. A history FLOOR (vs an arbitrary count/age cap) is the non-arbitrary bound: it never corrupts deletion semantics for an up-to-date client (floor stays at genesis in normal operation) and only engages exactly when history genuinely became incomplete. ALTERNATIVES CONSIDERED: (a) hard modal prompt / block sync below the floor until the user adjudicates each file — DECLINED: strongest against resurrection but heavy UX, awkward-to-impossible on mobile, and stalls headless/background sync; the batched notice gets ~all the benefit (user can act) without blocking, and data is never at risk either way. (b) keep+push SILENTLY (no notice) — DECLINED: least friction but leaves RC-1's core complaint (silent resurrection) unaddressed. (c) re-introduce an arbitrary tombstone cap (count or age) — REJECTED (the exact Round-6 regression: silent semantic corruption). (d) treat below-floor absence as deletion — REJECTED (induces real data loss). DEFERRED: a deliberate operator tombstone-PRUNE endpoint to actively bound growth (issueUnboundedTombstones, Low) — tombstones are tiny so growth is a slow, low-severity problem; the prune reuses the same floor+horizon machinery this pass builds, so it is a cheap bounded follow-up, not a rewrite. CRITERIA: no-data-loss (keep+push, always) x resurrection-made-visible (batched notice) x non-arbitrary bound (floor, engages only on real history loss) x usable (batched, non-blocking, mobile-safe) x proportionate (defer the Low prune).";
        :>> consequences = "SERVER: SqliteIndex gains set_history_floor + returns history_floor in its changes response; Vault caches history_floor (set on open, updated on reindex) and raises it to the current version when a reindex rebuilds from disk (was_corrupt); the protocol ChangesResponse gains a history_floor field (serde default so an older server deserializes as genesis, never a false reset). CLIENT: the transport surfaces history_floor; reconcile detects a reset (floor advanced past the stored floor, or version rewind) and, on a reset pass, batches the kept absent-without-tombstone files; main.ts persists lastHistoryFloor + shows one batched Notice; a fresh client (no stored floor) never false-triggers. Tests both sides (server: a corrupt reindex raises the floor, a healthy one doesn't; client: a floor-advance/rewind triggers the batched notice + keeps files, a steady floor doesn't). doc-sync: note the horizon in the deletion-safety docs. Resolves issueCorruptReindexResurrection (HIGH) and issueUnboundedTombstones (Low — the floor is the bound; the active prune is the deferred follow-up). Ships as a client plugin release (client behavior changed).";
    }

    verification d0019Accept : Test {
        :>> id = "c0f1a5cc-f121-4a10-9b20-a1b2c3d40f31";
        :>> method = VerificationMethod::confirmation;
        :>> procedureText = "wweatherholtz accepted (2026-07-07) via the design questions: below-floor client behavior = 'keep + push notify (batches, not per file)' and scope = 'Corrupt-reindex floor + horizon' — i.e. keep+push+batched-notify (hard-prompt declined, silent-keep declined), building the corrupt-reindex floor + client horizon now and deferring the deliberate operator tombstone-prune.";
    }
    part d0019AcceptR1 : TestResult { :>> id = "c0f1a5cc-f122-4a10-9b20-a1b2c3d40f32"; :>> outcome = VerdictKind::pass; :>> judgedAgainst = "33b4812"; :>> judgedAt = "2026-07-07"; :>> judgedBy = "wweatherholtz"; }
}
