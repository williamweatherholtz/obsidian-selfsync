// =====================================================================
// d0091 (PROJECT numbering) — clause 6 of 6 of D0055 ("D0055: a release is published only after its assets verify (draft → verify → publish), under a tag that is its own, with a rebuild-from-tag anchor in the daily check, a version-tagged server image per release, and SHA-pinned workflow actions"), recorded as its own Decision per
// D0303 option C (one Decision per clause, #DependsOn between them, the chain superseding the compound one) so the
// decision-scaffolding guard can see which clause an edge charters. The text is the parent's clause VERBATIM; the
// rationale and consequences are the parent's, which the clauses share. Status follows the parent's acceptance path:
// PROPOSED — the owner accepts each clause; the compound d0055 is retired by the #Supersede edge from clause 1.
// =====================================================================
package ProjectDecision0091 {
    private import EngineElement::*;
    private import EngineWork::*;
    private import EngineVerification::*;
    private import EngineRelationships::*;
    private import ProjectDecision0055::*;
    private import ProjectDecision0090::*;

    #ProspectiveChange part d0091 : Decision {
        :>> id = "b761ca57-b8df-4404-9f63-979fedff1718";
        :>> title = "D0091 (D0055 clause 6/6): check-release.mjs probes `gh auth status` first, includes gh's stderr in each problem, and downloads only the";
        :>> createdAt = "2026-09-13";
        :>> createdBy = "claudeOpus";
        :>> status = DecisionStatus::accepted;
        :>> context = "Clause 6 of 6 of D0055 (created 2026-09-11, accepted), split out on 2026-09-13 under keel 0.4.1's decision-scaffolding guard (D0303 option C, issue331): a compound Decision hides which clause a chartering edge delivers. The parent's context: D0054 (2026-09-11, proposed) made 'released' mean 'these bytes': release.yml records SHA256SUMS and re-verifies the published assets; check-release.mjs verifies digests daily; the plugin shows the digest of its installed main.js. The same day's architecture panel (release-channel critic, PEDANT-1 + PESSIMIST-2) attacked that design and found four MAJOR gaps in the mechanism as shipped in 1.30.17: (RL1) the release was created non-draft and BRAT-installable BEFORE the verify step, so a mismatch left a live bad release and a partial upload counted as 'released' on re-run; (RL2) `gh release create --target` silently reuses an existing tag, so a delete-assets-and-re-run recovery would publish a build of main-HEAD under a tag pointing at another commit, with SHA256SUMS agreeing with itself; (RL3) SHA256SUMS lives in the same mutable release as the assets, so anyone with contents:write can rewrite both — the digest detects corruption, not the H-5 threat UCA-57 names, yet the code and the STPA claimed the stronger property; (RL4) the sanctioned release path never produced a version-tagged server image (a GITHUB_TOKEN-created tag does not trigger server-image.yml), so docs/deployment.md told operators to pin a tag that did not exist; plus (RL5) mutable action refs, persisted checkout credentials, no Dependabot, and (RL6) check-release.mjs hiding gh's real error and downloading every asset. The critic independently confirmed the build is reproducible (a fresh build of tag 1.30.17 was byte-identical to the published main.js), which makes a rebuild-from-tag anchor cheap and honest.";
        :>> decision = "check-release.mjs probes `gh auth status` first, includes gh's stderr in each problem, and downloads only the verified assets. CONSIDERED, NOT ADOPTED: `npm ci --ignore-scripts` (esbuild's platform package install is script-driven in some configurations; the lockfile + pinned actions are the control); artifact signing / attestation (Sigstore, `actions/attest-build-provenance`) stays a follow-on the owner may charter.";
        :>> rationale = "Shared with D0055, whose clauses were decided together: A verification that runs after the artifact is already installable is a report, not a gate; making the release a draft until it verifies turns it into a gate at no cost (the verify step already existed). Reusing a tag that points elsewhere is the one path by which 'assets and tag describe the same build' could silently become false, and it was the documented recovery path — refusing it is cheaper than any check that could detect it afterwards. A digest stored beside the bytes it attests proves consistency, not origin; rebuilding the tag proves origin because the build is reproducible, and it reuses the exact steps release.yml runs. The missing version-tagged image was a documented promise the pipeline could not keep; a dispatch on the tag ref is the smallest change that keeps it. Pinning by SHA with Dependabot is standard supply-chain hygiene for workflows that hold contents:write. WHY A SEPARATE DECISION: D0054 is proposed and owned by the agent; D0108 forbids a non-owner overwriting it in place, and the amendment is substantive enough that the owner should accept it explicitly rather than find D0054's text changed under the same number. WHY PROPOSED: every touched file is enforcement surface (D0209 clause 2). THE SPLIT ITSELF: recorded one Decision per clause so that partial delivery is visible to the scaffolding guard and each clause can be chartered, accepted or superseded on its own; the wording is the parent's, unchanged.";
        :>> consequences = "Those of D0055 that this clause carries: release.yml gains a draft phase, an asset-presence check, a tag guard, a publish step and an image dispatch (actions:write); verify-released.yml gains the rebuild-and-compare step (fails red if the build is ever not reproducible — a true signal); server-image.yml + ci.yml + release.yml + verify-released.yml pin actions by SHA; .github/dependabot.yml is new; check-release.mjs reports honestly. First exercised by the 1.30.18 release (releaseIntegrityHardeningDoD). ORDER NOTE for the owner: as with D0054, the enforcement-surface change ships in the same commit the Decision is proposed in (the standing D0049-shape convention so the gate runs on it); the panel flagged that order against CLAUDE.md §3a — surfaced, not hidden. REMOVAL PATH: `git revert` of the sprint commit restores D0054's publish-then-verify shape. Accept with `keel accept d0055` (and `keel accept d0054`) from the owner's own terminal.";
    }
    #DependsOn dependency from d0091 to d0090;

    // acceptance event (D0121 review-queue sign-off; D0066/D0106 — human-judged, not fabricated)
    verification d0091Accept : Test { :>> id = "40125d11-7d98-43f9-9bcb-5e412a5d76b1"; :>> method = VerificationMethod::confirmation; :>> procedureText = "owner's words: '[x] Accept all 34 clause records' (decision page digest pasted by the owner on 2026-09-13) WARN: read-back - the quoted words do not name d0091 (D0201 B); recorded as given (D0423)."; }
    part d0091AcceptR1 : TestResult { :>> id = "c18caede-9d08-404f-89ba-e112bf2ed6f6"; :>> outcome = VerdictKind::pass; :>> judgedAgainst = "d7fc5711"; :>> judgedAt = "2026-09-13"; :>> judgedBy = "wweatherholtz"; :>> createdBy = "wweatherholtz"; }
}
