// =====================================================================
// D0030 — Adopt two COMPUTED correctness-verification processes: Property-Based Testing (find bugs via
// invariants, Anthropic's Claude-PBT method) and Mutation Testing (measure whether the suite catches bugs).
// Both produce FACTS (counterexamples, mutation scores) not attestations, both END by recording findings as
// tracked Issues, and both directly answer the founding complaint that bugs slipped past example-based tests.
// Deployed by the `property-based-testing` + `mutation-testing` skills. Accepted 2026-07-18 by wweatherholtz.
// =====================================================================
package ProjectDecision0030 {
    private import EngineElement::*;
    private import EngineWork::*;
    private import EngineVerification::*;

    #ProspectiveChange part d0030 : Decision {
        :>> id = "0d300a1c-7e34-4b55-9a11-2f3c4d5e6a30";
        :>> title = "D0030: adopt Property-Based Testing + Mutation Testing as recorded verification processes (correctness, computed-not-attested)";
        :>> createdAt = "2026-07-18";
        :>> createdBy = "wweatherholtz";
        :>> status = DecisionStatus::accepted;
        :>> context = "The session's founding complaint was that critique passes kept finding MEDIUM+ bugs that example-based tests did not catch. A research survey of AI-assisted critique methods (recorded in docs/design-history/2026-07-18-architecture-audit-design.md's sibling advisory + web sources) found: (a) intrinsic self-correction / self-refine is UNRELIABLE (self-bias, degeneration-of-thought) — independent adversarial critics (which the engine already mandates, D0080) are the fix, so our critique architecture stands; (b) the genuine GAP is correctness VERIFICATION that produces facts, best filled by Property-Based Testing (test invariants, not examples — Anthropic's Claude-PBT method: investigate -> propose properties grounded in the code -> write tests -> a reflection loop separating genuine bugs from wrong properties -> record; high-confidence severity-ranking raised finding validity 56%->86%) and Mutation Testing (inject faults; a surviving mutant is a concrete test-gap — the direct, computed answer to 'are tests being carried out?'; Meta drives LLM test-gen off exactly this signal). Both fit the engine's 'compute facts, don't attest' invariant (a counterexample / mutation score is a computed fact, D0026/D0088) and the criticality model (target the highest-risk pure cores first, keel arch criticality).";
        :>> decision = "Adopt both as first-class, recorded engine processes + deploying skills. (1) property-based-testing (.engine/processes/property-based-testing.sysml + skill): the 5-step Claude-PBT method over the PURE cores (decide/merge3/chunker/sameIgnoringEol/mergeEnabledPluginsJson via fast-check; the Rust chunker/safe_rel_path/index round-trips via proptest), prioritized by criticality; properties are CURATED against the code's real invariants (AI-drafted properties are frequently trivial/incorrect); the reflection loop separates a real bug from a too-strong property; findings recorded as Issues + permanent property regressions. (2) mutation-testing (.engine/processes/mutation-testing.sysml + skill): cargo-mutants (server) / Stryker (client) scoped by criticality; each surviving mutant is triaged (real test-gap -> a fail-first killing test; equivalent -> a justified accept), the mutation score recorded as a monitored Indicator (D0089) floorable in CI once a defensible baseline exists (D0088). BOTH processes END with a `record findings` step (Issues via D0077, computed TestResults/Indicators — never a prose 'looks correct'). Kick-off order: the PBT (Anthropic) pass runs FIRST on the pure cores; mutation testing follows to quantify the residual suite efficacy. Explicitly NOT adopted: self-refine / single-agent self-critique loops (unreliable), and blind trust in AI-generated properties/invariants (curate them); external SaaS PR-reviewers are at most an optional continuous net (code egress + noise), not a replacement for these computed methods.";
        :>> rationale = "These are the two methods that convert 'do the tests catch bugs?' from an opinion into a COMPUTED fact — exactly what the founding complaint needed and what the engine's compute-don't-attest philosophy wants. PBT finds the edge-case classes example tests miss (the CRLF-merge / false-absence family); mutation testing proves the suite would fail on a real fault (coverage only proves lines ran). Recording them as processes+skills (not conversation habit) is what D0040/D0059 require of recurring methods, and routing them by the architecture-audit criticality ranking focuses effort on the dataLoss/correctness elements. Ending each with a mandatory record-findings step keeps them honest (facts + tracked Issues, no prose attestation).";
        :>> consequences = "New: .engine/processes/property-based-testing.sysml, .engine/processes/mutation-testing.sysml, .engine/skills/property-based-testing/, .engine/skills/mutation-testing/ (+ registry entries). Adds a fast-check devDependency (client) for the PBT kick-off; cargo-mutants + Stryker are dev-only tools introduced when mutation-testing runs. New Indicator (mutation score) when mutation-testing runs. Findings from each run land as tracked Issues + permanent tests + (for mutation) a score Indicator. #ProspectiveChange: prior outputs stay valid; no reprocessing forced. First execution: a PBT pass on the pure client cores this session (findings recorded).";
    }

    verification d0030Accept : Test {
        :>> id = "0d30acc7-2b33-4c44-9d55-6e7f80912330";
        :>> method = VerificationMethod::confirmation;
        :>> procedureText = "wweatherholtz directed on 2026-07-18, after the AI-critique-methods research + fit-assessment: 'implement both as processes and kick off the anthropic one first. record finding at the end of the processes, of course.' — an explicit instruction to adopt PBT + mutation testing as recorded processes (findings recorded at each process's end) and to run the property-based-testing (Anthropic) pass first.";
    }
    part d0030AcceptR1 : TestResult { :>> id = "0d30ac00-ab22-4c33-9d44-5e6f70819330"; :>> outcome = VerdictKind::pass; :>> judgedAgainst = "0669645"; :>> judgedAt = "2026-07-18"; :>> judgedBy = "wweatherholtz"; }
}
