// =====================================================================
// D0041 — user-configurable bulk-delete CONFIRMATION (replaces the fixed ratio/empty-manifest guard).
// Owner-directed + owner-accepted (2026-08-10, "agreed on all counts … proceed"). Deliverable-domain PRODUCT
// behaviour change (no engine schema/process change) → NOT a #ProspectiveChange; same class as D0037-D0040.
// =====================================================================
package ProjectDecision0041 {
    private import EngineElement::*;
    private import EngineWork::*;
    private import EngineVerification::*;
    private import EngineRelationships::*;

    part d0041 : Decision {
        :>> id = "c3d4e5f6-7a8b-4c9d-ae1f-2b3c4d5e6f70";
        :>> title = "D0041: replace the fixed bulk-delete ratio guard with a user-configurable INCOMING-delete confirmation; outgoing deletes propagate exactly";
        :>> createdAt = "2026-08-10";
        :>> createdBy = "wweatherholtz";
        :>> status = DecisionStatus::accepted;
        :>> context = "The reconcile bulk-delete guard (BULK_DELETE_RATIO=0.5 + empty-manifest override + a cumulative DeleteRateGuard) refuses to PROPAGATE a deletion batch when it looks like a suspicious fraction of the synced set vanished. Its stated purpose is signal integrity — an index-loss / partial-restore / de-hydrated-listing 'files vanished' signal is indistinguishable per-file from a genuine bulk delete, so it biases to refuse+surface (recoverable) over propagate (irreversible). The owner objected to the SIDE EFFECT: it interrupts GENUINE user deletions (routine vault/folder refactoring — deleting half of a folder) and reinterprets them, and for a composed-vault subtree the whole-vault calibration (R9 finding A) mostly produces false pushback. The owner's position: a user's own deletion should be immediate + exact; irreversibility belongs to a backup/rollback system (explicitly OUT OF SCOPE — not to be built); if the concern is an ERRONEOUS signal, prevent THAT (bolster signal integrity) rather than block legitimate input; and the user should be able to choose the policy. A design discussion converged on a direction split + a user setting + a non-blocking confirmation gate.";
        :>> decision = "Split by DIRECTION and make the incoming case user-configurable. (1) OUTGOING (a local delete propagating to the server / other devices) is HONORED EXACTLY — no bulk guard — because it is the user's genuine input; the existing per-file absence RE-PROBE stays (it only ever skips a file that still exists on disk, i.e. correctness, not pushback). The prior OUTGOING guard (wouldDeleteRemote / guardRemoteDelete) is REMOVED. (2) INCOMING (a server/source tombstone batch that would wipe local copies) is gated by a USER SETTING: `Confirm large incoming deletions` = Off | 'More than N files' | 'More than N % of the synced set', with a validated numeric N; DEFAULT = 'More than 10 files' (absolute, not a percentage — a percentage nags on small sets). When an incoming pass's delete-local count exceeds the chosen threshold, those deletions are HELD (not applied) and surfaced NON-BLOCKINGLY (the existing conflict-review pattern, not a blocking modal — mobile syncs in the background) as 'N deletions awaiting your confirmation', with two actions: DELETE THEM (apply the removals → gone everywhere) or KEEP THEM (re-push/resurrect → both sides converge on kept, which also stops the re-nag loop the old refuse-only design had). The pending set is DERIVED each pass from the reconcile (not persisted) — it self-converges once resolved. (3) The cumulative DeleteRateGuard (a paced-malicious-server drain defense) is DROPPED — that threat is outside the trusted-server model (D0007). (4) An ALWAYS-ON integrity FLOOR remains beneath the setting and is not a count heuristic: never act on deletions from a source that is not `ready` (a reindexing/degraded server) — already enforced on the primary connect + the mount source-readiness probe. The policy is GLOBAL (one setting), applied per scope (primary + each mount use their own set size for the % case), so it is NOT mount-specific and it dissolves R9 finding A (a small mount with a 10-file threshold never false-fires).";
        :>> rationale = "This honors the owner's principle — genuine input is exact; the only interruption is on a signal the user did NOT personally issue (incoming) and can choose to disable — while keeping the real signal-integrity protections that work BY CAUSE, not by counting: the source-readiness floor catches server index loss, and the per-file re-probe catches a stale single-snapshot listing. The user threshold + human confirm then covers the remaining ambiguous case (a healthy source, but a surprising number of files vanished — e.g. another device/person deleted a lot) with a decision only the user can make, instead of a fixed heuristic guessing for them. NON-BLOCKING review (vs a modal) fits the plugin's existing honest-status/conflict UX + background/mobile sync. KEEP-as-resurrect converges cleanly and removes the old refuse-only re-nag. DROPPING the cumulative guard is consistent with the trusted-server threat model (D0007). ALTERNATIVES: (i) keep the fixed ratio guard — REJECTED (false pushback on legitimate deletes; the owner's core objection). (ii) build a backup/rollback so deletions are always safe to apply — REJECTED/out-of-scope by the owner. (iii) an explicit source-availability check as the SOLE guard (no user threshold) — insufficient: it can't cover a healthy-source surprising-bulk-delete the user may still want to confirm; adopted as the FLOOR, not the whole mechanism. (iv) gate outgoing too — declined for the default (owner: my deletes are exact), left as a possible future opt-in.";
        :>> consequences = "AUTHORIZES: new settings `bulkDeleteStrategy` (off|count|percent, default count) + `bulkDeleteThreshold` (default 10), parsed/validated at the persistence boundary + an Advanced-section control; a pure threshold predicate; reconcile changes — REMOVE the outgoing bulk guard + the cumulative DeleteRateGuard, gate the INCOMING delete-local batch on the predicate, and on a trip HOLD + emit the held paths for review (apply / resurrect helpers); a non-blocking review surface + a confirm modal; the pending set derived per pass. BEHAVIOUR CHANGE to the PRIMARY sync (not just mounts): a large local delete now propagates immediately (previously could be refused); a large incoming delete now HOLDS for confirmation per the user setting (default >10 files) instead of the fixed 50%/empty heuristic; below-threshold and 'Off' apply immediately. Local deletions still go to `.trash` (desktop) where the adapter supports it. This SUPERSEDES the R9-A tracked issue (issueMountDeleteGuardCalibration → resolved by this) and interacts with the composed-vaults mount scopes (same global policy). No engine schema/workflow/process/skill change ⇒ no #ProspectiveChange, no CLAUDE.md change.";
    }

    verification d0041Accept : Test {
        :>> id = "d4e5f6a7-8b9c-4d0e-af21-3c4d5e6f7081";
        :>> method = VerificationMethod::confirmation;
        :>> procedureText = "wweatherholtz proposed the mechanism (Advanced-section strategy pick: warn if >N files / >N% / off, a validated numeric control, default >10 files, and 'require acceptance before locally deleting an incoming over-threshold batch'), the AI refined it (direction split: outgoing exact / incoming gated; non-blocking review reusing the conflict pattern with Delete-vs-Keep-resurrect; drop the cumulative guard under D0007; keep the source-readiness floor), and the owner replied 'agreed on all counts, great insights. proceed' (2026-08-10) — an explicit acceptance of this design, authorizing implementation.";
    }
    part d0041AcceptR1 : TestResult {
        :>> id = "e5f6a7b8-9c0d-4e1f-b032-4d5e6f708192";
        :>> outcome = VerdictKind::pass;
        :>> judgedAgainst = "52b7163";
        :>> judgedAt = "2026-08-10";
        :>> judgedBy = "wweatherholtz";
    }
}
