// D0253 (status: the `status` field below is the truth) — A control's arming may be proven by TEST, and eight were classified by the wrong constraint
// Recorded via `keel record decision` (D0105 RMWX axis; issue054). Acceptance is a separate explicit
// human gate (method=confirmation, D0106): flip status + add the d0253Accept event on sign-off.
package ReferenceDecision0253 {
    private import EngineElement::*;
    private import EngineWork::*;
    private import EngineVerification::*;
    private import EngineRelationships::*;

    // #ProspectiveChange (D0070) - this Decision governs a process/schema change; the co-committed
    // change rides the process-change guard's hard lock.
    #ProspectiveChange part d0253 : Decision {
        :>> id = "38e3fb46-8f70-4aa8-9c18-1076d6103882";
        :>> title = "A control's arming may be proven by TEST, and eight were classified by the wrong constraint";
        :>> createdAt = "2026-08-29";
        :>> createdBy = "claudeOpus5";
        :>> status = DecisionStatus::accepted;
        :>> context = "Asked for stricter launching, verification and assurance - 'but I need real assurance' (st031) - the honest first move was to measure what the current assurance rests on rather than add to it. Four computed views, read together: `keel controls`: 9 declared controls, 1 ARMED, 8 not-machine-checkable - and `uncoveredHazards: []`, `hazardsWithADisarmedControl: []` regardless. A clean bill of health resting on one probe. `keel attestation`: 4,887 AI-judged results; of 1,203 EXERCISED claims, 5% carry a re-runnable receipt. 319 human-judged results, of which 0 ever failed. `keel verification`: 122 requirements, 84% examined and 79% exercised - but 88 reached by AI critique against 52 by test. `keel enforcement-report`: 5,986 in-loop hook fires, ZERO blocks, 72% advisory heed. `launcherFraction: unavailable - no run records yet`; `.keel/runs/` does not exist, so the launcher is fully implemented and has never been invoked. Every one of those numbers was already computable. Nothing had to be built to find this, which is itself the finding: the views existed and nobody had read them together.";
        :>> decision = "Three clauses. CLAUSE A - ARMING HAS A THIRD STATE: PROVEN-BY-TEST. A control's arming may be established by a test that exercises it, distinct from both checkable-by-view and not-checkable. `.engine/contracts/control-arming.toml` gains an optional `provenBy` naming the test file, so a reader re-derives the claim by running it instead of trusting the reason text. `checkable` continues to mean what it meant - whether `keel controls`, a read-only view, can establish arming - and is unchanged in meaning by this Decision. CLAUSE B - ctlWriteLock IS PROVEN, AND ITS OLD REASON IS KEPT. The write lock is proven to serialise by six concurrent OS processes contending through the sanctioned write path. Its previous justification stays quoted in full beside the new one rather than being replaced, because it was wrong in an instructive way and a silently corrected justification teaches nobody. CLAUSE C - THE OTHER SEVEN ARE NAMED AS UNPROVEN, NOT RECLASSIFIED. ctlPrePushBehind, ctlReverify, ctlPreWriteTiers, ctlFireLedger, ctlAuditHistory, ctlBranchProtection and ctlReleaseGateJob each need their own probe. None is reclassified by this Decision, and issue303 stays open until each has one or a stated reason no test can reach it.";
        :>> rationale = "THE SHARED ERROR, and it is worth stating precisely because it is subtle and nobody was careless. 'Not machine-checkable BY A READ-ONLY VIEW' was generalised into 'not checkable at all'. `keel controls` must not spawn processes, write files or make network calls - a view that silently performs I/O is a view you stop running - so it genuinely cannot establish most of these. A TEST may do all three. The arming question was answered against the constraints of the surface that happened to ask it, and the answer was then read as a property of the subject. WHY ctlWriteLock IS THE PROOF THAT THIS MATTERS. Its reason argued: no configuration can disarm it, so there is nothing to probe, and absence of a switch is stronger than a passing check. The first half is true. The conclusion does not follow: ruling out DISARMING says nothing about whether the lock SERIALISES, which is the property it exists for. issue184/issue185 record four concurrent `record issue` calls landing two issues with all four exiting 0 - and on that day it was equally true that no configuration could disarm it. The reasoning would have certified the exact failure it was meant to preclude. WHY THE TEST DISCRIMINATES rather than passing vacuously, which is the difference between a probe and a decoration: clobbering makes landed < exited-zero and fails the assertion; a lock refusing everything trips a second assertion, because a control that never lets anything through is stuck rather than armed; and a missing binary PANICS rather than skipping, so an unbuilt tree cannot look like a passing probe. The landed count is read from the TREE and never from the writers' exit codes - counting reported successes would have re-made the very error under test. WHY NOT RECLASSIFY THE OTHER SEVEN NOW. Because the finding is that classification without evidence is the problem, and moving seven controls into a new state on my reasoning alone would repeat it at a larger scale. Each earns the label by having a test, one at a time. COST OF NOT DECIDING. The assurance surface keeps reporting no uncovered hazards while eight of nine controls have never been observed to fire, and the next reader draws the same false comfort I did until I read four views together.";
        :>> consequences = "`keel controls` gains nothing automatically: `provenBy` is data a reader follows, not a new computed state, and `checkable` still drives the ARMED count. The census therefore still reads 1 ARMED of 9, which is CORRECT and deliberately not inflated - a test proving a property is not the view establishing it, and conflating them would rebuild the comfort this Decision removes. The honest count becomes 2 of 9 with evidence: 1 armed by view-probe, 1 proven by test. Seven remain, and issue303 tracks them. A precedent is set that arming probes live in the test suite. `.engine/tools/control_eval_probes.sh` already does this for guards - plant a defect in a throwaway worktree, assert the gate goes red - so this extends an existing shape rather than inventing one. NOT ADDRESSED HERE, and it is the largest single assurance gap in the model: the launcher has never run. Every Need about bounded, approved process launching - the human's first named area - has zero evidence behind it, and `enforcement-report` reports `launcherFraction: unavailable` rather than 'never invoked', which is the same declared-versus-armed confusion one level up. It needs its own sprint and is not folded in here.";
    }

    // acceptance event (D0121 review-queue sign-off; D0066/D0106 — human-judged, not fabricated)
    verification d0253Accept : Test { :>> id = "09f372a2-b244-4778-9fa4-1cd6752bf1a9"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0253AcceptR1 : TestResult { :>> id = "b1652cd4-6af5-4ea4-9704-d0c6ea4cc416"; :>> outcome = VerdictKind::pass; :>> judgedAgainst = "253e899"; :>> judgedAt = "2026-08-29"; :>> judgedBy = "wweatherholtz"; }
}
