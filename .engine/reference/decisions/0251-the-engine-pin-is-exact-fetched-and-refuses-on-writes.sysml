// D0251 (status: the `status` field below is the truth) — The engine pin names an exact version, the wrapper fetches and verifies it, and a skew refuses on writes
// Recorded via `keel record decision` (D0105 RMWX axis; issue054). Acceptance is a separate explicit
// human gate (method=confirmation, D0106): flip status + add the d0251Accept event on sign-off.
package ReferenceDecision0251 {
    private import EngineElement::*;
    private import EngineWork::*;
    private import EngineVerification::*;
    private import EngineRelationships::*;

    // #ProspectiveChange (D0070) - this Decision governs a process/schema change; the co-committed
    // change rides the process-change guard's hard lock.
    #ProspectiveChange part d0251 : Decision {
        :>> id = "439eb3de-7d4e-4b40-9549-36f06f239163";
        :>> title = "The engine pin names an exact version, the wrapper fetches and verifies it, and a skew refuses on writes";
        :>> createdAt = "2026-08-28";
        :>> createdBy = "claudeOpus5";
        :>> status = DecisionStatus::accepted;
        :>> context = "srProjectPinsItsEngine requires that the engine version a project declares is the one that runs, and that a mismatch REFUSES rather than warning. That is a strengthening of today's behaviour: `.engine/contracts/engine-version.toml` exists, holds an exact version string, and drives an advisory warning that pins nothing, so a project's checks are in fact whatever binary is on PATH. srWorkspacePinIsCoherent adds that projects sharing one repository must agree, because one repository is one checkout and therefore one binary. The requirement deliberately did not say HOW. Three questions were left open and put to the human as KEEL-ND fork 2, decomposed into three decisions with each option's cost stated: what the pin names, what happens when the pinned binary is not present, and which commands refuse on a skew. They selected the recommended option in all three, with no note, recorded verbatim as st030.";
        :>> decision = "Three clauses, one per decision. CLAUSE A - THE PIN NAMES AN EXACT VERSION. `engine = '0.3.0'`, not a range and not a version-plus-artifact-SHA. A range would let two clones of one tree resolve different binaries at different times, which is the precise property that makes a re-derived historical verdict disagree with the original. An artifact SHA would make a legitimate rebuild at the same version indistinguishable from tampering. CLAUSE B - ON A CACHE MISS THE WRAPPER FETCHES, VERIFIES, AND EXECS. A committed wrapper resolves the pinned version from a machine-local binary cache; on a miss it downloads THAT VERSION AND NO OTHER from the release page, verifies a committed SHA-256, and executes it. It never resolves any version other than the pinned one, and it never falls back to a binary on PATH. CLAUSE C - A SKEW REFUSES ON WRITES AND GATES, AND WARNS ON READS. Any command that records a fact or produces a verdict refuses when the running engine is not the declared one, naming both versions. Read-only computed views warn and proceed. `version` and `migrate` never refuse, because they are how a skew is inspected and repaired. THIS AMENDS D0175, and the amendment is the point of stating it rather than a footnote. D0175 accepted 'no package managers, no auto-update, no install scripts' and install from the Releases page only. Clause B introduces a fetch. It is compatible with D0175's INTENT and incompatible with a literal reading, so D0175 is superseded in part: the fetch is permitted, bounded to exactly the pinned version, and forbidden from resolving anything else.";
        :>> rationale = "WHY EXACT BEATS A RANGE, on the criterion the human was given. The question every option was scored against was whether the same tree provably produces the same gate verdict on any machine at any later time. A range fails that outright - not marginally, but by construction, since resolution depends on when it runs. This is also where the wider ecosystem lands from both directions: Gradle and Maven wrappers pin an exact distribution with no range facility at all, while Cargo and npm allow ranges in the manifest and then LOCK to exact versions, because reproducibility is what a lockfile is for. The accepted cost is real and was stated: every project bumps by hand each release, and a stale pin is invisible until someone looks. WHY FETCHING IS NOT AUTO-UPDATE, which is the whole reason clause B can coexist with D0175. Auto-update moves you off the version you asked for. This wrapper is the mechanism that makes that impossible: it resolves the pinned version, verifies it against a committed checksum, and refuses everything else. A tool that will only ever run the version your tree declares is the opposite of one that silently upgrades you. D0175's real target was uncontrolled acquisition, and a checksum-verified single-version fetch is controlled acquisition. WHY THE READ/WRITE LINE RATHER THAN REFUSING EVERYTHING. Refusing every invocation is strictly more coherent and was rejected for a reason this project has already paid for twice: an over-strict gate trains its actor to disable it. Blocking `orient` on a version skew blocks the command a person would use to diagnose the skew, which converts a small problem into a bypass. The read/write line is the narrowest cut that still makes the pin real - nothing enters the model, and no verdict is recorded, from an engine the project never declared. THE RESIDUAL, and it is on the page rather than hidden here: a read view can still be computed by a different engine, so what a reader sees may not be what the gate would say. That is accepted, and it is why the warning must be loud rather than incidental. COST OF NOT DECIDING. srProjectPinsItsEngine and srWorkspacePinIsCoherent cannot be refined into Gherkin: none of the scenarios can be written without knowing whether the pin is a version or a range, and what a miss does.";
        :>> consequences = "D0175 is SUPERSEDED IN PART by clause B. It stands on package managers, auto-update and unrestricted install scripts; it no longer forbids a wrapper that fetches exactly the pinned version and verifies it. A committed wrapper and a committed per-version checksum become project files that `keel init` must lay down, and the checksum becomes a thing that can be wrong - a new failure mode, stated: a bad committed checksum blocks everyone until corrected. `engine-version.toml` changes role from an advisory stamp to a binding declaration. Every project carrying one today begins to be held to it, so the escalation from warn to refuse must ship with a migration path rather than as a surprise. The two requirements become refinable, and Program A's remaining blocker is now only the unit-compatibility half (D0252). NOT DECIDED HERE: how a project discovers that a newer engine exists. Exact pinning is silent about that by design, and inventing a notification would be a second mechanism nobody asked for.";
    }

    // Clause B permits a fetch, which D0175 forbade on a literal reading. Recorded as a typed edge
    // rather than left as prose: D0175 stands on package managers, auto-update and unrestricted
    // install scripts, and is superseded ONLY on the single-version, checksum-verified fetch.
    #SupersedeClause dependency from d0251 to d0175;

    // acceptance event (D0121 review-queue sign-off; D0066/D0106 — human-judged, not fabricated)
    verification d0251Accept : Test { :>> id = "a2d664c7-36a2-464c-9f54-edd37de820c3"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0251AcceptR1 : TestResult { :>> id = "5a8c2787-4385-45e3-8e0b-fd4ed824d231"; :>> outcome = VerdictKind::pass; :>> judgedAgainst = "50fb6e7"; :>> judgedAt = "2026-08-29"; :>> judgedBy = "wweatherholtz"; }
}
