// D0371 (status: the `status` field below is the truth) — gateAnswersFromItsReceipt: a green gate writes a receipt keyed on every input a guard can read, and the next run whose key is equal answers from it
// Recorded via `keel record decision` (D0105 RMWX axis; issue054). Acceptance is a separate explicit
// human gate (method=confirmation, D0106): flip status + add the d0371Accept event on sign-off.
package ReferenceDecision0371 {
    private import EngineElement::*;
    private import EngineWork::*;
    private import EngineVerification::*;
    private import EngineRelationships::*;

    // #SafetyChange (D0070) - this Decision governs a process/schema change; the co-committed
    // change rides the process-change guard's hard lock.
    #SafetyChange part d0371 : Decision {
        :>> id = "7e383ec9-a6a5-4db2-b803-a93bfb193712";
        :>> title = "gateAnswersFromItsReceipt: a green gate writes a receipt keyed on every input a guard can read, and the next run whose key is equal answers from it";
        :>> createdAt = "2026-09-07";
        :>> createdBy = "claudeOpus5";
        :>> status = DecisionStatus::accepted;
        :>> context = "D0367 ranked this fourth. After the guards ran in parallel (D0368), the commit facts were cached (D0369) and the corpus was read once per process (D0370), an idle turn boundary on this host still cost 5.2-5.4 s: `keel hook stop` re-ran validate, sixty-five guards and the declared rules over a tree that, most turns, was byte-for-byte the one the previous boundary had judged green. The guards read the corpus, `.keel/actor`, the commit facts cache under `.keel/cache/` and git; none reads the wall clock (`grep now() guards.rs` finds none), `.keel/metrics/` or `target/`. Measured on this tree, shell timer: idle `keel hook stop` 5202 / 5428 ms before, 218 / 260 / 318 ms after against an equal key; `keel guard` 5081 ms with `--no-receipt`, 215 / 239 ms from the receipt, stdout identical except the one added line; `keel gate --fast .` 677 ms to 189 / 229 ms. A touched tracked file forced a full run (5549 ms) and the key returned to the receipt's after `git checkout` of that file, because git, not the mtime, says whether a tracked file equals HEAD.";
        :>> decision = "A green run of `keel guard`, `keel hook stop` or the commit gate (`workspace::gate_problems`) writes `.keel/metrics/guard-receipt.toml` carrying the KEY of the tree it judged: HEAD's full id, every `(XY, path)` entry of `git status --porcelain -z -uall` with that path's `(len, mtime)`, the relative path and `(len, mtime)` of every file under `.keel/` outside `metrics/` and `bin/`, and the binary's build commit with its own `(len, mtime)`; beside the key it stores which layers the run covered (validate, guards, rules) and each guard's name, scanned count and warnings - never a violation, because a receipt exists only for a green run. A run whose computed key is EQUAL answers from the receipt: `keel guard` prints the stored reports and one line naming the receipt's age, `keel gate --fast` prints its clean line the same way, and the turn boundary returns silently as any green turn does (D0359). The key is computed before the run and again after, and the receipt is written only when the two agree; a path whose mtime is younger than two seconds makes the key unsettled and an unsettled key is neither written nor honoured; any red run deletes the receipt; `--no-receipt` or `KEEL_NO_RECEIPT=1` forces the run; a key git cannot supply is no shortcut. The fast tier reads a receipt but never writes one - three guards are not the guard set. Because `main.rs`'s hook path and `workspace.rs`'s gate are the enforcement surface (D0209 clause 2) this is a #SafetyChange and waits for the human's word. NOT A FORK: this is the mechanism D0367 ranked fourth with its number, and a receipt changes no verdict - it is the same computation's answer, returned when its inputs are provably the same.";
        :>> rationale = "A gate must not skip; it may recognise the same question. The key is what makes recognition honest: HEAD covers every unmodified tracked file, git's own status names every file that is not, and each of those carries the fact that would change if it changed; the `.keel/` inputs and the binary are the two things outside the tree a guard reads, and both are in the key. What is excluded is excluded by argument, not convenience - `.keel/metrics/` is written by the hooks themselves at every fire and read by no guard, and `.keel/bin/` holds binaries the build id already covers. The before-and-after key refuses the one race a digest cannot see, a file changed while the run read it; the two-second bar refuses the one race a digest cannot resolve, a rewrite inside an mtime tick, and it is git's own bar. Deleting on red is what keeps a receipt from ever standing over a red tree by any path. The alternative refused is a daemon or watcher holding state between runs: it would answer the same question faster still, but its correctness would rest on the watcher having seen every write, and a missed event is a green over a red tree with nothing in the tree to show it. The receipt rests on facts the tree carries at the moment of asking.";
        :>> consequences = "An idle turn boundary costs about a quarter of a second on this host instead of five; `keel guard` and the fast gate the same when nothing has moved. A boundary right after an edit runs everything (the edited file is inside the racy window) and does not write a receipt; the boundary after it runs everything once more and writes. A project that has not ignored `.keel/` still gets receipts - its own receipt and ledger are dropped from the status entries the key reads. CI checks out no `.keel/` and always runs everything, so nothing remote answers from a local receipt. `keel status` and `keel suite` are unchanged. dcHookDaemonOnlyIfTheReceiptIsNotEnough is judged against the after number: 0.2-0.3 s is under its 1 s bar. Sprint 601 records the numbers.";
    }

    // acceptance event (D0121 review-queue sign-off; D0066/D0106 — human-judged, not fabricated)
    verification d0371Accept : Test { :>> id = "dc99cb90-1d71-41b8-a74d-bbc5ba260f95"; :>> method = VerificationMethod::confirmation; :>> procedureText = "their words, 2026-09-08, the copy-for-Claude text of the published brief with their selections marked: '[x] Ratify: a green run may answer from its receipt / [ ] Reverse it, every boundary runs everything / [ ] Discuss (answers: d0371)'"; }
    part d0371AcceptR1 : TestResult { :>> id = "75fa4a9b-6d68-4b3c-ab0e-7098fde2e8f0"; :>> outcome = VerdictKind::pass; :>> judgedAgainst = "a08f2a1"; :>> judgedAt = "2026-09-08"; :>> judgedBy = "wweatherholtz"; :>> createdBy = "claudeOpus5"; }
}
