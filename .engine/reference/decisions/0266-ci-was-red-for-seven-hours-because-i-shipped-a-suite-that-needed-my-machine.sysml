// D0266 (status: the `status` field below is the truth) — The federation suite is made hermetic, the live claim gets its token, and the missing control is that nothing checks CI after a push
// Recorded via `keel record decision` (D0105 RMWX axis; issue054). Acceptance is a separate explicit
// human gate (method=confirmation, D0106): flip status + add the d0266Accept event on sign-off.
package ReferenceDecision0266 {
    private import EngineElement::*;
    private import EngineWork::*;
    private import EngineVerification::*;
    private import EngineRelationships::*;

    // #SafetyChange (D0070) - this Decision governs a process/schema change; the co-committed
    // change rides the process-change guard's hard lock.
    #SafetyChange part d0266 : Decision {
        :>> id = "a8ac1217-ee4c-4b8a-95a6-8e19fc94a222";
        :>> title = "The federation suite is made hermetic, the live claim gets its token, and the missing control is that nothing checks CI after a push";
        :>> createdAt = "2026-08-30";
        :>> createdBy = "claudeOpus5";
        :>> status = DecisionStatus::accepted;
        :>> context = "The human asked whether the CI failure was being addressed. It was not. CI went red at 18:44 and stayed red across five pushes until they asked at 21:35 - roughly seven hours - and I did not look once. My own recorded working note says to check `gh run` after EVERY push and not to wait for GitHub's emails. I did not. THE CAUSE WAS MINE AND SINGULAR. CI was green through 15:06 and failed on every push after the federation suite landed, with the same three cases each time (8 passed, 3 failed): F4 imported from THE DEVELOPER'S library and panicked on a machine that had none. F5 built an isolated library correctly but the clone had NO GIT IDENTITY, so `publish` exported the unit and then failed to commit it - the export succeeded and the command still exited non-zero. F6 called `gh api` on a runner with no GH_TOKEN.";
        :>> decision = "THREE FIXES, one per cause. F4 IS REWRITTEN HERMETICALLY. Its claim - availability is not activation - needs no library at all: it now switches an engine-shipped unit off and on and reads `keel activation` back, asserting the deactivated unit is reported INACTIVE rather than skipped silently, and that the switch reverses. A federation claim must not depend on the operator's private state to be checkable. F5 GIVES ITS ISOLATED LIBRARY AN IDENTITY. Two `git config` calls on the clone. The failure it hit is worth keeping in view: a half-done write that reports failure is the honest outcome, and the assertion caught exactly that. F6 GETS THE TOKEN. `GH_TOKEN: ${{ github.token }}` on the test step. The alternative - declaring KEEL_FEDERATION_OFFLINE=1 in CI - is permitted by pf44 but strictly weaker: it would leave the only assertion that touches real GitHub unexercised in the one place that runs on every push. Read-only, repo-scoped, public repository.";
        :>> rationale = "WHY THIS IS A SAFETY CHANGE. It edits a CI workflow, which the keystone lock covers (D0209 clause 2) precisely so that a change to the enforcement surface cannot be made quietly. Supplying a token to a test step widens what CI can reach, and that deserves the co-committed record even though it makes the gate stronger rather than weaker. THE REAL FINDING IS NOT THE THREE BUGS. It is that nothing observed CI. The local gate is thorough - validate, 56 guards, check-engine, rules, clippy - and it passed every time, because the failing cases are environment-dependent and my environment has a library and a git identity and an authenticated gh. `keel land` reports 'landed' on a successful PUSH, which is where its knowledge stops. So the tree was green locally, the push succeeded, the command said landed, and CI was red. Every signal I look at said fine. WHY NOT 'REMEMBER TO CHECK'. That is manual vigilance, which D0047 rejects as a control, and my own memory already carried the instruction verbatim - it did not help, for seven hours. The control has to be mechanical.";
        :>> consequences = "CI green again, with the live GitHub claim actually running rather than skipped. FILED, NOT FIXED HERE (issue318): `keel land` should not report success on a push whose CI it never looked at. The honest shape is that land, having pushed, WAITS for or at minimum REPORTS the resulting run's verdict - turning 'landed' from a statement about a git operation into a statement about the tree's actual standing. Scoped as its own work because it changes what a core command means, and because doing it inside a hotfix would be exactly the kind of unreviewed enforcement change this Decision's marker exists to prevent. The three environment dependencies are named in the suite's own header, so the next case written there inherits the lesson rather than rediscovering it.";
    }

    // acceptance event (D0121 review-queue sign-off; D0066/D0106 — human-judged, not fabricated)
    verification d0266Accept : Test { :>> id = "0ffe8fd9-cdfa-40c2-965a-08fc15854c95"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0266AcceptR1 : TestResult { :>> id = "fd5b4e79-2dea-4c40-989c-9b317627f72c"; :>> outcome = VerdictKind::pass; :>> judgedAgainst = "8265554"; :>> judgedAt = "2026-08-30"; :>> judgedBy = "wweatherholtz"; }
    part d0266AcceptR2 : TestResult { :>> id = "0a28544d-ebb8-4178-9916-67dab5189413"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences guard count renumbered 9 to 8 at 429fc87 - editorial, the agreed substance unchanged. Their standing words, verbatim: 'issues raised are automatically accepted. they can be customizedly changed post-fact.'"; }
}
