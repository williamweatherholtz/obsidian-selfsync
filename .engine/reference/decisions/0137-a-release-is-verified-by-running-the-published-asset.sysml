// D0137 — A release is not published until a DOWNLOADED asset has been run and confirmed to
// self-identify as the tagged version and commit. Closes the gap that let three releases ship
// verified only by the existence of files at a URL (issue092).
// #ProspectiveChange (D0070): the three prior releases stay valid records; the stricter check is forward.
package ReferenceDecision0137 {
    private import EngineElement::*;
    private import EngineWork::*;
    private import EngineVerification::*;
    private import EngineRelationships::*;

    #ProspectiveChange part d0137 : Decision {
        :>> id = "7c2a4e19-83bd-4f06-91e7-5da60c38b214";
        :>> title = "D0137: a release counts as published only once a downloaded asset reports the tagged version and commit";
        :>> createdAt = "2026-08-14";
        :>> createdBy = "claudeOpus5";
        :>> status = DecisionStatus::accepted;
        :>> context = "issue092, found while answering an ambiguous one-word report ('not working?') by verifying the thing downstream ACTUALLY RUNS rather than the thing on my disk. `relTagPublish` (D0135) required 'Verify the workflow succeeded and the assets are attached' — a condition satisfied by a green workflow plus a non-empty asset list. So for v0.2.0, v0.2.1 and v0.2.2 the verification consisted of confirming that files existed at a URL, and NO published asset was ever downloaded or executed. Every behavioural claim made about those releases was measured on a LOCAL build and attributed to the published one, with nothing establishing the two were the same artifact. The gap was not hypothetical: the first actual download exposed that the binary could not report its own version (issue091), so two downstream projects blocked on issue089/issue090 had no way to confirm whether they were running the fix — and neither did I. The process argues against itself in `relGate`: 'A release is the one artifact that cannot be quietly re-verified later: downstream users have the binary.' That reasoning applies to the PUBLISHED BINARY, not only to the tree that was tagged — the tree is what you still have, the asset is what they get.";
        :>> decision = "(A) `relTagPublish` is extended: after confirming the workflow succeeded and the assets are attached, OBTAIN a published asset from the Release and confirm `keel version` reports the tagged version and the tag's commit. (B) A mismatch means the release is NOT published — fix and re-tag rather than recording it, so a bad asset can never acquire a `Release` fact. (C) The check is stated as producing part of the step's artifact, so the produced artifact is now 'a published Release with per-platform binaries, one of which has been downloaded and confirmed to self-identify', making the verification part of what the step DELIVERS rather than an optional diligence. (D) The release skill carries the concrete commands plus two new anti-patterns: verifying a release by checking that assets exist, and claiming behaviour measured on a local build. (E) This is possible only because `keel version` now exists (D0137 depends on the v0.2.3 work); before it, the asset had no way to identify itself, which is why the two were delivered in sequence rather than together.";
        :>> rationale = "The distinction being enforced is between 'the file is there' and 'the right thing is there', and only the second is a verification. Everything the old check could pass — an asset built from the wrong ref, a stale or partially-uploaded artifact, a cross-compiled target that does not execute, a binary that cannot state its own build — fails the new one, and every item on that list is a real failure mode of a CI publish rather than a theoretical one. The cost is one download per release, which is negligible against the failure it prevents: a release is the single artifact whose defects are discovered by other people. ALTERNATIVES: (i) leave it and rely on CI being trustworthy — REJECTED, CI being green says the build succeeded, not that the attached bytes are the build, and this is exactly the class of assumption the engine refuses elsewhere (state is computed, never asserted); (ii) add a CI step that self-checks the asset before upload — REJECTED as insufficient alone, because it verifies the artifact on the producing side and the whole point is to verify what a CONSUMER receives, which is the only side that matters and the only side that was never checked; it remains a reasonable ADDITION later; (iii) verify all three platform assets — REJECTED for now as disproportionate: the Windows and Linux hosts available here cannot execute the macOS-arm64 binary, so requiring it would make the step unsatisfiable and invite exactly the bypass habit that cost eight commits earlier in this sitting (issue081); one asset plus a green matrix build is the honest maximum. GENERAL LESSON: a verification step must name the OBSERVATION it makes, not the condition it hopes for — 'the assets are attached' describes a hoped-for state and was satisfiable without observing anything about them.";
        :>> consequences = "`relTagPublish` in .engine/processes/deploy.sysml gains the obtain-and-run requirement and a stronger producedArtifact; .engine/skills/release/SKILL.md gains the commands and two anti-patterns. issue092 resolves. Releases from v0.2.3 forward carry this evidence — v0.2.3 was in fact verified this way before the Decision was authored (asset reported keel 0.2.3 / build commit b006f10, matching the tag), so the process change codifies a practice already demonstrated rather than an untested one. Marked #ProspectiveChange (D0070): the v0.2.0/v0.2.1/v0.2.2 Release facts remain valid as records of what shipped, and are NOT retro-failed for missing evidence the process did not then require — the forward-only grandfathering rule (issue068). Acceptance state is carried by `status` plus the d0137Accept event.";
    }

    verification d0137Accept : Test { :>> id = "3f8b1d05-6ea7-4c93-88b1-0c7e5a2946df"; :>> title = "Human acceptance of d0137"; :>> createdAt = "2026-08-14"; :>> createdBy = "claudeOpus5"; :>> method = VerificationMethod::confirmation; :>> procedureText = "wweatherholtz accepted this specific change, 2026-08-14: '#2 accepted. proceed with backlog please'. Item #2 as presented was, verbatim: 'One decision is genuinely blocking frontier #1. dcReleaseAssetVerification (issue092) needs your acceptance because it edits a process definition: extend relTagPublish so a release is not published until a downloaded asset is confirmed to self-identify as the tagged version. Three releases were verified by confirming files existed at a URL.' The presentation named the process definition being edited, the specific condition being added, and the defect motivating it, and the reply accepted that item by number with no qualification. Nothing here is inferred from the work having been done: the change was PROPOSED and deliberately left unapplied across two turns pending this sign-off."; }
    part d0137AcceptR1 : TestResult { :>> id = "9a41c6b8-2d70-4e15-b3fa-71e08d59c247"; :>> outcome = VerdictKind::pass; :>> judgedAgainst = "bd2ebfa"; :>> judgedAt = "2026-08-14"; :>> judgedBy = "wweatherholtz"; }
}
