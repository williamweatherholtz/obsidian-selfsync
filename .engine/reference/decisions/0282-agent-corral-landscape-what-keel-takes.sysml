// D0282 (status: the `status` field below is the truth) — Agent-corral landscape: fifteen projects in three families, six ideas adopted in rank, two declined with reasons
// Recorded via `keel record decision` (D0105 RMWX axis; issue054). Acceptance is a separate explicit
// human gate (method=confirmation, D0106): flip status + add the d0282Accept event on sign-off.
package ReferenceDecision0282 {
    private import EngineElement::*;
    private import EngineWork::*;
    private import EngineVerification::*;
    private import EngineRelationships::*;

    part d0282 : Decision {
        :>> id = "644d75b2-9c71-4d27-a48b-80c22ba15f5e";
        :>> title = "Agent-corral landscape: fifteen projects in three families, six ideas adopted in rank, two declined with reasons";
        :>> createdAt = "2026-09-02";
        :>> createdBy = "claudeOpus5";
        :>> status = DecisionStatus::accepted;
        :>> context = "An unauthenticated commenter on the standing-consent override thread (issue #29, 2026-09-02) asked whether keel records consent scope and rule revision on each auto-accepted Decision, and linked an in-path MCP authorization product. The recording Action refused to record the comment - the login is not a declared decider - which was the control working. The human then asked for a spike: what are other public and private projects doing to manage and corral AI agents, and what can keel learn. Run through adversarial-panel-review (D0187, def pin 64f2dea) as three parallel web-enabled lenses: in-path intermediaries, in-repo and harness-level discipline, runtime-formal and ledger. Fifteen projects examined with URL-cited evidence plus six runners-up; every claim the lenses made about keel's OWN state was then checked against source before it became a finding, and one (capture completeness) was narrowed on that check. Full reports: docs/reviews/agent-corral-landscape-2026-09-02.md; knowledge record .tracking/knowledge/agent-corral-landscape-2026-09-02.sysml.";
        :>> decision = "Adopt six ideas as backlog items in this rank, which is their declaration order: (1) dcAcceptanceBindsToTheText - an acceptance compares the accepted fields at its judgedAgainst SHA with HEAD, and drift computes as suspect, resolving issue341; (2) dcConsentIsScopedAndExpires - a costed FORK proposal on whether standing consent binds to the revision it was granted under and expires, resolving issue342; (3) dcExternalFactGate - a TestResult class CI verifies against a real run id and SHA, which the agent cannot assert; (4) dcSkillsRouteBehaviourally - real-model tests that a skill fires, tracked as an indicator; (5) dcUntrustedTaintClosure - guard 56 follows the untrusted label through derivation to privileged sinks; (6) dcCommitDeltaView - a computed delta view rendered where the human's authority already lives. Feed two mechanisms into the existing fork dcProcessStepsBindToChecks rather than opening new items: a closed predicate registry a ProcessStep binds to by name (AgentSpec), and a parseable requirement grammar a guard can refuse (EARS, as Kiro uses it). Decline two: SMT narrowing-versus-expansion over guard predicates (Progent), and hook fire-ledger reconciliation in CI (halo-record) - recorded as knowledge, not as work.";
        :>> rationale = "WHAT CONVERGED across three independent lenses, which is why the ranking is defensible rather than taste. First, nobody checks substance: in-path products answer whether a call may happen, in-repo products whether an artifact exists, formal systems whether a pending call satisfies a predicate - the only partial exceptions are PAuth recomputing an operand at the server and Beads closing a gate on a real CI run, and those two are ranks 1 and 3. Second, standing consent is the artifact the field has learned to distrust: Entra time-bounds grants and re-attests on extension, CapLease proves single-use tokens still replay under agent retry without durable confirmation state, the IETF compliance-receipts draft mandates a policy digest and expiry. keel's D0207 is the outlier, and the human chose it knowingly, so it is a fork with costed options (rank 2), not a defect with one fix. Third, keel's three legs - computed state, blocking guards at the harness boundary, independent re-derivation on infrastructure the agent cannot modify - exist together nowhere else; Beads has computed state with a gitignored database and an actor that defaults to unknown, Kiro has blocking hooks the agent can edit, agentgateway and ToolHive have separation without any model of the work. That is why the adopted ideas are all additions to what keel has rather than replacements for it. WHY RANK 1 IS RANK 1: it is one guard, it closes a hole keel already closes for evidence and confirmations, and the owner of most Decisions is the AI that proposed them, so D0108 ownership permits exactly the edit the guard would catch. WHY THE TWO DECLINES: Progent's decision procedure is correct in principle but encoding 57 guard conditions as SMT formulae rewrites the guard layer for a defect class not yet observed here - a loosened predicate landing without a signed Decision - and the audit already catches deletion and downgrade; it becomes work the day that class lands. Capture completeness was checked and found narrower than the lens claimed: CI re-derives validate and every guard on the tree, so a bypassed hook cannot hide dishonest state, only a skipped advisory, and the fire-ledger is machine-local by design (D0180). WHAT THE TRIGGER WAS: an MCP intermediary whose own page says the in-path proxy is on the roadmap - today an MCP server the agent may simply not call. Its ledger is real, its enforcement is not yet, and its question was legitimate regardless.";
        :>> consequences = "Six ranked items enter the frontier; two land above the schema fork because they are cheap and close consent-integrity holes, four sit at the tail. issue341 and issue342 are triaged on arrival. dcProcessStepsBindToChecks (issue336), which had a problem statement and no mechanism, now has two concrete mechanisms to cost in its proposal. The knowledge record pins the process definition version and links every produced item, so which-version-produced-this is answerable for this spike exactly as for evidence. The human receives one page with the fifteen, the six, and the two declines, and decides nothing on this Decision - the decisions that are theirs are inside rank 2 and issue336, and both will arrive as forks with per-option cost. What this Decision does NOT claim: that any of the six is built, or that the landscape was exhaustive - fifteen verified projects and six runners-up, with the exclusions and their reasons listed so the sweep can be audited.";
    }

    // acceptance event (D0121 review-queue sign-off; D0066/D0106 — human-judged, not fabricated)
    verification d0282Accept : Test { :>> id = "5ac5472e-c58c-4ffd-9ff5-8a90e02ee20b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0282AcceptR1 : TestResult { :>> id = "293efeb4-b6ad-4260-8d66-78db7934bc3e"; :>> outcome = VerdictKind::pass; :>> judgedAgainst = "7a7f066"; :>> judgedAt = "2026-09-02"; :>> judgedBy = "wweatherholtz"; }
}
