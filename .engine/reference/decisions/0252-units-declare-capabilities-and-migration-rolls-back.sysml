// D0252 (status: the `status` field below is the truth) — A unit declares the capabilities it needs, not a version range, and a migration that cannot finish rolls back
// Recorded via `keel record decision` (D0105 RMWX axis; issue054). Acceptance is a separate explicit
// human gate (method=confirmation, D0106): flip status + add the d0252Accept event on sign-off.
package ReferenceDecision0252 {
    private import EngineElement::*;
    private import EngineWork::*;
    private import EngineVerification::*;
    private import EngineRelationships::*;

    // #ProspectiveChange (D0070) - this Decision governs a process/schema change; the co-committed
    // change rides the process-change guard's hard lock.
    #ProspectiveChange part d0252 : Decision {
        :>> id = "bc71ed1f-5f7c-446b-92d6-0bed67604215";
        :>> title = "A unit declares the capabilities it needs, not a version range, and a migration that cannot finish rolls back";
        :>> createdAt = "2026-08-28";
        :>> createdBy = "claudeOpus5";
        :>> status = DecisionStatus::accepted;
        :>> context = "srUnitDeclaresEngineRange requires that a portable unit carry a declared compatibility statement, and that installing it into an engine outside that statement fail AT INSTALL, naming both sides, leaving no file written. srUnitMigrationPath requires that a unit behind the engine have a path forward that reports per file what it cannot migrate, 'never partially migrating and reporting success'. Both were written without saying HOW compatibility is expressed, or what state a failed migration leaves behind. Put to the human as fork 3, decomposed into two decisions; they selected the recommended option in both, verbatim as st030. The material fact that shaped the recommendation was found in the code rather than assumed: `keel-cli/src/process_cmd.rs:493` already implements a capability handshake (D0183/K8). It reads the guards a unit declares, diffs them against THIS binary's guard inventory, and REFUSES on missing teeth - or proceeds loudly under `--degrade` with a recorded Issue. The rules slice does the same for declared rules. So capability-based compatibility is not a new mechanism to build; it is a half-built one to finish.";
        :>> decision = "Two clauses. CLAUSE A - A UNIT DECLARES CAPABILITIES, NOT A VERSION RANGE. The existing guard-and-rule handshake is EXTENDED to the rest of what a unit can depend on - the schema types it instantiates and the commands it invokes - and that declaration is the compatibility statement. An install whose target engine lacks a declared capability refuses at install time and names the missing capability, not a version number. No `engineRange` or `minEngine` field is introduced: a version range would sit beside the handshake and could contradict it, which is two sources of truth for one question. CLAUSE B - A MIGRATION THAT CANNOT FINISH ROLLS BACK ENTIRELY. On any un-migratable file the unit is left EXACTLY as it was, and the command reports per file what blocked it and why. No partially-migrated state is created, so no surface has to model or honour one, and a half-migrated unit can never be installed because it never exists.";
        :>> rationale = "WHY CAPABILITIES BEAT A RANGE, on the criterion put to the human: whether the declaration states what the unit actually depends on, or a number standing in for it. A library's version IS its API contract, which is why ranges work in Cargo, npm and pip. A keel unit's dependency is not shaped like that - it needs specific guards to exist, specific schema types to be declared, specific commands to be present. Naming those says the true thing, and the refusal it produces names what is missing rather than printing two numbers a reader must interpret. It also survives renumbering: 0.9 to 1.0 breaks no unit that did not actually depend on something removed. THE HONEST WEAKNESS OF THE RANGE OPTION, which is what settled it: nobody can know the upper bound at authoring time. An author either guesses pessimistically, and units expire while still working, or optimistically, and the refusal never fires when it should. A declaration that cannot be authored correctly is not a control. WHY ROLLING BACK BEATS KEEPING FLAGGED PARTIAL PROGRESS. The criterion was whether a unit that cannot fully migrate can nonetheless end up installed somewhere. Rolling back makes that unreachable with no new state to model; keeping partial progress needs a flag that every surface must honour, and a state that exists is a state something must check - the sort of obligation that is honoured on the day it ships and forgotten by the third surface added afterwards. keel's own write path settled the same shape at smaller scale: writes are temp-file-then-rename and a writer that cannot take the lock fails loudly, on the recorded reasoning that a refused write is recoverable and a lost one is not. A rolled-back migration is a refused write at unit scale. THE ACCEPTED COSTS, both stated on the page and both real. Capabilities: more to declare per unit, and capability names become an interface that cannot be renamed casually - a renamed guard breaks every unit that named it. Roll-back: one stubborn file blocks nine that would have migrated fine, and the nine are migrated again on the next attempt. WHAT NEITHER CLAUSE CAN EXPRESS, and it is worth knowing rather than discovering: neither a capability set nor a version range can say 'works, but subtly wrong on 0.4'. Behavioural drift with no missing capability passes both. That gap is real and is not closed here. COST OF NOT DECIDING. srUnitDeclaresEngineRange and srUnitMigrationPath cannot be refined, and the library (D0250) cannot safely publish units whose compatibility nobody can state.";
        :>> consequences = "The D0183/K8 handshake becomes the compatibility mechanism rather than a guard-set check, and grows to cover schema types and commands. Its existing refusal behaviour and its `--degrade` escape are inherited rather than redesigned. Capability names become a public interface. Renaming a guard, a schema type or a command is now a breaking change for units that declare it, which was previously an internal matter. This is a real cost of clause A and is recorded so a future rename is not made casually. No `engineRange` or `minEngine` field is added to `unit.toml`. A downstream project expecting one will not find it; the compatibility statement is the capability list. Migration gains no new unit state. `keel migrate` and any unit-level migration report per file and leave the unit untouched on failure. STILL NOT CLOSED, and named rather than left for a reader to find: behavioural incompatibility with no missing capability is undetectable by this mechanism. If that class shows up in practice, a version range returns as a supplement - and it would then be the second source of truth this Decision declined, which is a trade to make consciously rather than by drift.";
    }

    // acceptance event (D0121 review-queue sign-off; D0066/D0106 — human-judged, not fabricated)
    verification d0252Accept : Test { :>> id = "c8e212bc-70d5-4050-a43d-b990e60e0f1b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0252AcceptR1 : TestResult { :>> id = "1f7add76-2ec2-4b0c-9340-2848459b7f49"; :>> outcome = VerdictKind::pass; :>> judgedAgainst = "897e677"; :>> judgedAt = "2026-08-29"; :>> judgedBy = "wweatherholtz"; }
}
