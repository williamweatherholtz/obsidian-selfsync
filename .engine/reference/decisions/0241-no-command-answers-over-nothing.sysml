// D0241 (status: the `status` field below is the truth) — a command that reads a model refuses rather than answering over nothing
// Recorded via `keel record decision` (D0105 RMWX axis; issue054). Acceptance is a separate explicit
// human gate (method=confirmation, D0106): flip status + add the d0241Accept event on sign-off.
package ReferenceDecision0241 {
    private import EngineElement::*;
    private import EngineWork::*;
    private import EngineVerification::*;
    private import EngineRelationships::*;

    part d0241 : Decision {
        :>> id = "1c624277-53a9-435f-b09f-45f4966ff65f";
        :>> title = "a command that reads a model refuses rather than answering over nothing";
        :>> createdAt = "2026-08-27";
        :>> createdBy = "claudeOpus5";
        :>> status = DecisionStatus::accepted;
        :>> context = "D0234 made `validate` REFUSE a non-project rather than report a clean tree over nothing (issue269). That refusal was applied to `validate` ALONE, and the project predicate had exactly one non-test call site. So at a WORKSPACE ROOT — a repository holding projects with none at the root — every other model-reading command answered about an empty model and called it an answer. Measured in a two-project workspace full of work, before this change: * `orient` exited 0 with an empty ready list, zero outstanding, 100 percent decomposed and `answerStatus: COMPUTED` — and `orient` is the surface CLAUDE.md makes the AI's ONLY legitimate state read, explicitly forbidding prose substitutes. It returned nothing-to-do for a repo full of work. * `whats-next` printed 'COMPUTED-EMPTY — this is an answer, not a failure' over ZERO items. * `check-engine` printed '.engine instance files validated clean' over zero files, while being a BLOCKING step in this repository's own commit gate. Separately, `find_repo_root` had no git boundary while workspace discovery did, so standing in a directory nested under an unrelated keel project, `keel validate` with no argument walked OUT of the repository and validated the OUTER repo's project — reporting it clean.";
        :>> decision = "A command that reads a MODEL refuses when its resolved root is not a keel project, naming the projects the repository does hold. The refusal lives in `workspace::require_project` and is called from every root-resolution path; `find_repo_root` stops ascending at the repository boundary. `sync` and `land` are deliberately NOT covered: they are repository-scoped by design, and `projects` and `gate --workspace` are workspace-level surfaces that must answer at a workspace root.";
        :>> rationale = "ALTERNATIVES: (A) aggregate across the discovered project set instead of refusing — rejected for now, and it is the more useful answer eventually: `orient` over three projects is a real thing to want. But aggregation has to decide how to MERGE ranked frontiers from independent models, and inventing a cross-project priority order silently is worse than refusing, because declaration order IS priority (D0052) and there is no declared order ACROSS projects. Refusing names the projects so the caller chooses; aggregating would answer a question nobody asked. (B) refuse in each command — rejected: it is a per-command edit to forget, and forgetting is exactly how one refusal covered one command. (C) a shared precondition at every root-resolution path — CHOSEN. CRITERIA: can a new command be added without the check; does it change any answer inside a project; and does it ever answer a question the caller did not ask. THE PART WORTH RECORDING: (C) was implemented at what I believed was the single chokepoint — `root_arg`, which 41 commands already call and which already had an error channel. Nine commands then refused and THREE still exited 0, because they resolve their roots elsewhere: `cmd_view0` for the zero-argument views, `repo_arg` plus nothing for `verification`, and `attestation` inside its own module. Sweeping every model reader found the first two; a TEST sweeping them found the third, and the third turned out to be a worse defect than the one being fixed — `indicators` accepted `--root` only, so a POSITIONAL root was silently ignored and the view was computed against whatever project the process happened to be standing in. `keel indicators <someWorkspace>` reported real numbers about a DIFFERENT project and exited 0. That is not a zeroed green; it is a confident wrong answer, which is the class this engine exists to remove. So the criterion 'can a new command be added without the check' is not yet satisfied by construction, only by a test that sweeps. That is stated rather than claimed away.";
        :>> consequences = "Twenty-two model-reading commands refuse at a workspace root and all of them still work inside a project — both directions measured, and held by `keel-cli/tests/no_green_over_nothing.rs`, which sweeps the set and asserts the refusal NAMES the projects, because a refusal the reader cannot act on is only half a fix. `root_arg` now VALIDATES as well as parses. Its unit test used synthetic paths (`/r`) that are not projects, so the test was updated to pass a real project root — the assertions' intent, that the positional is found around a declared flag, is unchanged, and a new assertion pins the added half: an existing path that is not a project is refused. `indicators` now takes a positional ROOT like every other view, keeping `--root` for compatibility. find_repo_root's boundary changes one more behaviour worth naming: from a directory that is inside no project and inside no repository, commands now say 'no .engine/ found ... the search stops at the repository boundary' instead of silently adopting a project from further up the filesystem. NOT done, and the better answer eventually: aggregation. `orient` across a workspace is a real want, and it needs a declared cross-project order to be honest. Refusal is the correct interim because it is never wrong; aggregation invented in silence would be.";
    }

    // acceptance event (D0121 review-queue sign-off; D0066/D0106 — human-judged, not fabricated)
    verification d0241Accept : Test { :>> id = "ab25c6d7-9599-4bb3-a6ba-7fd92f459757"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0241AcceptR1 : TestResult { :>> id = "e18e4d33-2b99-4899-bbb5-9d82f9dd359d"; :>> outcome = VerdictKind::pass; :>> judgedAgainst = "20ba134"; :>> judgedAt = "2026-08-27"; :>> judgedBy = "wweatherholtz"; }
}
