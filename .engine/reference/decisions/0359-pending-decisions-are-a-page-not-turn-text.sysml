// D0359 (status: the `status` field below is the truth) — pendingDecisionsArePublished: the stop hook says nothing about outstanding decisions, and the queue is surfaced only as the published page
// Recorded via `keel record decision` (D0105 RMWX axis; issue054). Acceptance is a separate explicit
// human gate (method=confirmation, D0106): flip status + add the d0359Accept event on sign-off.
package ReferenceDecision0359 {
    private import EngineElement::*;
    private import EngineWork::*;
    private import EngineVerification::*;
    private import EngineRelationships::*;

    // #ProspectiveChange (D0070) - this Decision governs a process/schema change; the co-committed
    // change rides the process-change guard's hard lock.
    #ProspectiveChange part d0359 : Decision {
        :>> id = "84b3d6fc-9268-475f-a1ec-477d51782606";
        :>> title = "pendingDecisionsArePublished: the stop hook says nothing about outstanding decisions, and the queue is surfaced only as the published page";
        :>> createdAt = "2026-09-06";
        :>> createdBy = "claudeOpus5";
        :>> status = DecisionStatus::accepted;
        :>> context = "D0351 put one line at the end of every green turn: the count of proposed Decisions, their id range, how to accept, and their short names. It replaced a worse nag (D0269) and it was the owner's own format. It has now run for a day against a queue that did not move, and the owner's verdict on it is that the text repeats without carrying anything new: their words, 2026-09-06, 'I don't want stop says text anymore. remove. I'm interested in a post-analysis, like an AI skill that assesses if there are outstanding decisions and posts the exec summary if so, but not repetitive prose anymore.' The failing property is not accuracy - the line was accurate every time - it is that a per-turn restatement of an unchanged fact is read once and skipped thereafter, which is the same blindness the warning-count line trains. Meanwhile the channel that CAN carry a decision - the published brief, one section per pending item with the stake, the options and their costs, the recommendation and the falsifier - is produced by a process (decision-surfacing, D0269) whose own text still instructs me to re-surface the link every turn and to lead every response with it. Both surfaces were repeating; only one of them can actually be decided from.";
        :>> decision = "Outstanding decisions are surfaced only as the published decision page, produced by a post-analysis at the end of substantive work: the stop hook emits nothing about them on a green tree, and the decision-surfacing skill assesses the pending set, republishes the brief to the same URL when that set has changed, links it once when it does, and says nothing at all when it has not. NOT A FORK: the alternative shapes were weighed and none survives the owner's instruction - keeping a shorter line, or firing the line only when the set changes, are both still turn text, which is what they asked to remove; and dropping the channel entirely would leave a queue nobody is pointed at, which is the D0269 failure this project has already had once.";
        :>> rationale = "The line and the page are not two views of the same thing. A count tells the reader that something waits; a brief lets them decide it. Repeating the count next to a page that already exists spends attention on the surface that cannot resolve anything, and trains the reader past the one that can. Removing the line is therefore not a loss of oversight as long as the page is genuinely refreshed - which is why the same change binds the skill to a post-analysis with a state test, rather than to a habit of mentioning. The state test is what makes silence honest: nothing is said because the published set matches the pending set, not because the turn ended quietly. The residual is stated plainly rather than hidden: no gate can read conversational output, so nothing MAKES the post-analysis run - it is the same class as the verify-before-asserting clause (D0151), and the honest control available is that the skill's assessment is one computed command whose answer is checkable by anyone reading the page against `keel orient`.";
        :>> consequences = "A green turn ends silent again, as it did before D0351. `keel orient` remains the machine-readable answer to what waits - pendingAcceptances is already in its output - so nothing is lost to automation. The decision-surfacing skill changes shape: it stops instructing me to lead every response with the link and to re-surface every turn, and instead runs as a post-analysis that publishes and links only on change. The brief's computed-facts script and its chart primitives move out of a session scratchpad into `scripts/exec_brief/`, because a process that cannot be re-run by the next session is not a process - it is a memory, and this project does not keep those. `stop_advisory_is_one_line` is replaced by a test pinning the silence, so the removal cannot be undone by accident. WHAT THIS DOES NOT CHANGE: the acceptance controls themselves - the quoted word, the read-back, the device-bound tap - all stand exactly as they are, and standing consent is still scoped as D0337 left it.";
    }
    #SupersedeClause dependency from d0359 to d0351;

    // acceptance event (D0121 review-queue sign-off; D0066/D0106 — human-judged, not fabricated)
    verification d0359Accept : Test { :>> id = "2032bab1-c34d-4262-8903-e96d52f71b6a"; :>> method = VerificationMethod::confirmation; :>> procedureText = "their words: 'I don't want stop says text anymore. remove. I'm interested in a post-analysis, like an AI skill that assesses if there are outstanding decisions and posts the exec summary if so, but not repetitive prose anymore.'"; }
    part d0359AcceptR1 : TestResult { :>> id = "8091031b-fc4c-4076-9410-fe95c88d31f4"; :>> outcome = VerdictKind::pass; :>> judgedAgainst = "3dd4c2c"; :>> judgedAt = "2026-09-06"; :>> judgedBy = "wweatherholtz"; :>> createdBy = "claudeOpus5"; }
}
