// D0449 (status: the `status` field below is the truth) — renderFamilyFoldsIntoRender: diagram, report and decision-card become sub-verbs of keel render; the three top-level names are removed in the same commit as their call sites
// Recorded via `keel record decision` (D0105 RMWX axis; issue054). Acceptance is a separate explicit
// human gate (method=confirmation, D0106): flip status + add the d0449Accept event on sign-off.
package ReferenceDecision0449 {
    private import EngineElement::*;
    private import EngineWork::*;
    private import EngineVerification::*;
    private import EngineRelationships::*;

    // RESEARCH: Measured 2026-09-11 against .engine/cli/commands.sysml and keel-cli/src/main.rs at 1419069 (re-runnable: the census scripts under the session scratchpad read the CliCommand facts and grep the tree for keel followed by a family verb). The rendering family holds six facts: render, diagram, report, decision-card (all reads, stable) and deck, serve (both effects; not folded, they are the console and the deck and each writes through the API). Call sites of the three folded verbs outside target/: engine-authored surface 24 (skills, processes, docs, contracts, views), .claude generated 10, root docs 1, Rust source 5, Rust tests 2, .tracking records 16 (not rewritten: a record names the commands that existed when it was written, sprint 512 review pass 2). keel show hardening helpCoverage.dispatched reads 72 before the fold. keel diagram . is already keel render model byte for byte in intent - render_html routes model to diagram_html - but two runs of keel diagram . against the same tree differ in element order (same byte count, 6557881), so the graph output is not deterministic run to run and its baseline comparison is on sorted content, not raw bytes; report and decision-card are compared byte for byte.
    // #ProspectiveChange (D0070) - this Decision governs a process/schema change; the co-committed
    // change rides the process-change guard's hard lock.
    #ProspectiveChange part d0449 : Decision {
        :>> id = "f28653ba-7fc1-4b8c-8ae7-6077c7886e53";
        :>> title = "renderFamilyFoldsIntoRender: diagram, report and decision-card become sub-verbs of keel render; the three top-level names are removed in the same commit as their call sites";
        :>> createdAt = "2026-09-11";
        :>> createdBy = "claudeOpus5";
        :>> status = DecisionStatus::accepted;
        :>> context = "d0399 option A, the human's own word on 2026-09-11, folds five CLI families into their routers, one breaking transform each in the shape sprint 512 established for the lens family (D0273): a D0067 transform, a byte-equality baseline captured from the pre-fold binary, call-site rewrites in the SAME commit, no alias window. This Decision fixes the mapping for the smallest family, rendering, so the transform has a stated target to hold to and the reader of keel --help has one verb for everything that draws. The render verb already takes a first positional that is either a declared view name or the reserved word model, so the fold is an extension of a router that exists, not a new one.";
        :>> decision = "The rendering family folds into keel render. keel diagram [ROOT] becomes keel render model [--root ROOT]; keel report <kind> [--html] [--trend] becomes keel render report <kind> [--html] [--trend]; keel decision-card [NAME] [--proposed] becomes keel render decision-card [NAME] [--proposed]. The three top-level names diagram, report and decision-card are REMOVED from the dispatch, from COMMAND_NAMES, from the CliCommand facts and from cli_facts.rs, and the render fact's invocation names the three sub-verbs; deck and serve keep their names because they write. render resolves its first positional in a fixed order - the reserved words model, all, whole, report, decision-card, then control-structure, then a declared view - and a test in the Rust suite holds that no declared .view.toml is named a reserved word, so a view can never shadow a sub-verb silently. The report and decision-card arms are MOVED verbatim into the router, their functions untouched, and the criterion is byte equality against outputs captured from the pre-fold binary: every report kind with and without --html and the decision-card outputs compared raw; the graph compared on sorted content because the pre-fold diagram is itself not deterministic run to run, which is recorded as its own Issue rather than folded into this change. Every call site under .engine (skills, processes, docs, contracts, views, tools), .claude, the root docs, the Rust source and tests is rewritten by the committed transform or by hand in the one commit that removes the names; .engine/decisions and .tracking are not rewritten. NOT A FORK: d0399 option A chose the course; this Decision states the mapping that course lands on for one family.";
        :>> rationale = "One verb for everything that draws is what a newcomer expects and what d0399 A asked for: render already meant that for declared views, and diagram was a second spelling of render model with nothing of its own. The order of resolution is fixed and tested because the alternative - a declared view named report shadowing the sub-verb, or the reverse - is a silent wrong answer, the class sprint 512 found in the console view binder and caught only by a unit test. The three names are removed rather than aliased under D0273's own rule: an alias window is a tree in which a skill names a command that will disappear, and no gate reads a deprecation. Byte equality is the criterion because a consolidation that changes an answer is a rewrite wearing a rename's clothes; the one output that cannot be compared raw is not exempted but measured on the shape that can be compared, and the nondeterminism it exposes becomes a tracked Issue.";
        :>> consequences = "One sprint, two points: the transform under .engine/tools/migrations/ with a dry run that reconciles counts before --apply, the dispatch and cli_surface and cli_facts edits by hand, the reserved-word test, and the byte comparison against the captured baseline. keel show hardening helpCoverage.dispatched falls from 72 to 69 and the sprint's implement gate reads the number back. CLAUDE.md section 2 and guards.md name the new spellings in the same commit. Downstream projects holding skills that name keel report or keel diagram must update engine and skills together, which the D0252 clause A handshake makes visible by name. The remaining four families of d0399 A follow under their own Decisions; this one lands nothing for them.";
    }

    // D0303 layering: the mapping for one family under the program d0399 option A chose
    #DependsOn dependency from d0449 to d0399;

    // acceptance event (D0121 review-queue sign-off; D0066/D0106 — human-judged, not fabricated)
    verification d0449Accept : Test { :>> id = "6492faa2-00a6-4950-b8a2-d9cd5eb589f3"; :>> method = VerificationMethod::confirmation; :>> procedureText = "PLAN-COVERED under d0399 step 'rendering becomes keel render <what>': the human signed the plan itself and this enumerated step does not re-ask (D0375 option C / D0396). The plan's judge: wweatherholtz."; }
    part d0449AcceptR1 : TestResult { :>> id = "7d747c01-a2b3-414f-b2e1-14ffc3892679"; :>> outcome = VerdictKind::pass; :>> judgedAgainst = "1419069"; :>> judgedAt = "2026-09-11"; :>> judgedBy = "wweatherholtz"; :>> createdBy = "claudeOpus5"; }
}
