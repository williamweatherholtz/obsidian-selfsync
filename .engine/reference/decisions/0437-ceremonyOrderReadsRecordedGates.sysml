// D0437 (status: the `status` field below is the truth) — ceremonyOrderReadsRecordedGates: the ceremony guard's order and retro-scan checks read a RECORDED gate - pass or proposed - while every done-ness reader keeps reading pass alone
// Recorded via `keel record decision` (D0105 RMWX axis; issue054). Acceptance is a separate explicit
// human gate (method=confirmation, D0106): flip status + add the d0437Accept event on sign-off.
package ReferenceDecision0437 {
    private import EngineElement::*;
    private import EngineWork::*;
    private import EngineVerification::*;
    private import EngineRelationships::*;

    // #ProspectiveChange (D0070) - this Decision governs a process/schema change; the co-committed
    // change rides the process-change guard's hard lock.
    #ProspectiveChange part d0437 : Decision {
        :>> id = "96843d5b-7742-4d80-87b8-57cb7960b7db";
        :>> title = "ceremonyOrderReadsRecordedGates: the ceremony guard's order and retro-scan checks read a RECORDED gate - pass or proposed - while every done-ness reader keeps reading pass alone";
        :>> createdAt = "2026-09-10";
        :>> createdBy = "claudeOpus5";
        :>> status = DecisionStatus::accepted;
        :>> context = "D0312 option B, applied at sprint 663, makes an AI-judged pass on an examined method with no replayable receipt land as VerdictKind::proposed. The plan named the readers that must keep testing the pass literal so a proposed result is not-done by construction: orient's gate_passed, guard 52, the suspect and done algebra. It did not name the ceremony guard. That guard's ORDER check (guards.rs gates_passed -> ordering_violations) reuses orient::gate_passed, so on the first sprint recorded under the tier its Refine and Standup gates - inspect and analyze, judged by the recorder subagent, correctly proposed - read as UNPASSED when the Implement gate passed on its receipt, and the Stop hook went red: `[ceremony] sprint663_proposedOutcomeTier: Implement passed but Refine (earlier) unpassed; Implement passed but Standup (earlier) unpassed` (issue470, in-field). Under D0049 every sprint's Refine, Standup, Review, CloseOut and Retro are AI-recorded and none carries a ci-run receipt, so without this Decision every sprint from here on is red at its Implement gate until a human accepts two proposed results first - a gate on the human's word for every sprint, which is the class of control the human asked on 2026-09-10 to dissolve, not to add.";
        :>> decision = "NOT A FORK: the guard's question is sequence, and the fix restores the question it was written to ask. The ceremony guard's order check and its retro-scan check read the RECORDED set: a gate counts as recorded when a `part ...<gate>Gate...R<n> : TestResult` declaration carries outcome VerdictKind::pass OR VerdictKind::proposed (orient::gate_recorded, new). A violation reads `<G> recorded but <E> (earlier) unrecorded`. A recorded Retro owes its avoidable-issue scan evidence whether it passed or is proposed. Nothing else changes: orient::gate_passed, keel advance, the sprint frontier, guard 52 and the suspect algebra keep reading VerdictKind::pass alone, so a proposed gate is still not done, the sprint it belongs to is still in progress, and `advance` still refuses a forward gate past it. A fail, an inconclusive, an error or no result at all is unrecorded to the guard exactly as before.";
        :>> rationale = "The ceremony guard exists for issue010 and issue011: a gate recorded out of turn, and a Retro recorded without a scan. Both are statements about what was WRITTEN and in what order - a recorder that skipped Standup and wrote Implement, or wrote a Retro that scanned nothing. A proposed result is a record written in its turn whose judgment is pending; treating it as absent conflates the guard's question with orient's. Keeping done-ness on pass alone is what D0312 B is for and is untouched here; the alternative of accepting the two results by hand each sprint would put a human gate in front of every autonomous sprint, which D0049 says the ceremony does not have and which no observed subversion justifies (the control census, 2026-09-10). This is the reader plan663 missed, found by the control that exists to find it - the Stop hook ran the guard at the turn boundary and refused the turn - so the correction is a Decision and a test pair, not a hand-edit of the results.";
        :>> consequences = "Process-change (D0337): proposed until the human's word; the guard change rides this Decision's #ProspectiveChange lock in the same commit. orient.rs gains gate_recorded beside gate_passed over one shared matcher; guards.rs renames gates_passed to gates_recorded and threads the recorded set through ordering_violations and retro_scan_missing; the violation wording changes from passed/unpassed to recorded/unrecorded. Tests: the D0388 pair named before the guard moved - a proposed Refine and Standup ahead of a passed Implement is no violation while gate_passed still reads the Refine as unpassed (known positive), and a Refine with no result at all ahead of a proposed Standup and a passed Implement is two violations (known negative); a proposed Retro without scan evidence still fails. guards.md row `ceremony` says recorded, not passed. STATED RESIDUAL: a sprint can now be recorded fully in order with every gate proposed, and the guard is green over it - correctly, because whether those proposals are ever judged is dcSetJudgmentWritePath's question (next on the frontier), and orient reports the sprint in progress until they are. issue470 resolves on this Decision, as do the two red-yield obligations its red produced: obligation5bf22a2c (the ceremony guard's yield on sprint663) and obligationf3b226aa (the issues guard's yield on that obligation while untriaged).";
    }

    // acceptance event (D0121 review-queue sign-off; D0066/D0106 — human-judged, not fabricated)
    verification d0437Accept : Test { :>> id = "f4b57355-2d09-4a2a-a518-5c82a5127bca"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0437 (D0201 B); recorded as given (D0423)."; }
    part d0437AcceptR1 : TestResult { :>> id = "fcc501f9-d6f2-4f22-874a-13dc71143ced"; :>> outcome = VerdictKind::pass; :>> judgedAgainst = "3e6c518"; :>> judgedAt = "2026-09-11"; :>> judgedBy = "wweatherholtz"; :>> createdBy = "claudeOpus5"; }
}
