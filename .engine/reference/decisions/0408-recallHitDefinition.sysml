// D0408 (status: the `status` field below is the truth) — recallHitDefinition: what the eight-case recall harness counts as a hit - the named governing record only, any element that answers by a stated rule, or the named record reached through a human-owned alias
// Recorded via `keel record decision` (D0105 RMWX axis; issue054). Acceptance is a separate explicit
// human gate (method=confirmation, D0106): flip status + add the d0408Accept event on sign-off.
package ReferenceDecision0408 {
    private import EngineElement::*;
    private import EngineWork::*;
    private import EngineVerification::*;
    private import EngineRelationships::*;

    // RESEARCH: Measured 2026-09-09 on the binary built 10:26 (python .engine/tools/recall_ab.py, re-runnable): injection ON 7/8, OFF 0/8, silent 0/8, mean 1270 ms; the one miss is d0176 on 'what is an obligation and what discharges one?'. The seven hits sit at positions 8, 3, 4, 5, 4, 9, 13 of 13 rows. d0176's own text uses the word 'obligation' twice and 'discharge' never (grep -oi over .engine/decisions/0176-*.sysml: 2 and 0); the obligation records under .tracking/obligations/ cite it in their header as the Decision that created them ('OBLIGATION (auto-recorded, D0176/K7): a control was overridden or yielded; a human review discharges it'), so it IS the governing record and IS lexically unreachable from the question. The 13 rows shown for that question include d0276 and d0395, each naming d0176 once in text and neither joined to it by a typed edge; d0176's inbound typed edges are five #CharteredBy (p1PavedWritePathStory, obligationRecorderStory, p1TieredDeny, p1BashMatcher, p1RedYield; grep 'to d0176' over .engine .tracking .knowledge), none of which is among the 13 shown rows. The lexicon at .knowledge/lexicon/engine-lexicon.sysml holds 4 Alias items, all createdBy claudeFable5, none for 'obligation'; alias_targets in keel-cli/src/view/knowledge.rs seeds on them at Field::Alias weight. The criterion 'the hand set stays at 7/8 or better' lives in recallRanksLinkedRecordsAsWellAsGrepDoesDoD (backlog.sysml:519), whose R3 pass at 018315a already stands - so under D0307 that text is not edited; the definition lands in the harness header and in dcRecallHitDefinitionIsStated's own DoD result.
    part d0408 : Decision {
        :>> id = "fc190a2e-2d9b-45ab-a25d-3b335f2319b9";
        :>> title = "recallHitDefinition: what the eight-case recall harness counts as a hit - the named governing record only, any element that answers by a stated rule, or the named record reached through a human-owned alias";
        :>> createdAt = "2026-09-09";
        :>> createdBy = "claudeOpus5";
        :>> status = DecisionStatus::accepted;
        :>> context = "issue391, tracked as dcRecallHitDefinitionIsStated. The harness fixes eight questions and one ground-truth record each before any run, and scores a hit only when that record is among the rows the payload shows. Today it reads 7/8 against a required 7/8. The eighth, d0176 for the obligation question, is the record that created the obligation fact - the files it auto-records say so in their first line - yet it names the word twice and never says discharge, so no lexical or graph mechanism reaches it, and every mechanism change since 2026-09-04 has left it exactly there. The other case the issue raised, the rebase question, hits today at position 8 and is not at stake. What is at stake is whether a bar with zero headroom and one case no mechanism can move is a target or a permanent red, and the DoD says in so many words that I do not resolve this by editing the ground truth of a test I am failing, nor by adding a lexicon entry for it on my own initiative - the lexicon file is human-owned and an alias written to pass a case is fitting.";
        :>> decision = "OPTION A (keep 'the named record, or nothing', and declare the unreachable case): a hit is the ground-truth record among the shown rows, as now. recall_ab.py carries an UNREACHABLE marker on the d0176 case, stated in the CASES table before any run, printing 'unreachable (declared)' in place of 'no'; the required bar is stated as 7 of 8 with the eighth a declared sentinel whose hit, if a future mechanism produces one, is news rather than the norm. COST: zero headroom - any one regression among the seven fails the bar and there is no gradient on the eighth; the harness says less than it looks like it says about semantic reach, and the criterion text admits that one of its eight questions cannot be answered by the mechanism it measures. Changes: recall_ab.py (one field, one print branch), the harness docstring, no engine code. OPTION B (a hit is 'an element that answers', by a rule written here before it is applied): a shown row counts when it is the ground truth, or when it is joined to the ground truth by ONE typed edge in either direction and its own title or text carries the question's rarest content word. Under that rule, applied to today's payloads: the rebase case already hits on d0129 itself; the obligation case still misses, because d0276 and d0395 name d0176 in prose and share no typed edge with it, so B changes no number today. COST: the harness needs the edge set (a `keel why --json` call or the model loader per case, roughly 8 x 1.3 s more), the criterion measures 'a row near the answer' rather than 'the governing record', and the rule's two parameters (one edge, the rarest word) are mine and would be the next thing argued over. Changes: recall_ab.py, the docstring, and a re-read of the eight cases under the rule, which I have done above. OPTION C (the human authors the alias): an Alias item 'obligation / discharge' with a dependency to d0176 in .knowledge/lexicon/engine-lexicon.sysml, createdBy the human, because the lexicon is the declared home for 'the words a human uses, mapped to the elements that answer them' and this is such a word; the harness definition stays as in A and the case becomes reachable at Field::Alias weight. COST: the case then measures the alias, not the ranker - a hit proves the lexicon entry exists; and it sets the precedent that a hand-set miss is fixed by knowledge curation, which is exactly the move the criterion forbids me and permits them. Changes: one lexicon item by their hand, the harness docstring naming that the case is alias-reached. OPTION D (as it stands): 7/8 measured, criterion unchanged, issue391 open. COST: the next ranker change that loses one case reads as a regression against a bar it could never have exceeded, and nobody has said which case is the sentinel.";
        :>> rationale = "WHY THIS IS THEIRS: the question is what the measurement MEANS, and it was raised because the honest fix to the number was a move an agent must not make on its own; whichever way it goes, the definition has to be written by someone who is not grading themselves against it. WHAT I RECOMMEND, AND WHAT WOULD CHANGE IT: OPTION A. The criterion is met today on the definition it was written under; A keeps that definition, states the one case it cannot reach where the harness prints it, and leaves the eighth case in the set as the one that would detect a mechanism that reads meaning rather than words. B would be right if the harness's job were 'does the model get something it can answer from' - it is not; the payload's job (D0161, D0365) is to put the governing record in front of the model, and a near row is what the 50-case bench already measures. C is theirs to take if they judge 'obligation' a word they use for d0176's fact - a judgment about their own vocabulary I cannot make - and it composes with A rather than replacing it. It would change to B if they want the eight-case set to grade answerability, in which case the rule above is the one I would apply, with its two parameters named as mine.";
        :>> consequences = "On A: recall_ab.py gains the per-case UNREACHABLE field and print branch and its docstring states the definition and the sentinel; dcRecallHitDefinitionIsStated's DoD result records the definition and the 7/8 with the eighth declared; the R3 criterion text in recallRanksLinkedRecordsAsWellAsGrepDoesDoD is not edited (D0307) and its 'stays at 7/8 or better' remains true as read. On B: the same files, the one-edge-plus-rarest-word rule written into the harness before it runs, and every future mechanism change re-read against it; the number today stays 7/8. On C: the human's Alias lands in the lexicon with their createdBy; the harness re-run is expected to read 8/8 with the obligation case marked alias-reached, and the docstring says a hit there measures the lexicon. On D: nothing changes and issue391 stays open with its resolver undone.";
    }

    // acceptance event (D0121 review-queue sign-off; D0066/D0106 — human-judged, not fabricated)
    verification d0408Accept : Test { :>> id = "da9c28b6-f6ff-4cda-9d01-7c686d6ea555"; :>> method = VerificationMethod::confirmation; :>> procedureText = "Selected on the decision brief copy-out (fifteenth publish), pasted into chat 2026-09-11; d0408 option A, the recommended course. No note added. - their words, verbatim: “A: a hit is the named record among the shown rows; the obligation case is printed as a declared UNREACHABLE sentinel (recommended)”"; }
    part d0408AcceptR1 : TestResult { :>> id = "8406fc11-f3b8-4128-a713-756e04a9add0"; :>> outcome = VerdictKind::pass; :>> judgedAgainst = "3e6c518"; :>> judgedAt = "2026-09-11"; :>> judgedBy = "wweatherholtz"; :>> createdBy = "claudeOpus5"; }
}
