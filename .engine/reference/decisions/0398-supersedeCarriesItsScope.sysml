// D0398 (status: the `status` field below is the truth) — supersedeCarriesItsScope: a Supersede edge retires its whole target, a SupersedeClause edge reverses one clause and leaves the target in force, and superseded leaves the DecisionStatus vocabulary
// Recorded via `keel record decision` (D0105 RMWX axis; issue054). Acceptance is a separate explicit
// human gate (method=confirmation, D0106): flip status + add the d0398Accept event on sign-off.
package ReferenceDecision0398 {
    private import EngineElement::*;
    private import EngineWork::*;
    private import EngineVerification::*;
    private import EngineRelationships::*;

    // RESEARCH: Census 2026-09-09 (grep over .engine and .tracking, re-runnable): 7 Decisions carry status=superseded (d0003, d0014, d0038, d0069, d0071, d0310, d0353); 10 Supersede edges target a Decision, of which 3 retire a target already reading superseded (d0129->d0014, d0311->d0310, d0356->d0353) and 7 reverse one clause of a target that stays accepted and in force (d0152->d0114, d0158->d0115, d0149->d0129, d0251->d0175, d0289->d0178, d0291->d0205, d0359->d0351); 4 superseded Decisions have no incoming edge and name their superseder only in a trailing comment (d0003 by D0096, d0038 by D0044, d0069 by D0070, d0071 by D0075). Of the 7 superseded, 6 carry a human acceptance pass and d0038 carries none. The kernel accepts the two-marker construct (conformance_lane --construct, ACCEPTED 2026-09-09). Every Rust reader of a supersede edge keys on kind == supersede and treats the target as retired (view/mod.rs superseded_names, staleness.rs:434, critique.rs:695, guards.rs:4582, tier-satisfaction), so today those seven readers hold d0129 - never rebase - retired.
    // #ProspectiveChange (D0070) - this Decision governs a process/schema change; the co-committed
    // change rides the process-change guard's hard lock.
    #ProspectiveChange part d0398 : Decision {
        :>> id = "f735cb17-bf2d-4fc2-afcc-33914d44f184";
        :>> title = "supersedeCarriesItsScope: a Supersede edge retires its whole target, a SupersedeClause edge reverses one clause and leaves the target in force, and superseded leaves the DecisionStatus vocabulary";
        :>> createdAt = "2026-09-09";
        :>> createdBy = "claudeOpus5";
        :>> status = DecisionStatus::accepted;
        :>> context = "D0384 option A, the human's word 2026-09-09: the edge is authoritative, status leaves the vocabulary, the edge gains a scope. The scope cannot be an attribute on the marker: the kernel grammar's prefix form `#Marker` carries no body, and the member form `{ @Marker { ... } }` is one the Rust authority rejects (relationships.sysml, D0070 note). The scope is therefore a second declared marker. NOT A FORK: the direction is D0384's, accepted; the representation is the one both toolchains parse.";
        :>> decision = "EngineRelationships declares `metadata def SupersedeClause;` beside `Supersede`. A `#Supersede dependency from X to Y;` RETIRES Y whole: Y leaves every in-force scope - the acceptance queue, blocked-on-acceptance, the decisions scorecard, critique and staleness governance, the ready frontier. A `#SupersedeClause dependency from X to Y;` reverses one clause of Y named in X's text and leaves Y in force. `DecisionStatus` becomes `{ proposed; accepted; rejected; }`: a retired Decision keeps the standing it had when retired - accepted when an acceptance pass is on record, otherwise proposed - and `keel validate` refuses `DecisionStatus::superseded` as an unknown member. The seven clause edges are retyped and the four comment-only supersessions become edges by the D0067 transform `.engine/tools/migrations/2026-09-09-supersede-scope.py`, with control totals reconciled before apply. `keel record decision` gains `--supersedes-clause` / a `supersedes-clause:` draft line for the clause form.";
        :>> rationale = "One fact, one home (D0105): supersession was writable in two places and nothing held them equal, which is how d0353 read proposed on the queue for a day after d0356 retired it (issue396). With the edge authoritative the graph answers 'is this in force' without opening the file, and the queue cannot show a retired Decision because the same edge that retired it is what the queue reads. The scope is what makes the edge safe to read that way: without it the seven clause reversals would retire Decisions still in force, including never-rebase (d0129). A retired Decision's status keeps its last standing rather than inventing a fourth value, because that standing is a recorded fact - d0003 was accepted 2026-06-17 and later retired, and both remain true.";
        :>> consequences = "Schema: relationships.sysml gains SupersedeClause, work.sysml drops superseded (frozen core, this Decision is the sign-off record under D0384). Readers: pendingAcceptances, blockedOnAcceptance, the review and authority queues, the decisions scorecard's accepted count, critique/staleness governance and judgment-request-quality exclude the retired set. Data: 7 status values migrate (6 to accepted on their acceptance pass, d0038 to proposed), 7 edges retype to SupersedeClause, 4 edges are authored from their recorded trailing comments; nothing else in those files moves and the transform proves it by hash. D0070's statement that a cross-decision Supersede edge is intentionally not authored is reversed by this Decision for d0069. Anything reading `->supersede` in why-traversal now sees the clause reversals as `->supersedeclause`.";
    }

    // acceptance event (D0121 review-queue sign-off; D0066/D0106 — human-judged, not fabricated)
    verification d0398Accept : Test { :>> id = "05d08834-2434-4958-87ca-1e5f43402ef1"; :>> method = VerificationMethod::confirmation; :>> procedureText = "PLAN-COVERED under d0384 step 'a schema CR adds scope to Supersede': the human signed the plan itself and this enumerated step does not re-ask (D0375 option C / D0396). The plan's judge: wweatherholtz."; }
    part d0398AcceptR1 : TestResult { :>> id = "7367173e-8f69-4947-bd59-8c28de1c14a9"; :>> outcome = VerdictKind::pass; :>> judgedAgainst = "9369863"; :>> judgedAt = "2026-09-09"; :>> judgedBy = "wweatherholtz"; :>> createdBy = "claudeOpus5"; }
}
