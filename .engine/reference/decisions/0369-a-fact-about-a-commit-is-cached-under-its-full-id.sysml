// D0369 (status: the `status` field below is the truth) — gitFactsCached: the facts orient asks git about an immutable commit are served from a content-addressed cache keyed by the full commit id
// Recorded via `keel record decision` (D0105 RMWX axis; issue054). Acceptance is a separate explicit
// human gate (method=confirmation, D0106): flip status + add the d0369Accept event on sign-off.
package ReferenceDecision0369 {
    private import EngineElement::*;
    private import EngineWork::*;
    private import EngineVerification::*;
    private import EngineRelationships::*;

    part d0369 : Decision {
        :>> id = "fed1e188-417b-4736-a299-a283c1ab6214";
        :>> title = "gitFactsCached: the facts orient asks git about an immutable commit are served from a content-addressed cache keyed by the full commit id";
        :>> createdAt = "2026-09-07";
        :>> createdBy = "claudeOpus5";
        :>> status = DecisionStatus::accepted;
        :>> context = "D0367 ranked the spawn term of issue409 second: after the guards ran in parallel (D0368), `keel orient` on this host still spent 3.3 of its 5.2 s in 23-24 git spawns, and 14 of them asked questions whose answers are facts about a commit that cannot change - is this id a commit, what did a task's DoD say in a given file at that commit, what does `git grep` find for a moved DoD at that commit, which paths differ between that commit and HEAD. Every turn boundary re-asked them and paid a Windows process spawn per answer. The one wrinkle the measurement exposed: 4993 of the 5527 `judgedAgainst` anchors in this tree are 7-hex, so a cache keyed only by what the anchor says would have missed nine in ten. Measured with the same binary shape, a shell timer around `keel orient .`, cache absent then warm: 5.2-6.7 s cold and `git x24 in 3263-3505ms`; 1.67-1.73 s warm and `git x11 in 484-521ms`; stdout byte-identical across the previous binary, the cache absent, cold and warm (diff). `keel guard` on the same tree: 11.7 s to 7.1-8.2 s, stdout identical apart from the timing lines.";
        :>> decision = "A new module `gitfacts` holds a machine-local content-addressed cache at `.keel/cache/git-facts.toml` (gitignored with the rest of `.keel/`, written temp-then-rename through `write::write_atomic`, loaded once per process) of exactly four kinds of fact, each keyed by a FULL 40-hex commit id: is-commit (positives only), the DoD criterion of a task as a given file held it at that commit, the grep fallback's answer for a task at that commit, and the paths `git diff --name-only` lists between that commit and a full HEAD id. orient's `valid_commits`, `criterion_suspects`, `git_criterion_at` and `changed_paths_since` answer from it on a hit and fill it from their existing batched spawns on a miss. A short id's resolution is never read from disk: git resolves it fresh in every process inside the one `cat-file --batch-check` orient already runs, whose output line carries the full oid, and that mapping lives in memory for the process only - so a short anchor costs one spawn per process instead of one per question, and nothing on disk depends on how a short id resolves. A negative is-commit answer is never remembered, because a fetch can make it true; a git failure is never remembered, because it is not a fact about the commit. NOT A FORK: this is the mechanism D0367 ranked second with its number, and its honesty rests on one property the module doc states - every cached value is a pure function of (commit, question) over an immutable object, so the cache has no age, no eviction and no invalidation, and deleting it recomputes every answer identically.";
        :>> rationale = "A cache is honest when its key is the whole input. For a fact about a commit the whole input IS the commit id plus the question, which is why this cache can have no expiry: there is nothing that could make the entry wrong short of the commit object itself changing, which git's own model forbids. The two places that could have smuggled a mutable input in are named and refused - a short id, whose meaning is a function of the whole object store and so of the next fetch, and a negative, whose meaning is a function of what has been fetched so far. Resolving the short id in-process from a spawn that already happened costs nothing new and keeps the disk file free of any fact that could go stale. The extracted criterion is what is cached rather than the blob it was extracted from, because the blob is a whole tracking file at that commit - 150 KB each, across 534 commits - while the criterion is one line; the file is 1 MB and loads in 9 ms. The alternative of moving these reads in-process on a git library was ranked fifth by D0367 and remains conditional on the residual measured after this change: 11 spawns in about half a second per orient, all about HEAD and the remote and so not facts about a commit.";
        :>> consequences = "`keel orient` answers in about a third of its previous wall time on a warm cache and its git spawns fall from 24 to 11; `keel guard` gains the same from the priority-inversion guard that reruns orient. The remaining spawns are questions about the working tree and refs (rev-parse --abbrev-ref, rev-list, log -1, rev-parse HEAD/--short/--git-path) - the residual dcGitReadsStayInProcess judges against its 500 ms line. The cache is a cache: `rm .keel/cache/git-facts.toml` is always safe, a fresh clone starts cold, and `keel orient` is the only writer (the guards' own batched blob reads in staleness are untouched and are rank 3's corpus work if they matter). The one measurement that cannot transfer is the wall time, which is this host's spawn cost. Sprint 599 records the numbers.";
    }

    // acceptance event (D0121 review-queue sign-off; D0066/D0106 — human-judged, not fabricated)
    verification d0369Accept : Test { :>> id = "cdb82836-9727-44ce-9d24-6364b7603405"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0369AcceptR1 : TestResult { :>> id = "b55aa568-8ce3-4035-925f-c7213c10d6f0"; :>> outcome = VerdictKind::pass; :>> judgedAgainst = "7affb60"; :>> judgedAt = "2026-09-07"; :>> judgedBy = "wweatherholtz"; :>> createdBy = "claudeOpus5"; }
}
