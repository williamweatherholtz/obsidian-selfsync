// =====================================================================
// D0053 — trackedMetadata-deferred: on investigation (schema unfrozen with human
// sign-off), the @Tracked migration is a multi-system change, not one schema edit.
// Deferred behind a proper replan; schema/core stays frozen. Accepted 2026-06-16
// by wweatherholtz (signed off the unfreeze; this records the scope finding + defer).
// =====================================================================
package ReferenceDecision0053 {
    private import EngineElement::*;
    private import EngineWork::*;
    private import EngineVerification::*;

    part d0053 : Decision {
        :>> id = "2d3e4f50-6172-423b-376f-1324a5b6c7e4";
        :>> title = "D0053: defer trackedMetadata — @Tracked migration is multi-system, not one schema edit; replan first";
        :>> createdAt = "2026-06-16";
        :>> createdBy = "wweatherholtz";
        :>> status = DecisionStatus::accepted;
        :>> context = "The human signed off temporarily unfreezing schema/core to collapse the four duplicated tracking bases (Element + TrackedRequirement/TrackedUseCase/TrackedVerification, each declaring id/title/createdAt/authoredBy) into a single @Tracked metadata annotation (U2, 'SPIKED GREEN 2026-06-11'). Investigation before editing found the real scope is far larger than the 5-pt estimate: (1) the duplication is FORCED by SysML metaclass rules (requirement/use-case/verification def cannot specialize part def Element), so it cannot be removed by inheritance; (2) collapsing to @Tracked requires rewriting EVERY instance's `:>> id/title/createdAt/authoredBy` (hundreds across .tracking + .engine) to `@Tracked { ... }` annotation syntax; (3) the Rust parser/indexer — now the AUTHORITY (D0048) — does not parse metadata-application on instances and would need a rewrite, re-suspecting the whole deliverable (D0050); (4) validate_actors.py reads `:>> authoredBy` and would break. The 'spike green' only proved @Tracked PARSES in the kernel, not that the full migration is safe.";
        :>> decision = "DEFERRED. schema/core is RE-FROZEN — no change made (the temporary unfreeze is unused; lower risk than a half-migration). trackedMetadata is gated behind a new trackedMetadataReplan task that must first scope the migration as a multi-sprint effort INCLUDING Rust parser support for @Tracked metadata-application, an instance-migration tool (bulk :>> id -> @Tracked), validate_actors + kernel-validator updates, and a deliverable re-verify pass; only after that replan + a fresh human sign-off does the migration proceed.";
        :>> rationale = "Investigation before editing found the real scope far larger than the 5-pt estimate: (1) the duplication is FORCED by SysML metaclass rules (requirement/use-case/verification def cannot specialize part def Element), so it cannot be removed by inheritance; (2) collapsing to @Tracked requires rewriting EVERY instance's :>> id/title/createdAt/authoredBy (hundreds across .tracking + .engine) to @Tracked annotation syntax; (3) the Rust parser/indexer — now the AUTHORITY (D0048) — does not parse metadata-application on instances and would need a rewrite, re-suspecting the whole deliverable (D0050); (4) validate_actors.py reads :>> authoredBy and would break. The 'spike green' only proved @Tracked PARSES in the kernel, not that the full migration is safe. GROUNDED 2026-06-16 (kernel spike + OMG/SysML-library research): cross-metatype specialization is a HARD KerML type-compatibility rule, so per-metatype Tracked* duplication IS a confirmed anti-pattern and metadata (@Tracked) is the idiomatic AND ONLY uniform cross-metatype mechanism — the defer stands on migration COST (every instance + Rust-parser @Tracked support), NOT on direction: trackedMetadataReplan should plan the metadata migration, not seek an alternative.";
        :>> consequences = "No schema change now; schema/core stays frozen. trackedMetadata leaves the ready frontier (blocked on trackedMetadataReplan). The auto-followed next item becomes specVersionRuntimeCheck. issue003 (conflicting Release types, relatedTask trackedMetadata) rides with the replan. This is the engine's 'capture decisions even when they cause no action' discipline: a scope finding that converts a queued task into a planned effort rather than a reckless autonomous migration of the just-promoted toolchain. GROUNDED 2026-06-16 (empirical kernel spike _spike_element_spec.py + online OMG/SysML-library research, both agreeing): cross-metatype specialization is a HARD KerML type-compatibility rule, not an anti-pattern we chose to avoid — part def -> Part/structure vs requirement def -> RequirementCheck/ConstraintCheck/predicate vs use-case/verification def -> Case/behavior are incompatible roots (kernel: 'Cannot specialize structure' + duplicate 'self' from Part vs RequirementCheck). The per-metatype Tracked* duplication IS a confirmed anti-pattern, and metadata (@Tracked with typed values, cf. library ModelingMetadata::StatusInfo) is the idiomatic AND ONLY uniform cross-metatype mechanism (a shared abstract supertype is impossible). So the defer stands on migration COST (every instance + Rust-parser @Tracked support), NOT on direction: trackedMetadataReplan should plan the metadata migration, not seek an alternative.";
    }

    verification d0053Accept : Test { :>> id = "fc793df1-3e64-450a-8382-93216cdf984a"; :>> method = VerificationMethod::confirmation; :>> procedureText = "wweatherholtz attests acceptance of decision d0053 (D0066 acceptance-events migration, attested 2026-06-17); prior record: status=accepted + file prose."; }
    part d0053AcceptR1 : TestResult { :>> id = "bc87b17f-3282-4528-80ba-28409a56ab6e"; :>> outcome = VerdictKind::pass; :>> judgedAgainst = "e146621"; :>> judgedAt = "2026-06-17"; :>> judgedBy = "wweatherholtz"; }
}
