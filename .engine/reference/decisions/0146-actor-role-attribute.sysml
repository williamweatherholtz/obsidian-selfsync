// D0146 — ACCEPTED (wweatherholtz, 2026-08-15): `Actor` gains a `role` attribute so enrollment can
// record it as model data. FROZEN CORE (§1.5) — the sign-off is the d0146Accept event below.
// #ProspectiveChange (D0070): existing actors stay valid — role is optional.
package ReferenceDecision0146 {
    private import EngineElement::*;
    private import EngineWork::*;
    private import EngineVerification::*;
    private import EngineRelationships::*;

    #ProspectiveChange part d0146 : Decision {
        :>> id = "5a2e91d3-7b64-4c08-9f15-2e83a70c6d49";
        :>> title = "D0146: Actor gains an optional `role` attribute (frozen core)";
        :>> createdAt = "2026-08-15";
        :>> createdBy = "claudeOpus5";
        :>> status = DecisionStatus::accepted;
        :>> context = "FOUND by the consumer check while building `keel enroll` (sprint 287, D0144). The actor-enrollment process step `enrollKindRole` requires two things to be ASKED and RECORDED, never inferred: KIND and ROLE. It says plainly that 'role is model data, not tribal knowledge' and that neither may be defaulted. KIND exists — `Actor.kind : ActorKind` — and enrollment records it. ROLE HAS NOWHERE TO GO: `part def Actor` carries `name`, `email[0..1]` and `kind`, and nothing else. The obvious `part def Role` was deleted by D0142 as dead schema, correctly, since it had zero declarations; but the enrollment process was written expecting role to be recordable somewhere. So a process step that this engine's own workflow declares mandatory is, today, unsatisfiable. Checking the schema BEFORE writing the enrollment command is what surfaced this; had it been checked after, `keel enroll --role` would have been built writing role into a comment or a name string — model data in a place no view can query, which is the dual-truth defect the engine exists to prevent.";
        :>> decision = "ACCEPTED under §1.5: add `attribute role : String[0..1];` to `part def Actor` in `.engine/schema/core/element.sysml`. A free String rather than an enum, deliberately: the process names five roles (contributor, supervisor, integrator, reviewer, or a project-declared role) and explicitly permits a project-declared one, so a closed enum in FROZEN core would force every downstream project with a different role vocabulary through a frozen-schema sign-off just to name its own roles — the exact issue089 dynamic where an engine-level constraint blocks a project from working. Optional (`[0..1]`) so every existing actor stays valid without migration. On acceptance, `keel enroll` gains a REQUIRED `--role` argument, matching the process's 'neither may be defaulted'.";
        :>> rationale = "RECORDED AS PROPOSED RATHER THAN APPLIED because frozen core needs explicit human sign-off on the specific change (§1.5), and an AI actor cannot supply it. The alternative considered and rejected was to build `keel enroll --role` now and write the value into the actor's `name` string or a trailing comment: that would satisfy the process's letter while defeating its stated purpose, since 'model data, not tribal knowledge' means queryable, and a role inside a display name is neither. The honest interim is what sprint 287 shipped: enrollment records identity, kind and binding — everything the item's own VERIFY list demands — and REPORTS at the end that role is unrecorded and why, pointing the reader at this proposal. ALTERNATIVES: (i) an `enum def ActorRole` — REJECTED, closed vocabulary in frozen core blocks project-declared roles; (ii) a separate `part def Role` re-added with a `hasRole` edge — REJECTED as heavier than the need, and D0142 removed exactly that type for having no instances; (iii) leave role permanently unrecorded and amend the process to stop requiring it — a legitimate option the human may prefer, and cheaper than a schema change; (iv) CHOSEN for proposal.";
        :>> consequences = "If ACCEPTED: one optional attribute in frozen core, `keel enroll` gains a required `--role`, and the enrollment process step becomes satisfiable. If REJECTED: `.engine/processes/actor-enrollment.sysml` step `enrollKindRole` must be amended to stop requiring role, because a declared process step that cannot be satisfied is worse than an absent one — it is cited as if enforced. Either way something changes; the current state, where the process demands a field the schema cannot hold, is the one outcome that must not persist. Tracked as issue110.";
    }

    // acceptance event (D0121 review-queue sign-off; D0066/D0106 — human-judged, not fabricated)
    verification d0146Accept : Test { :>> id = "8fb7e7e9-b5c4-4b41-9105-ea59a760a5dc"; :>> method = VerificationMethod::confirmation; :>> procedureText = "wweatherholtz, 2026-08-15, verbatim: 'accepted on all three. expand to suit the new improved schema'. Given in direct reply to the sprint-298 report, which presented D0146 (Actor.role), D0147 (a Claim type) and D0148 (ship the EngineCodeAudit module) together as one finding - process definitions demanding data the schema cannot hold - each with its alternatives and with what must happen on rejection. The human accepted all three and directed the follow-on work."; }
    part d0146AcceptR1 : TestResult { :>> id = "22094f21-06ec-4ad9-a62a-526fe6a99934"; :>> outcome = VerdictKind::pass; :>> judgedAgainst = "46f0cca"; :>> judgedAt = "2026-08-15"; :>> judgedBy = "wweatherholtz"; }
    part d0146AcceptR2 : TestResult { :>> id = "8b0fbaef-f80e-4bf5-ad57-86de77da5553"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): decision wording PROPOSED to ACCEPTED at a6b7123 - editorial, the agreed substance unchanged. Their standing words, verbatim: 'issues raised are automatically accepted. they can be customizedly changed post-fact.'"; }
}
