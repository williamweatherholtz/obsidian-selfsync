// D0215 (status: the `status` field below is the truth) — docCountHasOneHome: the doc surface may not hardcode the total guard count - delete the number, do not reconcile it
// Recorded via `keel record decision` (D0105 RMWX axis; issue054). Acceptance is a separate explicit
// human gate (method=confirmation, D0106): flip status + add the d0215Accept event on sign-off.
package ReferenceDecision0215 {
    private import EngineElement::*;
    private import EngineWork::*;
    private import EngineVerification::*;
    private import EngineRelationships::*;

    // #ProspectiveChange (D0070) - this Decision governs a process/schema change; the co-committed
    // change rides the process-change guard's hard lock.
    #ProspectiveChange part d0215 : Decision {
        :>> id = "0eac5dea-9170-4eb7-a38a-d2b5b065db4c";
        :>> title = "docCountHasOneHome: the doc surface may not hardcode the total guard count - delete the number, do not reconcile it";
        :>> createdAt = "2026-08-24";
        :>> createdBy = "claudeFable5";
        :>> status = DecisionStatus::accepted;
        :>> context = "Four of the nine panel lenses independently named the same drift mechanism, and the brief that DIAGNOSED report-vs-truth drift committed it twice itself. Measured: CLAUDE.md said 'all 45 forward guards' and .engine/docs/guards.md said 'runs **45** forward guards' while 48 were enforced - and guards.md's very next sentence said that keel 0.2.3 build commit: 3ef14f7+dirty api contract: 2.0.0 (derived; breaking changes recorded in release Decisions) claude surface: 0.2.3 (generated from this binary) engine declared: matches (engine-version.toml or pre-D0190 absent) guards: 49 (40 hard-blocking, 9 warning-only) reports the split computed from the enforced set 'so the number has one home'. It stated a number while declaring the number should not live there. The same class was live in a shipped contract: activation.toml directed readers to .engine/contracts/process-units.toml, a file D0141 deleted, and copied that ghost into every new project. This is the highest-frequency drift mechanism in this repository because it needs no defect to appear - only time.";
        :>> decision = "A number the engine can compute may not be typed into the doc surface, and the enforcement is DELETION rather than reconciliation. New hard guard scans CLAUDE.md and .engine/docs/*.md and FAILS on a hardcoded total guard count, naming the computed value and pointing at the one home (keel 0.2.3 build commit: 3ef14f7+dirty api contract: 2.0.0 (derived; breaking changes recorded in release Decisions) claude surface: 0.2.3 (generated from this binary) engine declared: matches (engine-version.toml or pre-D0190 absent) guards: 49 (40 hard-blocking, 9 warning-only)). The two live claims are removed rather than corrected: CLAUDE.md now reads 'every enforced forward guard (count: keel 0.2.3 build commit: 3ef14f7+dirty api contract: 2.0.0 (derived; breaking changes recorded in release Decisions) claude surface: 0.2.3 (generated from this binary) engine declared: matches (engine-version.toml or pre-D0190 absent) guards: 49 (40 hard-blocking, 9 warning-only))' and guards.md 'runs the enforced forward guards', so the count exists in exactly one place. The ghost process-units.toml reference is swept from both activation.toml and the ACTIVATION_HEADER that init writes. The guard is NARROW BY CONSTRUCTION: only the canonical current-total phrasing is checked. An 'all N guards' branch was implemented first and REMOVED after probing it against the real corpus, where it fired on guards.md legitimately narrating history ('passed validate and all 37 guards') - a true statement about the past. A guard that fires on true prose gets bypassed, so historical narration and ordinal references ('Guard 37 checks...') are deliberately untouched.";
        :>> rationale = "Reconciliation - syncing 45 to 48 - fixes today and drifts again on guard 49, because the defect is the DUPLICATION and not the value; D0105 gives every fact one canonical home and this fact's home is the computed one. Deletion is therefore the root fix and it is subtractive, which is what the panel's reducer argued the whole slate needed. D0047 requires the control because the defect recurred: it was live in two governing documents AND reproduced by me in the review artifact, so manual vigilance has already demonstrably failed. It is HARD rather than warning-level because a false number in the AI's own governing document is dishonest state, not incompleteness - D0098 forbids gating completeness and says nothing against gating honesty.";
        :>> consequences = "GUARD_NAMES goes 48 -> 49 and the guard is hard: a commit reintroducing a hardcoded total fails. Verified both directions - the cleaned corpus PASSES (4 files scanned, 0 violations) and reintroducing 'all 45 forward guards' FAILS at exit 1 naming the file, line, claim and computed value; the false positive found during development is gone. guards.md gains its catalogue row in the same commit, and that row states the removed branch and why, so the next author does not re-add it. NOTE the reflexive consequence, which is the point: guards.md may no longer state its own guard total, so this Decision's own count (49) appears in this record and in keel 0.2.3 build commit: 3ef14f7+dirty api contract: 2.0.0 (derived; breaking changes recorded in release Decisions) claude surface: 0.2.3 (generated from this binary) engine declared: matches (engine-version.toml or pre-D0190 absent) guards: 49 (40 hard-blocking, 9 warning-only), not in the catalogue. Resolves issue246.";
    }

    // acceptance event (D0121 review-queue sign-off; D0066/D0106 — human-judged, not fabricated)
    verification d0215Accept : Test { :>> id = "d455833b-4d4f-4098-b603-7355df8e01ba"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/12."; }
    part d0215AcceptR1 : TestResult { :>> id = "b1b2921f-657a-4c9c-b5da-53a08b838549"; :>> outcome = VerdictKind::pass; :>> judgedAgainst = "766343d"; :>> judgedAt = "2026-08-24"; :>> judgedBy = "wweatherholtz"; }
}
