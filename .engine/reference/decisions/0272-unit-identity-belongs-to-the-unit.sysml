// D0272 (status: the `status` field below is the truth) — A unit's identity belongs to the unit, not to the project exporting it
// Recorded via `keel record decision` (D0105 RMWX axis; issue054). Acceptance is a separate explicit
// human gate (method=confirmation, D0106): flip status + add the d0272Accept event on sign-off.
package ReferenceDecision0272 {
    private import EngineElement::*;
    private import EngineWork::*;
    private import EngineVerification::*;
    private import EngineRelationships::*;

    // #ProspectiveChange (D0070) - this Decision governs a process/schema change; the co-committed
    // change rides the process-change guard's hard lock. Here that change is library-stewardship's
    // rule 5, which governs publishing an adaptation back - rule 3's own path, and the one that had
    // this bug.
    #ProspectiveChange part d0272 : Decision {
        :>> id = "d6eff824-10b8-47a7-9fc5-3bfdd14c0963";
        :>> title = "A unit's identity belongs to the unit, not to the project exporting it";
        :>> createdAt = "2026-09-01";
        :>> createdBy = "claudeOpus5";
        :>> status = DecisionStatus::accepted;
        :>> context = "Observed live, publishing an improvement to the exec-summary skill from a project that had IMPORTED it. `keel process export` resolved the unit's id from `unit-ids.toml` alone - the registry of ids this project MINTED. But the import had filed the unit under the LIBRARY's id in `installed-units.toml` and written nothing to the minted registry, so the lookup missed, minted a fresh id, and shipped the improved content under an identity no consumer had ever installed. `next_unit_version` then looked THAT id up, missed again, took its `None => 1` arm, and restarted the version at 1. The unit changed content, changed identity, and kept its version number. This repo's own install record ended up carrying `exec-summary` under two ids, both at v1.";
        :>> decision = "Export resolves a unit's exchange identity from the INSTALL RECORD first, the minted registry second, and mints only when neither knows the process. Two clauses make that enforceable rather than merely stated. When the registries DISAGREE the minted one is REPAIRED in place - preferring the right id at export time is not enough, because `unit-ids.toml` is what the NEXT export reads, so leaving it wrong reopens the defect on the following publish. When one process name is filed under TWO ids, export REFUSES and names both. Separately, `next_unit_version` stops conflating 'a new unit' with 'I could not find it': a missed lookup on a process the project demonstrably HAS installed refuses, and only a process with no install record at all starts at version 1.";
        :>> rationale = "This is worse than a numbering bug, and that is why it is a Decision rather than a patch. A consumer decides whether it is behind by comparing versions - exactly what `keel status`'s drift section does, shipped one day earlier against srDriftIsReportedPerUnit. Holding v1 against a library advertising v1, it reports 'nothing behind' while the content differs entirely. The report does not MISS the update; it AFFIRMS there is none, and a lens returning a confident wrong answer is worse than one returning nothing, because nothing prompts a look and a green does not. The identity change compounds it: even a corrected version number would not have helped, because the unit a consumer installed no longer existed under that id. REJECTED, keying the version off the process NAME: it would have masked this exact failure and reintroduced the collision the id exists to prevent - names duplicate across projects, which is why D0183 minted ids at all. REJECTED, warning on a registry disagreement instead of repairing it: the warning is read by whoever is publishing, the person least likely to act on it, and the disagreement then persists into the next publish. REJECTED, resolving a forked identity by heuristic (oldest section, most files): every heuristic silently picks an identity on a human's behalf, and picking wrong orphans installs - refusing costs one manual reconciliation, guessing costs a consumer base.";
        :>> consequences = "Publishing from an importing project now carries the unit's real identity, and a project that has never imported is unaffected because its two registries already agree. Three cases hold it in `unit_identity_survives_republish.rs`: the round trip issue323 named (publish, import elsewhere, change one shipped file, republish, assert the id UNCHANGED and the version INCREMENTED), the forked-identity refusal, and the registry-disagreement repair. All three were run against the pre-fix binary and all three FAIL there, the round trip showing the re-mint directly with one id published over another - a control never observed to fail is a claim (D0253). The live damage is repaired: the re-minted section is gone from this repo's install record and exec-summary is republished at its original id, v2. THE RESIDUAL, stated rather than closed: the corrupted state is caught at the WRITE PATH, when someone exports, and by no guard - so it can sit in a committed contract until the next publish refuses. Judged sufficient because the refusal is loud and lands exactly when the wrong id would otherwise ship, and a guard would widen the keystone-locked enforcement surface for a state only one command can create and that command now refuses to propagate. If a second way to fork an identity appears, revisit this trade.";
    }

    // acceptance event (D0121 review-queue sign-off; D0066/D0106 — human-judged, not fabricated)
    verification d0272Accept : Test { :>> id = "579fecff-950c-45c5-9d5c-e70577ad939f"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0272AcceptR1 : TestResult { :>> id = "88d9285a-bcaf-449f-8a0e-077de3683ed1"; :>> outcome = VerdictKind::pass; :>> judgedAgainst = "a9d8c90"; :>> judgedAt = "2026-09-01"; :>> judgedBy = "wweatherholtz"; }
}
