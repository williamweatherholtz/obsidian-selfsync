// D0299 (status: the `status` field below is the truth) — The recorder of an acceptance is provenance distinct from the judge: every accept path stamps createdBy on the acceptance result, and the delegated-substance rule binds only records whose recorder is not the judge
// Recorded via `keel record decision` (D0105 RMWX axis; issue054). Acceptance is a separate explicit
// human gate (method=confirmation, D0106): flip status + add the d0299Accept event on sign-off.
package ReferenceDecision0299 {
    private import EngineElement::*;
    private import EngineWork::*;
    private import EngineVerification::*;
    private import EngineRelationships::*;

    // #ProspectiveChange (D0070) - this Decision governs a process/schema change; the co-committed
    // change rides the process-change guard's hard lock.
    #ProspectiveChange part d0299 : Decision {
        :>> id = "988c6a35-7e8a-45d0-9983-e303b6ba63ad";
        :>> title = "The recorder of an acceptance is provenance distinct from the judge: every accept path stamps createdBy on the acceptance result, and the delegated-substance rule binds only records whose recorder is not the judge";
        :>> createdAt = "2026-09-04";
        :>> createdBy = "claudeOpus5";
        :>> status = DecisionStatus::accepted;
        :>> context = "issue287: the human accepted d0235 themselves through the console while the AI was working, with the note 'agreed with panel's decisions', and delegatedAcceptanceSubstanceRule FAILED the gate - demanding that the human quote themselves. The rule's intent is right: a DELEGATED acceptance, one an AI records on the human's behalf, must quote their words or cite their gesture, because that is the only thing between a real sign-off and a fabricated one (D0192). The defect was that nothing recorded WHO RECORDED an acceptance - only who judged it - so the rule could not tell a delegated record from a self-recorded one and applied the delegated demand to both, which is governance aimed at the one party it must never bind (D0204). The console's channel stamp (issue287's first half, e4e8ee8) made console records self-evidence through the note text; the second half - a recorder as provenance, so the rule scopes by fact rather than by inferring from prose - is this Decision.";
        :>> decision = "write::accept_decision takes recorded_by and writes it as the acceptance result's createdBy - an attribute TestResult already inherits from Element, so no schema change. Every accept path supplies it, never defaulted: the console passes the judge (the human recorded it themselves); keel accept with no --by passes the judge (the bound human at their own terminal); keel accept --by <human> passes the SESSION's own actor and refuses if none is bound (an agent recording on the human's behalf is a delegated record and the record says so); record decision's standing-consent auto-accept passes the recording actor, so it is delegated by construction and its AUTO-ACCEPTED quote is what the rule reads. acceptQuotesDelegatedWords now returns true when the result's createdBy equals its judgedBy (self-recorded), and otherwise reads the note as before. A result with NO createdBy - every acceptance before this Decision - is read as delegated: absence of provenance is never taken as evidence of self-recording, and those records already carry their quote or gesture.";
        :>> rationale = "WHY A FACT AND NOT THE NOTE TEXT: the console stamp works, but it makes the rule depend on a phrase in prose, and a rule that scopes itself by reading its own subject's wording is one an agent can satisfy by writing the wording. createdBy is written by the binary from the actor it resolved, which is the same provenance every other write carries. WHY UNSTAMPED RECORDS STAY DELEGATED: reading them as self-recorded would retroactively excuse every past AI-recorded acceptance from the quote requirement; reading them as delegated changes nothing about them, since they already pass. WHY --by MEANS DELEGATED: naming a judge other than yourself is the definition of recording on someone's behalf. WHY NO SCHEMA CHANGE: the attribute exists on Element with the comment that TestResult 'uses judgedBy instead' - it now uses both, for two different facts, which is what the two attributes are for.";
        :>> consequences = "dcRecorderIsDistinctFromJudge is delivered; issue287 resolves. The human's own words are never altered by any path - the console appends its channel citation, the CLI writes the note as given. keel accept --by refuses when the session actor is unbound, which is new friction with a named cause (provenance never defaulted, D0129). The attestation view can now distinguish self-recorded from delegated acceptances by fact; that lens is not built here. Grandfathering is by absence of the attribute, not by date, so no cutoff is authored.";
    }

    // acceptance event (D0121 review-queue sign-off; D0066/D0106 — human-judged, not fabricated)
    verification d0299Accept : Test { :>> id = "52abc63a-3901-4c2c-86f7-a460816d27dc"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0299AcceptR1 : TestResult { :>> id = "e55ec47d-a5de-4c9b-a65b-49f14bcd85ff"; :>> outcome = VerdictKind::pass; :>> judgedAgainst = "d82c512"; :>> judgedAt = "2026-09-04"; :>> judgedBy = "wweatherholtz"; :>> createdBy = "claudeOpus5"; }
}
