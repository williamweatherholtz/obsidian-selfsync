// D0279 (status: the `status` field below is the truth) — Keel enforces form rigorously and substance weakly, and its gates were advisory by failure mode - the rigor panel's verdict and the two fixes it authorises
// Recorded via `keel record decision` (D0105 RMWX axis; issue054). Acceptance is a separate explicit
// human gate (method=confirmation, D0106): flip status + add the d0279Accept event on sign-off.
package ReferenceDecision0279 {
    private import EngineElement::*;
    private import EngineWork::*;
    private import EngineVerification::*;
    private import EngineRelationships::*;

    // #SafetyChange (D0070) - this Decision governs a process/schema change; the co-committed
    // change rides the process-change guard's hard lock.
    #SafetyChange part d0279 : Decision {
        :>> id = "39748478-8376-443f-9431-a6365d05d5b9";
        :>> title = "Keel enforces form rigorously and substance weakly, and its gates were advisory by failure mode - the rigor panel's verdict and the two fixes it authorises";
        :>> createdAt = "2026-09-01";
        :>> createdBy = "claudeOpus5";
        :>> status = DecisionStatus::accepted;
        :>> context = "The human's question, in their words: 'why are we losing rigor? it feels like analyses of facts constantly slip, and while we do stop AI agents from going rogue sometimes, we lack the authority needed to really strongly drive custom processes. what's lacking?' A five-critic panel (architectural-critique, D0046) read fifteen functions at file:line - the hooks, the guard runner, the three governance guards, actor resolution, the keystone, the write paths, done-ness and open-ness - and each critic attacked one claim the engine makes about itself. Every number came from this tree today. THE MEASUREMENTS: 12 enforcement points, 2 fail-closed - the Stop hook allowed on a missing binary, printing 'this gate did not run'. 37 processes, 16 assert any guard, 11 undeclared, five of them authored in the last two days. The three guards standing between a finding and its loss - issues, decision-scaffolding, retro-backlog - all check that something EXISTS rather than that it is RIGHT, and retro-backlog examined a retro only if it contained the literal tokens AVOIDABLE-ISSUE or LESSON:. Six findings written into retros today were examined by nothing.";
        :>> decision = "The verdict, in one sentence the five critics converged on: keel enforces FORM rigorously and SUBSTANCE weakly, and the enforcement it has is advisory by failure mode. TWO CHANGES ARE MADE NOW, both on the enforcement surface and both authorised here. FIRST, the Stop hook fails CLOSED on a missing binary - its wrapper emits a block decision naming the install path instead of allowing - and this refines D0134: a hook never fails a turn on infrastructure absence holds for ADVISORY hooks and is withdrawn for GATING hooks, which is the line pre-write already sat on. SECOND, retro-backlog takes its third shape: every retro gate is examined whatever words it uses, and a finding is tracked only when THIS COMMIT ADDS a tracked item the retro's own text names, or the retro states why none is needed; naming the task it delivered - which every retro does - no longer counts. A violation, not a warning. THREE FINDINGS ARE RECORDED AND CARRIED with the reason each: session identity does not reach the hooks (issue337, a plumbing fix outside the keystone that corrects issue332's wrong diagnosis); a process step binds to no predicate and analyses live in String fields (issue336, a schema proposal that must go to the human as a fork); and the second-red-pass yield stays fail-open by design, as loop avoidance with a recorded obligation.";
        :>> rationale = "WHY THE PANEL'S SENTENCE IS THE RIGHT DIAGNOSIS, from the evidence rather than the feeling. The identity, edge and marker guards - identity-present, identity-well-formed, edge-endpoints, marker-vocabulary, duplicate-identity - hold, and they hold because they check exactly what they are trusted to check: form. The guards on whether the process is closing its own loops are the weak ones, and they are weak in one specific way: existence is cheap to check and cheap to satisfy, and each of them was satisfied by construction. An Issue with any resolver edge is triaged. A Decision with one inbound edge is delivered. A retro naming its own delivered task has tracked its findings. That is why facts slip: every analysis is a String, no control reads a String for meaning, so the moment an analysis is written it is invisible to every control at once, and the controls that were supposed to force its conversion into a typed item were greps. WHY THE TURN GATE CHANGE IS RIGHT DESPITE D0134. D0134's rule protected sessions from being trapped by infrastructure - correct for a routing reminder, and the hardening table's own precedent shows it was never applied to pre-write. A turn gate that switches itself off when its binary cannot be found is the definition of lacking authority, and the binary WAS unavailable twice today during ordinary rebuilds - each time the gate did not run and the turn ended green. The cost is a project without keel cannot end a turn until it is installed, which is loud, immediate and says what to do. WHY THE RETRO GUARD IS ON ITS THIRD SHAPE, which is the argument for the shape rather than an embarrassment: shape one accepted any co-staged tracked file and every commit stages one (issue189); shape two required the retro to name an item and every sprint names its delivered task; each fix was correct against the case that found it and wrong against the next. Shape three asks the question the guard was always for - does this commit add what this retro names - and its tests keep both earlier failure modes as regressions. REJECTED, making retro-backlog a warning again 'until the corpus is clean': only STAGED sprint files are examined, so no historical retro is ever re-judged, and a warning is what let six findings through today.";
        :>> consequences = "Fail-closed enforcement points go from 2 to 3 of 12: the turn gate, the protected-path write, the commit. retro-backlog becomes a blocking guard on the SAME commit as this Decision, and this commit satisfies it - the retro of sprint 514 names issue334 through issue337, all four added here. The registry (D0278) drops its retro-backlog entry in this same commit, because the Issue it pointed at resolves here; the ownership entry is re-pointed at issue337, the correct diagnosis. TWO RESIDUALS STATED. The harness timeout still resolves every hook to ALLOW and cannot be changed from inside keel; the fire-ledger detects an expected fire that did not happen, which is visibility and not prevention. And the hardening enforcementPoints table classifies each point's failMode by keyword-matching its own hand-written description - it is a description that must be kept true, not a measurement, and this Decision keeps it true for the row it changes while naming the mechanism as the panel's own pattern appearing inside the instrument that found it. THE OPEN QUESTION IS issue336 AND IT IS THE HUMAN'S: whether a ProcessStep may declare what checks it, and whether a Decision's clauses become addressable - both change what a Process and a Decision ARE under the frozen core, and the panel's fact-lifecycle critic argues they are the only change that stops analyses slipping rather than catching one more instance of it.";
    }

    // acceptance event (D0121 review-queue sign-off; D0066/D0106 — human-judged, not fabricated)
    verification d0279Accept : Test { :>> id = "b511a750-f18a-48af-bc4c-03da38e865b0"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0279AcceptR1 : TestResult { :>> id = "0eff1c60-c3c4-4311-bc67-855b47001b7a"; :>> outcome = VerdictKind::pass; :>> judgedAgainst = "1924c8e"; :>> judgedAt = "2026-09-01"; :>> judgedBy = "wweatherholtz"; }
}
