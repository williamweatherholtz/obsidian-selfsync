// D0174 (status: the `status` field below is the truth) — D-P0a: the .claude/ surface is engine-derived, keel-scope-owned, ships with keel init, and owns the protected-path deny list
// Recorded via `keel record decision` (D0105 RMWX axis; issue054). Acceptance is a separate explicit
// human gate (method=confirmation, D0106): flip status + add the d0174Accept event on sign-off.
package ReferenceDecision0174 {
    private import EngineElement::*;
    private import EngineWork::*;
    private import EngineVerification::*;
    private import EngineRelationships::*;

    part d0174 : Decision {
        :>> id = "49837275-c815-457a-9d52-30bd8894eb4d";
        :>> title = "D-P0a: the .claude/ surface is engine-derived, keel-scope-owned, ships with keel init, and owns the protected-path deny list";
        :>> createdAt = "2026-08-21";
        :>> createdBy = "claudeFable5";
        :>> status = DecisionStatus::accepted;
        :>> context = "The in-loop enforcement half (4 hooks, output style, permission rules) lives only in this repo's .claude/ and keel init scaffolds none of it (main.rs cmd_init @74ecefb); the 35 skills ship inside .engine/skills/ but land where no harness discovers them - shipped-but-undiscoverable. The output style exists precisely because CLAUDE.md was demonstrably ignored (issue084/085), yet downstream projects get only CLAUDE.md. Reviewed by a 9-member adversarial panel (2 pessimists, 2 optimists, 3 correctness critics, 1 reduction advocate, 1 systems engineer) across three rounds under an honesty rule; round 3 verdict 9 ACCEPT / 0 OBJECT, uncompelled. Full evidence and finding-to-resolution map: docs/proposals/2026-08-21-production-readiness-design.md sections 10-12. NOTE per the 2026-08-14 panel precedent (.tracking/panel-critiques.sysml): the panelists are subagent contexts of the authoring model, a rigor framing, NOT independent critics - this record claims convergence, never critic-independence.";
        :>> decision = "keel init scaffolds .claude/settings.json with five hook events including SubagentStop, the keel output style, keel-owned permission rules and the protected-path deny list (owned HERE; D-P1a owns only the ask/override/matcher semantics layered on top), one .claude/skills entry per skills-registry entry with counts asserted equal, an optional single-vendor CI workflow template (validate + guard + rules + audit-history; the rules step activates with D-P1b), and the fire-ledger emit plumbing (.keel/metrics). The scaffolded tree is a computed view: keel sync-claude deep-merges keel-owned entries only, stamps the generator version, and its --check IS the drift guard - one implementation, one surface. Adoption profiles are DECLARED, never inferred: keel init --profile strict|guided, recorded as a model-visible fact; default strict only for a provably empty directory. SubagentStop gates only when the tree fingerprint changed during the subagent's lifetime (baseline at first PreToolUse per session), degrading to systemMessage. keel hardening is extended to enumerate every enforcement point with its absent/error/timeout behavior.";
        :>> rationale = "The dominant production gap is not missing machinery but unshipped machinery: two years of in-loop engineering (D0128-D0134) exists and does not reach any downstream project, which is the difference between keel-the-methodology and keel-the-product. Treating .claude/ as a computed view of .engine keeps text-is-truth intact while making the surface regenerable; byte-equality drift checking would flag every legitimate downstream customization (settings.json is mixed-ownership by construction), so ownership is key-scoped. Profiles answer the only field data that exists - issue089 and issue129, two downstream lockouts in one week, both existing-repo adoptions - by making the strict default reachable only where init_smoke proves the tree starts green.";
        :>> consequences = "Downstream projects move from CLAUDE.md-text-plus-commit-gate to the full four-layer stack. Acceptance is behavioral on Windows and Linux, not presence-based: a protected .tracking write is refused with the sanctioned command named; a commit with the binary absent blocks with remedy text; skills are discoverable in a live session; sync-claude --check green; hooks demonstrably fire (fire-ledger evidence) in a spawned claude -p session; the hardening inventory lists every enforcement point; the profile fact is recorded. Charters the p0* backlog tasks.";
    }

    // acceptance event (D0121 review-queue sign-off; D0066/D0106 — human-judged, not fabricated)
    verification d0174Accept : Test { :>> id = "6f9e37e7-9563-4732-a0fd-e66d0c8fd306"; :>> method = VerificationMethod::confirmation; :>> procedureText = "Their words, verbatim: 'accepted all'. Said in response to the presented queue of fifteen proposed Decisions - D0174, D0175, D0176, D0177, D0178, D0179, D0180, D0181, D0182, D0183, D0184, D0185, D0186, D0187, D0188 - so 'all' is that queue and this acceptance covers this Decision as one of the fifteen. The open fork stated in the proposal (section 8-A, strict default for provably empty directories) was named to them alongside the queue with the invitation to object on D0174; they accepted without objection, so D0174 is accepted AS WRITTEN including its stated strict-for-empty default."; }
    part d0174AcceptR1 : TestResult { :>> id = "f3b105bb-8bf1-4448-ab0a-b1bc8ca8dc14"; :>> outcome = VerdictKind::pass; :>> judgedAgainst = "10b66bd"; :>> judgedAt = "2026-08-21"; :>> judgedBy = "wweatherholtz"; }
}
