// D0214 (status: the `status` field below is the truth) — warningsAreRead: the guard verdict states its warning population, and a superseded Release stops warning - detected-but-unread is the drift, not under-detection
// Recorded via `keel record decision` (D0105 RMWX axis; issue054). Acceptance is a separate explicit
// human gate (method=confirmation, D0106): flip status + add the d0214Accept event on sign-off.
package ReferenceDecision0214 {
    private import EngineElement::*;
    private import EngineWork::*;
    private import EngineVerification::*;
    private import EngineRelationships::*;

    // #ProspectiveChange (D0070) - this Decision governs a process/schema change; the co-committed
    // change rides the process-change guard's hard lock.
    #ProspectiveChange part d0214 : Decision {
        :>> id = "4b58a07b-04ab-412b-bde5-d7e3f685c41b";
        :>> title = "warningsAreRead: the guard verdict states its warning population, and a superseded Release stops warning - detected-but-unread is the drift, not under-detection";
        :>> createdAt = "2026-08-24";
        :>> createdBy = "claudeFable5";
        :>> status = DecisionStatus::accepted;
        :>> context = "The human asked why reports keep drifting from truth. The 2026-08-24 nine-lens panel's reducer gave the sharpest answer, measured: 'keel guard' printed the bare words [guard] ALL PASS while emitting 80 warnings across 10 guards, and one of those warnings was itself a live report-vs-truth contradiction that had shipped and gone unread - 'tag v0.2.0 points at e2c812f but its Release item records commit 425145d'. I read ALL PASS and skated past those warnings repeatedly in the same session, including in commits whose messages claimed the gate was clean. The panel explicitly REFUSED to add a new drift detector on the grounds that this engine already detects more than it triages, so another detector makes the felt problem worse; the fix had to be subtractive. Investigating the specific warning surfaced a second defect: the release-recorded guard did not honor #Supersede, and superseding is the ONLY correction path available to a non-owner (D0108), so that warning was unresolvable by construction - permanent noise that trained me to ignore the whole class.";
        :>> decision = "TWO changes, both subtractive. (1) The guard verdict line STATES ITS WARNING POPULATION: instead of the bare word ALL PASS, it reads 'ALL PASS - N warning(s) across M guard(s), NOT violations and NOT blocking, but UNREAD until someone reads them: <guard names>'. No new surface, no new computation, no new cost - the number appears where the verdict is already read, so ALL PASS can no longer be read without also reading how much went unread. (2) The release-recorded guard EXCLUDES a Release carrying an inbound #Supersede edge, matching what the sibling views already do for superseded Needs (issue088), requirements (issue127) and tasks (issue100). A guard whose warning cannot be cleared through the engine's own sanctioned correction mechanism is a guard that will warn forever. NOT DONE and deliberately so: no new detector, no new gate, no promotion of any warning to blocking - D0098 keeps completeness off the commit path and the panel's argument is that the marginal detector now subtracts value.";
        :>> rationale = "Detected-but-unread grows with every control added, which makes it the one drift mechanism that gets WORSE as assurance work proceeds - the opposite of the usual assumption. Stating the population at the point of the verdict is the honest-surface shape (N-C2) applied to the loudest surface in the engine: a bare pass hid a measured number. The supersede fix is the same class as three already-accepted fixes, so it is consistency rather than novelty, and it is what makes the first change actionable instead of merely louder - a warning population that CANNOT go down is noise no matter how prominently it is printed.";
        :>> consequences = "COUNTS MOVED and both sides are reported, as issue127's precedent requires: release-recorded went 5 scanned / 1 warning -> 5 scanned / 0 warnings, and the whole-suite total went 82 warnings across 11 guards -> 79 across 9. The extra delta is two priority-inversion warnings that this same work cleared honestly: appending two follow-on items above a High-issue resolver had silently re-prioritized them, the guard caught it, and the backlog was reordered rather than the warning explained away. The v0.2.0 tag disagreement is triaged rather than suppressed: git shows the recorded commit IS an ancestor of the tag two commits back, so the record was true when written and the tag was cut later; the tag is published and must not move (D0129), and release020 is owned by another actor, so a new release020Shipped records the shipped commit and SUPERSEDES the field - the sanctioned non-owner correction. Resolves issue244.";
    }

    // acceptance event (D0121 review-queue sign-off; D0066/D0106 — human-judged, not fabricated)
    verification d0214Accept : Test { :>> id = "f46ed4a1-f41a-49d4-bbc4-564f45f1360c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/11."; }
    part d0214AcceptR1 : TestResult { :>> id = "61f7338a-64b1-4545-adda-388076117341"; :>> outcome = VerdictKind::pass; :>> judgedAgainst = "3669487"; :>> judgedAt = "2026-08-24"; :>> judgedBy = "wweatherholtz"; }
}
