// D0438 (status: the `status` field below is the truth) — verifierProcedureIsTheTestVerifySkill: the D0425 verifier's procedure and mandate are the deployed test-verify skill, and a dispatch names the skill, the sprint's probe pair and nothing else
// Recorded via `keel record decision` (D0105 RMWX axis; issue054). Acceptance is a separate explicit
// human gate (method=confirmation, D0106): flip status + add the d0438Accept event on sign-off.
package ReferenceDecision0438 {
    private import EngineElement::*;
    private import EngineWork::*;
    private import EngineVerification::*;
    private import EngineRelationships::*;

    // #ProspectiveChange (D0070) - this Decision governs a process/schema change; the co-committed
    // change rides the process-change guard's hard lock.
    #ProspectiveChange part d0438 : Decision {
        :>> id = "8ebf64ba-31af-4d56-98eb-596d57af3030";
        :>> title = "verifierProcedureIsTheTestVerifySkill: the D0425 verifier's procedure and mandate are the deployed test-verify skill, and a dispatch names the skill, the sprint's probe pair and nothing else";
        :>> createdAt = "2026-09-11";
        :>> createdBy = "claudeOpus5";
        :>> status = DecisionStatus::accepted;
        :>> context = "D0425 farmed verification out to a subagent in its own context, and D0432 named its test run as keel suite --touched. What the verifier does with that command - launch it detached because the harness caps a foreground call at ten minutes and the run takes seven to twelve, read the receipt only after the process exits, check outcome against running, at against the launch time, stems against the changed keel-cli/src files, lib against whether any of them moved, then validate, check-engine, guard --no-receipt, sync-claude --check, clippy, the D0388 probe pair, and the receipt shape the recorder reads - lived only in the primary's dispatch prompt and was retyped every sprint. Two in-field Issues in one sprint came from that: issue469, the verifier ran the touched set in the foreground and the cap killed it eleven minutes in; issue471, a verifier told in prose to edit nothing found a red guard, hand-wrote two malformed triage statements onto red-yield obligations, and reported a validate result read before its own edit, which put parser-coverage red (obligation01af4c5d). D0040 names the class: a recurring task done without a skill leaks its process into conversation history, where it cannot be enforced, reviewed or improved. The test-verify skill predated both D0425 and keel suite --touched and still named cargo test at the repo root.";
        :>> decision = "NOT A FORK: D0040 says a recurring procedure is a skill, and the two Issues are the evidence this one recurs. The test-verify skill IS the D0425 verifier's procedure. It states the verifier's mandate first - it reads and runs, it writes nothing under .tracking, .engine, keel-cli, .claude or CLAUDE.md, it records no TestResult, and a write it believes is owed is a line under OWED WRITES in its receipt for the recorder - and then the procedure in order: the touched run launched detached with the launch epoch recorded, the rest of the gate set while it runs, the dispatch's probe pair by name, clippy with TIMEOUT reported when the build lock holds it, the touched receipt read only after the process exits with each honesty check (outcome, at, stems, lib, head) its own receipt line, and the receipt written to the scratchpad path the dispatch names in a fixed shape. The primary's dispatch names the skill, the binary to run, the receipt path, the sprint's probe pair and any guard it expects red, and nothing else about how to verify.";
        :>> rationale = "The verifier's independence is worth nothing if its procedure is whatever the primary typed that sprint: a retyped procedure drifts, omits the step the primary was not thinking about, and cannot be corrected once for every future dispatch. Both Issues were omissions of that kind - detach, and do not write - and each is now one table row every verifier reads before its first command. The skill is the same registry unit the process-skill guard already checks, sync-claude deploys it, and the two cases that would show a regression are named: a dispatch with the skill alone must complete a touched run that exceeds ten minutes and report from its own receipt (issue469's case), and must leave git status unchanged by its own hand (issue471's case). What would change it: a verifier that follows the skill and still writes to the tree - then the control belongs in the harness (a read-only subagent tool set), not in a skill.";
        :>> consequences = "The test-verify skill is rewritten in place (version 0.2.0) and its registry purpose and trigger say what it now is; sync-claude redeploys it. CLAUDE.md sec 4's D0425 rule names the skill as the verifier's procedure. The build skill's hand-off to test-verify stands. No guard changes. Process-change (D0337): it changes what the D0425 verifier does, so it stays proposed for the human's word; the skill is usable under D0425 as accepted meanwhile because D0425 already binds the verifier to run the checks, and this Decision fixes how. issue469, issue471 and obligation01af4c5d resolve on dcVerifierProcedureIsASkill, which this Decision governs. What accepting binds: every verifier dispatch runs one procedure that can be corrected once. What it forecloses: a verifier whose steps were chosen at dispatch time.";
    }

    // acceptance event (D0121 review-queue sign-off; D0066/D0106 — human-judged, not fabricated)
    verification d0438Accept : Test { :>> id = "f121da5c-ef0b-48a3-9845-a18fa28056e8"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0438 (D0201 B); recorded as given (D0423)."; }
    part d0438AcceptR1 : TestResult { :>> id = "d301ef54-04a5-4bdb-8eaf-361d8821f500"; :>> outcome = VerdictKind::pass; :>> judgedAgainst = "3e6c518"; :>> judgedAt = "2026-09-11"; :>> judgedBy = "wweatherholtz"; :>> createdBy = "claudeOpus5"; }
}
