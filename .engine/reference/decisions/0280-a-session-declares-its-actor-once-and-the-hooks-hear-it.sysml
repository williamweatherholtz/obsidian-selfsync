// D0280 (status: the `status` field below is the truth) — A session declares its actor once and the hooks hear it - the per-session binding, and the ownership defect leaving the registry
// Recorded via `keel record decision` (D0105 RMWX axis; issue054). Acceptance is a separate explicit
// human gate (method=confirmation, D0106): flip status + add the d0280Accept event on sign-off.
package ReferenceDecision0280 {
    private import EngineElement::*;
    private import EngineWork::*;
    private import EngineVerification::*;
    private import EngineRelationships::*;

    // #SafetyChange (D0070) - this Decision governs a process/schema change; the co-committed
    // change rides the process-change guard's hard lock.
    #SafetyChange part d0280 : Decision {
        :>> id = "58c6f380-2623-494d-86b4-7b2c9b83d9cb";
        :>> title = "A session declares its actor once and the hooks hear it - the per-session binding, and the ownership defect leaving the registry";
        :>> createdAt = "2026-09-01";
        :>> createdBy = "claudeOpus5";
        :>> status = DecisionStatus::accepted;
        :>> context = "KEEL_ACTOR is set per command in the session's shell. Every hook is spawned by the harness in the harness's environment, where that variable was never set, so actor::resolve fell through to the MACHINE binding - and on a machine two models share, the binding named the other one. Under the Stop hook 22 edits were attributed to the wrong actor and 12 items the session owned were flagged as non-owner edits, burying the 10 real ones (issue337, which supersedes issue332's wrong diagnosis). The rigor panel established at file:line that the ownership guard's predicate was correct and the identity simply had no path to it. This Decision is co-committed because the fix removes an entry from control-defects.toml, which the keystone lock covers - and rightly: removing a defect note is a weakening-shaped act even when the defect is gone.";
        :>> decision = "A per-session actor binding at .keel/sessions/<session-id>/actor, machine-local and gitignored like every .keel runtime file. Any keel command that resolves its actor from KEEL_ACTOR remembers it there, idempotently. actor::resolve reads it AFTER an explicit actor and KEEL_ACTOR and BEFORE the machine binding. The hook dispatcher seeds CLAUDE_CODE_SESSION_ID from the payload's session_id when the environment lacks it, so the binding is found under the key the session's own commands wrote. The session id is validated as UUID characters before it becomes a path. The ownership entry leaves the D0278 registry in the same commit, as that process requires.";
        :>> rationale = "WHY A SESSION BINDING AND NOT A CORRECTED MACHINE BINDING. The machine binding was not wrong for the session that set it; it was wrong for THIS session, and two models genuinely share this machine. One binding cannot be right for both, and re-binding the machine each session is the manual step D0047 says is not a control. WHY THE KEY IS SAFE TO RELY ON: the harness gives both sides the same id - CLAUDE_CODE_SESSION_ID in the shell, session_id in every hook payload - checked equal against the id the Stop hook had itself written into an obligation record hours earlier. WHY resolve() IS ALLOWED A WRITE SIDE-EFFECT, which is normally wrong: the alternative is a command every session must remember to run; the write records only what the session itself declared, is idempotent so a hook firing every turn cannot churn it, and a failure to write leaves the hooks on the machine binding - today's behaviour, never worse. REJECTED, parsing KEEL_ACTOR out of the pre-bash hook's command text: fragile, and it would attribute on the basis of a shell string rather than a resolution the write paths actually performed. WHY THE REGISTRY ENTRY LEAVES HERE AND NOT LATER: D0278 requires removal in the commit that resolves the Issue, because a note outliving its defect is how a true warning becomes noise - and the ownership guard was announcing a defect it no longer has.";
        :>> consequences = "Hook-run guards attribute edits to the session's declared actor. Live, read back: with KEEL_ACTOR unset, `keel actor` answers the session's actor, not the machine's. The D0278 registry holds two entries after this - issues and decision-scaffolding - both under-reporting, both carried for reasons that still stand. TWO THINGS STATED RATHER THAN LEFT. First: control-defects.toml is under the keystone lock, so every control-defect resolution that does not otherwise touch guard source needs a Decision like this one; that friction is accepted because the alternative - a registry anyone can silently empty - defeats the registry. Second: issue332's carry-reason was 'guard source under the keystone lock' and it was wrong; actor.rs and the dispatcher are not on D0209 clause 2's surface, so this defect could have been fixed the hour it was found. The control-defect process names an unjustified carry as its unacceptable case, and this was one.";
    }

    // acceptance event (D0121 review-queue sign-off; D0066/D0106 — human-judged, not fabricated)
    verification d0280Accept : Test { :>> id = "d574c682-23e6-44bf-a66d-093449052bcc"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0280AcceptR1 : TestResult { :>> id = "9a8c842b-1dc6-4e79-9db3-26912063328d"; :>> outcome = VerdictKind::pass; :>> judgedAgainst = "6eafa86"; :>> judgedAt = "2026-09-02"; :>> judgedBy = "wweatherholtz"; }
}
