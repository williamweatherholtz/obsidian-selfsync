// D0321 (status: the `status` field below is the truth) — processStepsBindToChecks: whether a ProcessStep may declare the guard that checks it, and whether analytical prose becomes structure controls can read
// Recorded via `keel record decision` (D0105 RMWX axis; issue054). Acceptance is a separate explicit
// human gate (method=confirmation, D0106): flip status + add the d0321Accept event on sign-off.
package ReferenceDecision0321 {
    private import EngineElement::*;
    private import EngineWork::*;
    private import EngineVerification::*;
    private import EngineRelationships::*;

    // RESEARCH: Measured 2026-09-05 with keel show hardening: 37 processes, 15 ENFORCED (assert at least one guard somewhere), 10 declared UNENFORCEABLE in process-enforcement.toml with a reason, 12 UNDECLARED. 'Enforced' means the process names a guard, not that any step has a check; only agile-workflow's ceremony steps carry per-step gates, which is why keel advance --to can refuse there and nowhere else. The 12 undeclared, each read against its steps: controlDefect (checkable - control-defect-registry, guard 57, is its register step's predicate); controlPropriety (judgment - whether a control is proper is the finding; its output Decision is gated like any fact); decisionSurfacing (checkable - judgment-request-quality, guard 48, checks the fork's shape; the one-URL publish is readable from deck); githubIntake (mixed - the verbatim ingest is unenforceable, the routing steps are untrusted-routing 56 and untrusted-taint 63); libraryStewardship (checkable - unit-extras-present 60 and manifest-key-portability 53); migration (checkable - the control totals marker-census computes are exactly what the process requires, an admitted gap since D0067); obligationReview (judgment by decision - D0204 says sitting review is never owed, so a check would contradict the process); projectMigration (mixed - the preflight step is adoption-check --vintage, the rest is reading a foreign project's CI); projectOnboarding (judgment - a person's understanding); reviewCritique (judgment - critique quality, the same shape as the declared critique); stpaDiagram (checkable - viewpoint-renderer 12 holds that the renderer exists; the drawing is judgment); stpaSelf (checkable - stpa-currency 62). Net: 7 could bind at least one step to an existing guard today, 4 join the declared judgments, 1 (githubIntake) does both. Prior art: process-enforcement.toml (D0173) already declares per-PROCESS enforceability in a contract; agile-workflow's per-step gates (D0209 clause 3) are the only per-step binding and are hand-coded in advance; D0303 counts a Decision's clauses by regex and D0311 counts a retro's citations by grep - both read prose because the facts have no structure to read. Outside: BPMN's gateway conditions and Camunda's execution listeners bind a step to a predicate in the model, not beside it.
    part d0321 : Decision {
        :>> id = "80b16cb8-8f6b-48d6-8fbf-5e2875c24a51";
        :>> title = "processStepsBindToChecks: whether a ProcessStep may declare the guard that checks it, and whether analytical prose becomes structure controls can read";
        :>> createdAt = "2026-09-05";
        :>> createdBy = "claudeOpus5";
        :>> status = DecisionStatus::accepted;
        :>> context = "The panel's process-authority finding (rigorProcessAuthorityCritique) and fact-lifecycle finding (rigorFactLifecycleCritique) share one root: a process is a document with an optional guard, not a machine, because a ProcessStep has no binding to a predicate and everything analytical lives in a String field no control can read. Authoring outruns enforcement - five processes authored in the last week are undeclared - and only the author's memory converts a step into a check. Both remedies are schema questions under the frozen core, so this is a FORK the human owns: it changes what a Process IS.";
        :>> decision = "OPTION A (checkedBy on the step): ProcessStep gains `checkedBy : String [0..1]` naming a guard or declared rule; hardening reports per-STEP enforcement (checked / declared judgment / undeclared) instead of per-process; a guard `step-check-resolves` holds that every named check exists in GUARD_NAMES or rules.sysml; `keel advance <process> --to <step>` generalises the ceremony refusal to any step with a binding. The 7 bindable processes above are annotated in the same change; the 4 judgments and obligationReview keep their contract declaration. COST: a frozen-core schema change (this Decision plus a D0067 expand/migrate/contract with control totals over 37 processes and ~180 steps), advance's ceremony table becomes data, the hardening lens changes shape, and every future step is either bound, declared, or counted undeclared - the honest cost is that authoring a step now asks a question. OPTION B (A, plus analytical facts as structure): as A, and a Decision's clauses become addressable children (`d0313C1`), a retro's findings become Issue items by construction rather than by grep, so D0303's clause counter and D0311's citation grep become edge reads. COST: A's cost plus a second schema type (DecisionClause), record decision --from and new sprint --fill growing structured sections, forward-only from the cutoff (re-splitting 320 Decisions is the D0129 class and is not done); the largest change to the writing surface since D0301, and the one that makes the two prose-reading controls unnecessary. OPTION C (a contract, no schema): `.engine/contracts/process-checks.toml` maps process step -> guard, read by hardening and advance exactly as A would read the attribute; no frozen-core change. COST: smallest - one contract and two readers - but the binding lives beside the process rather than in it, a second home for a fact about the step (D0105), resynced by migrate as engine content, and a step renamed in the process file silently orphans its binding.";
        :>> rationale = "WHY NOT DECIDE THIS AUTONOMOUSLY: it changes the frozen core and what a Process means, and B changes how the human's own Decisions are written. WHAT I RECOMMEND, AND WHAT WOULD CHANGE IT: OPTION A. The measurement says the binding is possible today for 7 of the 12 undeclared processes using guards that already exist - the gap is a place to write the fact, not a missing check - and the attribute is that place; C puts the same fact in a second file, which is the D0105 shape that made process-enforcement.toml a stopgap, and B is the right direction but a second schema type on top of A's migration is more than one Decision should carry (D0303). It stops recommending A if the human wants no frozen-core change this quarter (then C, as an expand step that A can later contract into) or wants the prose-reading controls gone now (then B, in two Decisions).";
        :>> consequences = "Until accepted: nothing changes; dcProcessStepsBindToChecks's own DoD is this proposal and passes when judgment-request-quality accepts it. On A: a schema Decision, a D0067 migration over the process files, hardening per step, advance generalised, and the 7 bindings authored. The per-process contract stays for the judgments. STATED: whichever option, a step bound to a guard is enforced only as far as that guard is - a binding names the control, it does not make it good (D0254).";
    }

    // acceptance event (D0121 review-queue sign-off; D0066/D0106 — human-judged, not fabricated)
    verification d0321Accept : Test { :>> id = "cf5334eb-b19b-424f-a6fd-eab92a4db129"; :>> method = VerificationMethod::confirmation; :>> procedureText = "OPTION A chosen (checkedBy on the ProcessStep). their words, verbatim, two lines with the line break rendered as ' / ': 'd0312 B / d0321 A'"; }
    part d0321AcceptR1 : TestResult { :>> id = "2cd56506-83b1-48a2-a661-10cb491a0fdf"; :>> outcome = VerdictKind::pass; :>> judgedAgainst = "811be12"; :>> judgedAt = "2026-09-05"; :>> judgedBy = "wweatherholtz"; :>> createdBy = "claudeOpus5"; }
}
