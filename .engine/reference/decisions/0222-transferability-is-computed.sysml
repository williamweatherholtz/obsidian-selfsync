// D0222 (status: the `status` field below is the truth) — transferabilityIsComputed: keel process audit answers whether every unit lands GREEN elsewhere, and the answer was 23 of 24 NO
// Recorded via `keel record decision` (D0105 RMWX axis; issue054). Acceptance is a separate explicit
// human gate (method=confirmation, D0106): flip status + add the d0222Accept event on sign-off.
package ReferenceDecision0222 {
    private import EngineElement::*;
    private import EngineWork::*;
    private import EngineVerification::*;
    private import EngineRelationships::*;

    // #ProspectiveChange (D0070) - this Decision governs a process/schema change; the co-committed
    // change rides the process-change guard's hard lock.
    #ProspectiveChange part d0222 : Decision {
        :>> id = "27b00bb4-0d8b-45c8-a40a-a28cea688a1c";
        :>> title = "transferabilityIsComputed: keel process audit answers whether every unit lands GREEN elsewhere, and the answer was 23 of 24 NO";
        :>> createdAt = "2026-08-24";
        :>> createdBy = "claudeFable5";
        :>> status = DecisionStatus::accepted;
        :>> context = "The human, before migrating to penumbra: 'fix keel, then we will migrate. not wanting to put the cart before the horse. i want a good transition. do a final pass to check if everything is easily transferrable.' Twice in the preceding hours a unit had been DECLARED transferable and was not - the channel left its whole mechanism behind (issue251), then left behind the declaration binding skill to process (issue252) - and BOTH were found by actually adopting, never by reading the export. So the honest answer to 'is everything transferable' could not be my reading of the tree; it had to be a computation, and the computation said NO for 23 of 24 units: each carried its process definition and its SKILL.md while the entry binding them stayed in the shared central registry, which cannot travel with one unit. Every adoption into a project lacking that process would have failed process-skill on arrival.";
        :>> decision = "TRANSFERABILITY IS COMPUTED, not asserted: process audit: would each unit land GREEN in a project that lacks it? (D0222) a unit TRAVELS WHOLE when it carries its definition, its deploying skill, and the declaration binding them - plus every extra it declares. Anything else lands red. [TRAVELS-WHOLE] actor-enrollment (3 file(s)) [TRAVELS-WHOLE] adversarial-panel-review (3 file(s)) [TRAVELS-WHOLE] agile-workflow (5 file(s)) [TRAVELS-WHOLE] architectural-critique (3 file(s)) [TRAVELS-WHOLE] business-elicitation (3 file(s)) [TRAVELS-WHOLE] decision-authoring (3 file(s)) [TRAVELS-WHOLE] decision-channel (7 file(s), 3 stated prerequisite(s)) [TRAVELS-WHOLE] definition-of-done (3 file(s)) [TRAVELS-WHOLE] definition-of-ready (3 file(s)) [TRAVELS-WHOLE] deploy (3 file(s)) [TRAVELS-WHOLE] diagram (3 file(s)) [TRAVELS-WHOLE] distributed-collaboration (3 file(s)) [TRAVELS-WHOLE] doc-sync (3 file(s)) [TRAVELS-WHOLE] element-critique (3 file(s)) [TRAVELS-WHOLE] indicator (3 file(s)) [TRAVELS-WHOLE] intake (3 file(s)) [TRAVELS-WHOLE] introduction (3 file(s)) [TRAVELS-WHOLE] issue-resolution (3 file(s)) [TRAVELS-WHOLE] knowledge-graph-memory (3 file(s)) [TRAVELS-WHOLE] migration (3 file(s)) [TRAVELS-WHOLE] obligation-review (3 file(s)) [TRAVELS-WHOLE] render (3 file(s)) [TRAVELS-WHOLE] report (3 file(s)) [TRAVELS-WHOLE] review-critique (5 file(s)) process audit: every unit travels whole. reports, per unit, whether it would land GREEN in a project that lacks it, and names the reason when it would not. It checks that a deploying skill exists, that the declaration BINDING skill to process travels, that every declared extra is present on disk, and that no carried file cites a path the adopter will not have. It is a REPORT and not a gate, because a project may legitimately hold units it never exports. On the strength of it, three fixes: (1) a committed migration transform MOVES all 36 AISkill declarations out of the shared registry into beside the skill each describes, reconciled 36 found = 36 moved = 0 skipped and verbatim so ids and provenance are unchanged; (2) RETIRES a central declaration an incoming per-skill file supersedes, announced on stdout, because otherwise a project on an older engine - penumbra exactly - gets the same id in two files and duplicate-identity fails on arrival; (3) the stale references are swept, including a process still naming the Smartsheet tap-inbox tooling D0206 RETIRED.";
        :>> rationale = "A portability claim nobody can re-derive is precisely the class this engine exists to kill, and I had made that claim twice and been wrong twice. Making it a computation converts 'I looked and it seems fine' into a number any project can reproduce before it promises anything - and the number was 23 of 24, which no amount of reading would have produced. The migration is a MOVE rather than a copy because duplicate-identity refuses a copy, which is what proves the ids were preserved rather than re-minted. Import retiring the superseded duplicate writes to a shared file where import otherwise refuses to, and that is defensible only because removing an exact-id duplicate is DETERMINISTIC - there is no question what to delete - whereas appending content could conflict.";
        :>> consequences = "The audit went 23 LANDS-RED of 24 to 0: every unit travels whole. Verified by ADOPTION rather than by re-reading: intake, migration, obligation-review and agile-workflow were each exported and imported into a fresh project that lacked them, and each left that project at [guard] ALL PASS; the penumbra case specifically - a project declaring the skill centrally from an older engine - was simulated and the import announced 'retired the superseded central skills-registry declaration for intakeSkill' with duplicate-identity clean afterwards. The audit itself was NARROWED TWICE against the real corpus after over-flagging: a directory convention ('write a codemod under .engine/tools/migrations/') and a placeholder ('<script>.py') are not dead references, and a check that fires on true prose gets bypassed. 260 tests, all gates green. Resolves issue253. FOUND AFTER RECORDING, and recorded here rather than left out: the central registry had FOUR readers and I fixed one before migrating, then found the rest as each broke - the same-rule-in-N-places class, where the systematic grep should have come first. (a) claude_surface::registry_skills read only the central file, so sync-claude reported 0/0 skills the moment the declarations moved and claude-surface-drift then passed VACUOUSLY on a population of zero - a false green, worse than the failure it hid. (b) is_engine_instance_file did not recognise a per-skill registry.sysml, so check-engine reported CLEAN over 36 files it was never reading - coverage that reads exactly like coverage. (c) With (b) fixed, check-engine immediately caught a real defect: the ONE hand-written registry file (decision-channel, written before the transform existed) was missing `private import EngineSkills::*` so AISkill was unresolved, while all 36 transform-generated files carried the import from the start - the transform got it right and I did not, which is the argument for the transform.";
    }

    // acceptance event (D0121 review-queue sign-off; D0066/D0106 — human-judged, not fabricated)
    verification d0222Accept : Test { :>> id = "fdbcc950-44ad-491b-a445-a0beb97f0be6"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/20."; }
    part d0222AcceptR1 : TestResult { :>> id = "2d21b951-9aa4-4579-a40b-424d8a1de2da"; :>> outcome = VerdictKind::pass; :>> judgedAgainst = "43a7b10"; :>> judgedAt = "2026-08-24"; :>> judgedBy = "wweatherholtz"; }
    part d0222AcceptR2 : TestResult { :>> id = "ad9929c8-fde7-4398-81e4-5a1a31faa5fa"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences gained a FOUND AFTER RECORDING note at 43a7b10 - editorial, the agreed substance unchanged. Their standing words, verbatim: 'issues raised are automatically accepted. they can be customizedly changed post-fact.'"; }
}
