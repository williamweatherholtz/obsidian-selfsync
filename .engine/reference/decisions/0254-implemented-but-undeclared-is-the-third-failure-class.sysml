// D0254 (status: the `status` field below is the truth) — The launcher's single-writer refusal becomes a declared control, and implemented-but-undeclared is named as its own failure class
// Recorded via `keel record decision` (D0105 RMWX axis; issue054). Acceptance is a separate explicit
// human gate (method=confirmation, D0106): flip status + add the d0254Accept event on sign-off.
package ReferenceDecision0254 {
    private import EngineElement::*;
    private import EngineWork::*;
    private import EngineVerification::*;
    private import EngineRelationships::*;

    // #ProspectiveChange (D0070) - this Decision governs a process/schema change; the co-committed
    // change rides the process-change guard's hard lock.
    #ProspectiveChange part d0254 : Decision {
        :>> id = "05b849d5-cfc0-479e-9b73-e42800bb4d57";
        :>> title = "The launcher's single-writer refusal becomes a declared control, and implemented-but-undeclared is named as its own failure class";
        :>> createdAt = "2026-08-29";
        :>> createdBy = "claudeOpus5";
        :>> status = DecisionStatus::accepted;
        :>> context = "D0253 established that eight of nine declared controls had never been observed to fire, and that their classification had been made against a read-only view's constraints rather than against whether the property is verifiable. The write lock was then proven by test. Turning the same question on the launcher produced a worse answer. `keel enforcement-report` reports `launcherFraction: unavailable - no run records yet`; `.keel/runs/` does not exist; `launcher::prepare` and `launcher::finish` are called from exactly one place, inside serve.rs's SSE handler, and have never once been invoked. The module's own doc says these are 'the parts that must be TESTABLE outside the SSE stream' - they were made testable and never tested. Probing them shows the mechanism works: on a clean tree `prepare` succeeds and captures the spawn-time HEAD (K12); on a dirty tree it REFUSES naming the reason (D0182 single-writer); `finish` writes a machine-local record carrying all fourteen declared fields, and a run whose diff is empty writes no tracked summary. THEN THE ACTUAL FINDING. `.tracking/architecture/control-map.sysml` declares NINE controls - ctlAuditHistory, ctlBranchProtection, ctlCommitGate, ctlFireLedger, ctlPrePushBehind, ctlPreWriteTiers, ctlReleaseGateJob, ctlReverify, ctlWriteLock - and the launcher's single-writer refusal is not among them. A grep for launch, dirty or singleWriter across the map returns nothing. The control is implemented, load-bearing and now proven, and the model does not know it exists.";
        :>> decision = "Three clauses. CLAUSE A - THE REFUSAL IS A DECLARED CONTROL. `ctlLaunchDirtyRefusal` enters the control map: a launch onto a dirty tree is refused, so a run's diff is attributable to that run alone. It carries `provenBy` naming the test that exercises it (D0253 clause A), and is the first control declared as proven-by-test at birth rather than retrofitted. CLAUSE B - IMPLEMENTED-BUT-UNDECLARED IS A NAMED FAILURE CLASS, distinct from the two already known. Declared-but-never-fired (D0217) is visible to a reader who looks. Declared-and-unprobeable (D0253) is visible as a classification. Implemented-but-undeclared is visible to NOBODY: `keel controls` computes over declared controls and declared hazards, so an undeclared control cannot appear as a gap, and neither can a hazard only that control covers. `uncoveredHazards: []` is therefore not evidence of coverage - it is evidence about the declaration. CLAUSE C - THE SWEEP IS TRACKED, NOT PERFORMED HERE. issue304 records that the control map has never been reconciled against the enforcement the binary actually implements. One control was found by asking about one mechanism; the map has nine entries and the binary has fifty-three guards, six hook events, a write lock, a launcher and a push gate. The gap is not estimated here, because estimating it is the work.";
        :>> rationale = "WHY THIS IS THE MOST DANGEROUS OF THE THREE CLASSES, and why it deserves its own name rather than being folded into D0253. The other two produce a signal a careful reader can find: a control listed as not-machine-checkable is at least LISTED. An undeclared control produces no signal at all, and worse, it makes the coverage view read cleaner - fewer declared controls with no gaps looks better than more declared controls with gaps. The measure improves as the map gets less complete. That is the failure mode this project has recorded twice already, in issue088 and issue240: a number that is truthful about the question it asks and misleading about the question a reader has. WHY THE LAUNCHER SPECIFICALLY MATTERS. Every Need about bounded, approved process launching rests on this mechanism, and until today none of them had any evidence behind them. `unavailable` was also the wrong word in `enforcement-report`: it does not distinguish 'never invoked' from 'cannot be measured', and a reader takes it as the second when it was the first. That is the D0217 declared-versus-armed confusion at the metric layer rather than the control layer. WHY DECLARE IT NOW RATHER THAN AFTER THE SWEEP. A control proven by test and still absent from the map would be the same defect, held knowingly. Declaring the one that has been proven costs nothing and makes the map's incompleteness the tracked residual rather than an unstated one. WHY THE SWEEP IS NOT ESTIMATED. Saying 'roughly N controls are missing' would put a number in the record that nothing computed, which is the habit the whole session has been correcting. issue304 states the question; the answer comes from doing it.";
        :>> consequences = "`keel controls` gains a tenth control. The ARMED census does not move - `checkable` still drives it, and this control is proven by TEST, not establishable by a read-only view (D0253's deliberate separation). The honest count becomes 3 of 10 with evidence: 1 armed by view-probe, 2 proven by test. The launcher's three behaviours now have tests that fail if they regress: the dirty-tree refusal, the spawn-time HEAD capture, and the fourteen-field run record. The record schema was declared exempt from existence checks by design, which meant nothing verified it; the field-by-field assertion is now what makes that exemption safe rather than merely stated. issue304 is open and unestimated: the control map has never been reconciled against the binary's actual enforcement surface. `.keel/runs/` still does not exist in this repository, and that is CORRECT - no run has been launched. The tests build their own throwaway repositories. What has changed is that the mechanism is now known to work, so the absence of run records means 'nobody has launched one', which is a different and much smaller problem than 'the launcher may not work'.";
    }

    // acceptance event (D0121 review-queue sign-off; D0066/D0106 — human-judged, not fabricated)
    verification d0254Accept : Test { :>> id = "77363343-4f2c-418e-bf3c-8c25411e0168"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0254AcceptR1 : TestResult { :>> id = "e048f123-a2a8-4ad6-b2ed-1ee10bd97fc9"; :>> outcome = VerdictKind::pass; :>> judgedAgainst = "e2876d6"; :>> judgedAt = "2026-08-29"; :>> judgedBy = "wweatherholtz"; }
}
