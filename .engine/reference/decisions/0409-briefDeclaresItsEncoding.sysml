// D0409 (status: the `status` field below is the truth) — briefDeclaresItsEncoding: a published page declares its charset in the first 1024 bytes and keeps its typographic characters; the executive-brief checker refuses a page that does not
// Recorded via `keel record decision` (D0105 RMWX axis; issue054). Acceptance is a separate explicit
// human gate (method=confirmation, D0106): flip status + add the d0409Accept event on sign-off.
package ReferenceDecision0409 {
    private import EngineElement::*;
    private import EngineWork::*;
    private import EngineVerification::*;
    private import EngineRelationships::*;

    // #ProspectiveChange (D0070) - this Decision governs a process/schema change; the co-committed
    // change rides the process-change guard's hard lock.
    #ProspectiveChange part d0409 : Decision {
        :>> id = "2a727006-968c-4c31-b2b0-a5c81bcda6ce";
        :>> title = "briefDeclaresItsEncoding: a published page declares its charset in the first 1024 bytes and keeps its typographic characters; the executive-brief checker refuses a page that does not";
        :>> createdAt = "2026-09-09";
        :>> createdBy = "claudeOpus5";
        :>> status = DecisionStatus::accepted;
        :>> context = "issue401, tracked as dcPagesDeclareTheirEncoding. The standing decision brief carried its typographic characters (curly quotes, en and em dashes, arrows, ellipses) as raw UTF-8 with no charset declaration. The artifact publisher wraps the file in its own head and supplies one, so every review from the publisher looked right; the file itself rendered mojibake on any host that sent Content-Type text/html with no charset parameter, because a browser given no declaration guesses, and on this host it guesses windows-1252. The executive-brief checker (scripts/check_templates.py check_brief) examined structure - ids, verb, asks, tabs, durations, members, figures - and had no clause about encoding, so a page unreadable on a guessing host passed it clean. Probe, 2026-09-09: a local HTTP server sending text/html with no charset served a constructed no-declaration page carrying those characters and the tabbed brief; the constructed page decoded as windows-1252 and its em dash read as three characters in the screenshot, the brief decoded as UTF-8 and read clean.";
        :>> decision = "NOT A FORK: the DoD asked me to weigh ASCII-with-entities against declaring the charset, and the weighing is settled by a fact already in the tree - every brief builder since 2026-09-08 (seven scripts under scripts/exec_brief/) emits <meta charset='utf-8'> as its first head element, so entities would be a second mechanism for a defect the first already fixes, and the checker clause is the only piece missing. The rule: a page declares <meta charset='utf-8'> (any quoting or case; the http-equiv Content-Type form also counts) within the first 1024 bytes of the file, which is the prescan window browsers read before they guess. The characters stay as characters. check_brief gains clause 0, reading the raw file's first 1024 bytes, refusing the page otherwise and naming the mojibake it prevents; the checker's brief fixture declares the charset by default and can be built without it, and the self-test carries three cases: no declaration refused, a declaration past the 1024-byte window refused, the http-equiv form passing.";
        :>> rationale = "Entities encode the fix into every character site and depend on every future builder remembering them; a declaration is one line at one place and is what the HTML standard names as the page's own authority when the transport says nothing. The defect class was a page that looked right where it was reviewed and wrong where it was read; the control that closes that class is one that reads the file as the host does - the first 1024 bytes, no transport help - which is what clause 0 does and what a visual review from the publisher can never do. The window is 1024 bytes and not the whole head because a declaration past it is one a browser may never see; the case that places it at byte 1100 is in the self-test so the boundary is a tested fact, not a comment.";
        :>> consequences = "scripts/check_templates.py: CHARSET_META, clause 0 in check_brief, the charset parameter on _brief_fixture, three self-test cases (18 to 21). .engine/skills/asi-templates/SKILL.md section 2.2 gains the rule so the contract names it where the builders are written; the .claude rendering follows through keel sync-claude. The standing tabbed page already passes the clause. A builder that omits the declaration is refused at check time, before publish; a page that is refused names the host condition that would have exposed it. The probe script that served both pages from a no-charset host is one-time and is not kept as a Sensor: its two cases and their outcomes are named in dcPagesDeclareTheirEncoding's DoD result, per D0388.";
    }

    // acceptance event (D0121 review-queue sign-off; D0066/D0106 — human-judged, not fabricated)
    verification d0409Accept : Test { :>> id = "79ad1560-ac9f-4762-a019-bcfc806e9c8e"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0409 (D0201 B); recorded as given (D0423)."; }
    part d0409AcceptR1 : TestResult { :>> id = "1f1f0fdc-56b0-45b8-b29c-f0b95741566a"; :>> outcome = VerdictKind::pass; :>> judgedAgainst = "3e6c518"; :>> judgedAt = "2026-09-11"; :>> judgedBy = "wweatherholtz"; :>> createdBy = "claudeOpus5"; }
}
