// D0459 (status: the `status` field below is the truth) — routeVerdictQuotesTheRequest: the routing rig gains a second judging step - a written six-question rubric a lower-capability model answers yes/no about the request, every yes quoting a verbatim substring of it; a verdict that cannot quote is refused, and a re-run's disagreement is a finding naming both quotes, never a rate
// Recorded via `keel record decision` (D0105 RMWX axis; issue054). Acceptance is a separate explicit
// human gate (method=confirmation, D0106): flip status + add the d0459Accept event on sign-off.
package ReferenceDecision0459 {
    private import EngineElement::*;
    private import EngineWork::*;
    private import EngineVerification::*;
    private import EngineRelationships::*;

    part d0459 : Decision {
        :>> id = "0ed9ddcd-b2b6-40af-ae2d-9c03625a1f91";
        :>> title = "routeVerdictQuotesTheRequest: the routing rig gains a second judging step - a written six-question rubric a lower-capability model answers yes/no about the request, every yes quoting a verbatim substring of it; a verdict that cannot quote is refused, and a re-run's disagreement is a finding naming both quotes, never a rate";
        :>> createdAt = "2026-09-12";
        :>> createdBy = "claudeFable5";
        :>> status = DecisionStatus::accepted;
        :>> context = "The routing rig (routing_probe.py, D0378 C, D0418) judges what the agent DID: which Skill a turn invoked. Nothing judged what the request ASKED, and every route the response contract names - VIEW, RECORD, CHANGE, EXECUTE, ORIENT, TRIVIAL - was an agent's unquoted judgment. The human's instrument for that judgment is in their own words (st111, us103): 'user said X - is the user asking for a view? if so, quote the text indicating so. Is the user asking to record? if so, quote the text indicating so'. D0381 fixes the shape of such a check: it runs once by a single agent following a written rubric, a check that disagrees with itself on identical inputs is a defect of the CHECK to critique, never a rate, and a genuinely subjective verdict is recorded with the text that decided it quoted beside it. dcRoutingVerdictQuotesItsEvidence carries the DoD; this Decision charters the shape.";
        :>> decision = "routing_probe.py --rubric hands the written rubric .engine/tools/routing_rubric.md, followed by one request from routing_prompts.toml between two marker lines, to a lower-capability model (haiku by default; the exact model id is read back from the CLI's own result and recorded, never typed) running with no tools, no hooks and no sight of this repository. The rubric asks six yes/no questions, one per route, and every yes must carry a verbatim quote from the request. judge_route is a pure function the probe runs before any model is paid for (D0388) and it REFUSES, rather than counts, an answer that misses a question, affirms a route without a quote, quotes words that are not a substring of the request, or affirms no route at all; a refused reply is kept beside the refusal so the rubric can be critiqued from what the model said. When a request already holds a recorded verdict, a differing verdict is written as a DISAGREES finding naming both quotes and both route sets; the run prints and records the names of what disagreed and what was refused, and no number is ever a rate. What each run cost and the model that answered are read from the CLI result and recorded in .keel/metrics/routing-rubric.json beside the verdicts. The transcript scorer of D0418 stands unchanged as the rig's first judging step; the two judge different things and are never combined. NOT A FORK: the shape follows from the human's words in st111 and from D0381; the one design choice inside it - refuse rather than count - is what the DoD of dcRoutingVerdictQuotesItsEvidence already states. NOT A PROCESS CHANGE: the rig is an investigation tool; no workflow, gate, schema, guard, hook or skill changes.";
        :>> rationale = "A verdict that quotes its evidence can be checked by anyone who can read, which is what makes a lower-capability model acceptable as the reader: the probe does not trust the model, it trusts the substring test. Refusing a quoteless or fabricated verdict is what turns the human's instruction into a control - a model that paraphrases, invents, or asks for more instead of answering produces no route, and the record says so by name. Writing disagreement as two quoted spans rather than an agreement rate follows D0381 and the human's own point (st111): a check that disagrees with itself is a poorly designed measurement, and the two quotes are what a person needs to critique the question that produced them. The first three paid runs made the point on the rubric itself: two replies took a request about requests arriving as speech for the task and asked for the request, so the rubric now fences the request between markers and says it is not addressed to the reader; and the runs disagree with each other on a large set of the situation-phrased prompts, which is recorded as an Issue against the rubric's questions, not averaged.";
        :>> consequences = "dcRoutingVerdictQuotesItsEvidence records its DoD result against the three paid runs: the fabricated-quote fixture is refused, every recorded verdict quotes a substring of its request, disagreement appears as a named finding with both quotes, and the model and cost are measured - and the VERIFY clause that each of the 47 requests produces a verdict does NOT hold, because on every run the model affirmed no route for one or two situation-phrased requests and the probe refused them as designed; that result is recorded as it is. The self-disagreement and the two refusals are one tracked Issue against the rubric with a resolver in the backlog. The scorer's --investigate path is untouched except that the CLI is resolved once per process, in the main thread, after a per-run lookup raced the CLI's updater. No standing routing number exists in either judge (D0378 C).";
    }
    #DerivedFrom dependency from d0459 to us103;
    // D0303 layering: the verdict shape - once, quoted, disagreement critiqued not averaged - is D0381's
    #DependsOn dependency from d0459 to d0381;

    // acceptance event (D0121 review-queue sign-off; D0066/D0106 — human-judged, not fabricated)
    verification d0459Accept : Test { :>> id = "4ce73b41-37a6-434c-ae59-cc4975bb2d1e"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0459AcceptR1 : TestResult { :>> id = "b6a498b3-f91c-42e1-825f-19d2d5d7a3ce"; :>> outcome = VerdictKind::pass; :>> judgedAgainst = "ac38d48"; :>> judgedAt = "2026-09-12"; :>> judgedBy = "wweatherholtz"; :>> createdBy = "claudeFable5"; }
}
