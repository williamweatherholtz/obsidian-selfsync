// D0447 (status: the `status` field below is the truth) — A tracked path whose working-copy line ending differs from the ending its .gitattributes declares is a named refusal in the touched run, in land and in a forward guard
// Recorded via `keel record decision` (D0105 RMWX axis; issue054). Acceptance is a separate explicit
// human gate (method=confirmation, D0106): flip status + add the d0447Accept event on sign-off.
package ReferenceDecision0447 {
    private import EngineElement::*;
    private import EngineWork::*;
    private import EngineVerification::*;
    private import EngineRelationships::*;

    // #ProspectiveChange (D0070) - this Decision governs a process/schema change; the co-committed
    // change rides the process-change guard's hard lock.
    #ProspectiveChange part d0447 : Decision {
        :>> id = "e9388afe-5510-4592-9a40-7037d2960275";
        :>> title = "A tracked path whose working-copy line ending differs from the ending its .gitattributes declares is a named refusal in the touched run, in land and in a forward guard";
        :>> createdAt = "2026-09-11";
        :>> createdBy = "claudeOpus5";
        :>> status = DecisionStatus::accepted;
        :>> context = "Every path type this repository cares about is pinned in `.gitattributes` (`*.sysml text eol=lf`, `*.rs text eol=lf`, and so on), and git honours that pin at the add: a CRLF working copy is normalised to LF in the index, so `git status` calls the tree clean and no diff ever shows the ending. Nothing that reads the working tree sees those normalised bytes. `keel suite --touched`, `keel land`, the guards, the hooks and the guard receipt all read the files as they are on disk, and on 2026-09-10 a Python `open(p, 'w')` on Windows left 140 of 1,733 `eol=lf` paths CRLF, five tests that read an exact newline-brace-newline anchor found 0 where they expected 2, and the verifier's receipt reported five failures nothing in the change could reach (issue478). The tree carried no control that could name the condition. The guard receipt (D0371) keys on HEAD plus the paths `git status` calls modified, so an eol-only rewrite left the key equal and a green receipt vouched for bytes no guard had read; the touched run and `land` compiled whatever ending the last tool wrote and reported a verdict that depended on which tool that was.";
        :>> decision = "A new forward guard, `working-tree-eol`, runs `git ls-files --eol -z` once over the tracked tree and fails naming every path whose `w/` column is `lf`, `crlf` or `mixed` and differs from the `eol=` value in its `attr/` column; paths whose attribute declares no ending (`text=auto`, `-text`, undeclared) and empty paths (`w/none`) are not judged, and a tree git cannot list scans zero with no verdict. `keel suite --touched` and `keel land` read the same census, computed once in `touched::compute`, and refuse before any test runs: the touched receipt writes `outcome = 'eol-mismatch'` with the paths in place of a verdict, and `land` prints the line naming the paths this push changed first and counting the rest, before the tree gate so the line is the refusal rather than one gate problem among many. The refusal is not behind the D0421 arming, because it is not a test run and a verdict that depends on which tool last wrote a file is not the verdict D0421 armed. The guard receipt's key gains the `(len, mtime)` of every tracked path from `git ls-files -z`, so an eol-only rewrite that status calls clean moves the key and a green receipt never answers for it.";
        :>> rationale = "The check is placed where the bytes are read, not where git would repair them: git's normalisation is real, but it happens at the add and protects the repository, while the tests, the guards and the hooks read the working tree and were protected by nothing. Judging only declared endings keeps the guard honest about what the repository has actually pinned - a `text=auto` file that is CRLF under `core.autocrlf=true` is git doing what it was told, and naming it would teach bypass (D0098). One census per run keeps the cost inside the budget the backlog set: `git ls-files --eol` takes about 0.8 s on this host over 1,782 tracked paths and the whole guard under 0.9 s, measured, and the touched receipt records the same phase as `eol_ms`. Extending the receipt key was the smaller change that closed the one dishonest path the incident exposed, at about a tenth of a second per key, rather than dropping the receipt shortcut or hashing every file's content.";
        :>> consequences = "`keel guard working-tree-eol` is a core guard (no process unit, no `activation.toml` entry) and runs in every project that carries a `.gitattributes` with `eol=` pins; a project without one scans zero and passes. `.engine/rules/guard-constraints.sysml` carries `constraint def workingTreeEol` and `.engine/docs/guards.md` carries the row; the `suite` and `land` synopses in `.engine/cli/commands.sysml` and its Rust mirror name the refusal. The control map (`.tracking/architecture/control-map.sysml`) needs a `gWorkingTreeEol : SystemSafetyConstraint` part bound to its hazard, an edit outside this change's scope that the recording step must make. A tree that currently holds a mismatch will see `land` refuse and the guard go red until the bytes are rewritten with the declared ending; the refusal line carries the remedy (a byte write or `newline=''`, never a translating writer), and `git ls-files --eol -- <path>` confirms the repair. Removal path: delete `working-tree-eol` from `GUARD_NAMES` and `run_one`, the `crate::eol` module and its call in `touched::compute`, the `before_gate`/`after_gate` split in `sync::cmd_land` (restoring the single `before_push`), the `ls-files -z` block in `receipt::key`, the constraint def, the docs row and the two synopsis clauses, under a superseding Decision that says why the working tree's endings no longer need judging.";
    }

    // acceptance event (D0121 review-queue sign-off; D0066/D0106 — human-judged, not fabricated)
    verification d0447Accept : Test { :>> id = "10479179-208b-4bd6-b613-b74daf7eadbe"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0447 (D0201 B); recorded as given (D0423)."; }
    part d0447AcceptR1 : TestResult { :>> id = "82dc87ca-b4dc-4eec-81c1-f455f392357a"; :>> outcome = VerdictKind::pass; :>> judgedAgainst = "3e6c518"; :>> judgedAt = "2026-09-11"; :>> judgedBy = "wweatherholtz"; :>> createdBy = "claudeOpus5"; }
}
