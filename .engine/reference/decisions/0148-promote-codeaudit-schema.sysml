// D0148 — ACCEPTED (wweatherholtz, 2026-08-15): promote the EngineCodeAudit schema module into the
// engine's shipped schema. FROZEN CORE (§1.5) — sign-off is the d0148Accept event below.
// #ProspectiveChange (D0070): this adds a module; nothing existing changes meaning.
package ReferenceDecision0148 {
    private import EngineElement::*;
    private import EngineWork::*;
    private import EngineVerification::*;
    private import EngineRelationships::*;

    #ProspectiveChange part d0148 : Decision {
        :>> id = "c7e05a41-9b38-4d72-8e16-0f4b9a2d5c83";
        :>> title = "D0148: ship the EngineCodeAudit schema module (frozen core)";
        :>> createdAt = "2026-08-15";
        :>> createdBy = "claudeOpus5";
        :>> status = DecisionStatus::accepted;
        :>> context = "FOUND by the consumer check while scoping keelArchViews, which is the last item on the ready frontier. That item asks for a `keel arch` command group — elements, criticality, coupling, drift, stpa-inputs, coverage — all computed over an authored `CodeElement` registry. ITS OWN DoD NAMES THE PREREQ IN ITS FIRST LINE: promote the EngineCodeAudit schema module (CodeElement + RiskClass/InvariantSafety/StpaRole/DesignPattern + the #Controls/#Feedback/#Restructure markers) into the engine's shipped schema, so `keel init` gives every downstream project the type. MEASURED: `CodeElement` exists nowhere in this engine — `.engine/schema/` holds `core` and `safety` and nothing else, and the only occurrences of the name in this repo are prose in the backlog and issues describing this very item. A downstream project (SelfSync) authored a local copy at `.engine/schema/codeaudit/` to prove the model, which sprint 298 confirms works: project-declared types resolve and their instances participate in declared views. So the model is proven; what is missing is SHIPPING it.";
        :>> decision = "ACCEPTED under §1.5: add `.engine/schema/codeaudit/` as a third schema module alongside `core` and `safety`, carrying `CodeElement` and its enums, so `keel init` ships it to every downstream project. A MODULE rather than an addition to `core`, deliberately and by the precedent `safety` already sets: code-audit types are a coherent optional concern, not part of the vocabulary every project needs, and putting them in frozen `core` would make every project carry them to serve the projects that want them.";
        :>> rationale = "WHY THE COMMANDS ARE NOT BUILT FIRST. `keel arch` reads authored `CodeElement` instances; with no such type in the engine, building the command group now would ship a producer for a type the engine does not define, verified against data that does not exist here — a producer with no consumer, which is precisely what D0144 exists to prevent, committed in a sprint that would have to cite D0144 as its charter. The item's own VERIFY compounds it: it requires testing 'on SelfSync's authored registry', which is a different project's data this repo does not hold, so the acceptance criterion is unreachable from here even with the schema in place. ALTERNATIVES: (i) build the commands against a synthetic probe registry — REJECTED, it would demonstrate the commands run, not that they compute anything true, and the item asks for a specific ranked result on real data; (ii) leave the type project-local forever and let each project declare its own — a legitimate option the human may prefer, and it costs nothing today since sprint 298 proved project types work; the price is that every project reinvents the same registry and no two are comparable; (iii) CHOSEN for proposal.";
        :>> consequences = "If ACCEPTED: one new schema module shipped by `keel init`, after which keelArchViews becomes executable — though its verification still needs a project with an authored registry, which this repo is not, so the item should be re-scoped to name where it will be verified. If REJECTED: keelArchViews must be re-scoped or superseded, because its stated prereq will not happen and an item whose first line is an unmeetable prerequisite is not ready work. Either verdict unblocks the frontier; the current state is the only one that leaves it stuck. Tracked as issue114.";
    }

    // acceptance event (D0121 review-queue sign-off; D0066/D0106 — human-judged, not fabricated)
    verification d0148Accept : Test { :>> id = "bdd31c09-e6cc-4dbc-a1bd-c57060307d48"; :>> method = VerificationMethod::confirmation; :>> procedureText = "wweatherholtz, 2026-08-15, verbatim: 'accepted on all three. expand to suit the new improved schema'. Given in direct reply to the sprint-298 report, which presented D0146 (Actor.role), D0147 (a Claim type) and D0148 (ship the EngineCodeAudit module) together as one finding - process definitions demanding data the schema cannot hold - each with its alternatives and with what must happen on rejection. The human accepted all three and directed the follow-on work."; }
    part d0148AcceptR1 : TestResult { :>> id = "deb896b3-55bd-4c4a-9f0e-c85882fbdcf7"; :>> outcome = VerdictKind::pass; :>> judgedAgainst = "46f0cca"; :>> judgedAt = "2026-08-15"; :>> judgedBy = "wweatherholtz"; }
    part d0148AcceptR2 : TestResult { :>> id = "270b1542-daed-4ea1-9267-96e83e6ed990"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): decision wording PROPOSED to ACCEPTED at a6b7123 - editorial, the agreed substance unchanged. Their standing words, verbatim: 'issues raised are automatically accepted. they can be customizedly changed post-fact.'"; }
}
