// D0464 (PROPOSED — NOT YET ACCEPTED) — dominanceRuleOrDominanceBar: on today's tree D0364's no-regression rule and the hand-set bar cannot both hold - keep the rule and let the bar fail at 1.5, or weight the rule so 1.25 stands
// Recorded via `keel record decision` (D0105 RMWX axis; issue054). Acceptance is a separate explicit
// human gate (method=confirmation, D0106): flip status + add the d0464Accept event on sign-off.
package ReferenceDecision0464 {
    private import EngineElement::*;
    private import EngineWork::*;
    private import EngineVerification::*;
    private import EngineRelationships::*;

    // RESEARCH: Measured 2026-09-12 with .engine/tools/recall_bench.py --sweep and recall_ab.py against the tree at 33c398a (keel 0.4.1; the ranker in keel-cli/src/view/knowledge.rs is unchanged since D0365), re-runnable with KEEL_BENCH_BIN. One-hop arm, 50 cases: DOMINANCE=0 hits 45/50 median 2 top-3 28/45 mean rows 12; 1.1 45/50 median 4 top-3 21/45; 1.25 45/50 median 3 top-3 27/45; 1.3, 1.35, 1.4, 1.45 each 45/50 median 3 top-3 27/45; 1.5 45/50 median 2 top-3 28/45. Two-hop arm, 50 cases: 0 hits 20/50 median 5 top-3 2/20 mean rows 13; 1.1 24/50 median 3 top-3 15/24; 1.25 23/50 median 4 top-3 8/23; 1.3 23/50 median 4 top-3 7/23; 1.35 22/50 median 5 top-3 6/22; 1.4 21/50 median 5 top-3 5/21; 1.45 21/50 median 5 top-3 4/21; 1.5 20/50 median 5 top-3 2/20. Verdict lines, verbatim - one-hop over 0, 1.1, 1.25, 1.5: DISCRIMINATED on KEEL_RECALL_DOMINANCE: median position moved - hits 45..45 (0=45, 1.1=45, 1.25=45, 1.5=45); median position 2..4 (0=2, 1.1=4, 1.25=3, 1.5=2); top-3 21..28 (0=28, 1.1=21, 1.25=27, 1.5=28). Two-hop over the same: DISCRIMINATED on KEEL_RECALL_DOMINANCE: hits and median position moved - hits 20..24 (0=20, 1.1=24, 1.25=23, 1.5=20); median position 3..5 (0=5, 1.1=3, 1.25=4, 1.5=5); top-3 2..15 (0=2, 1.1=15, 1.25=8, 1.5=2). Off against 1.5 alone, both arms: COULD NOT CHOOSE on KEEL_RECALL_DOMINANCE: hits 45 and median position 2 never moved across KEEL_RECALL_DOMINANCE = 0, 1.5, and no case's outcome changed at any value; and: hits 20 and median position 5 never moved across KEEL_RECALL_DOMINANCE = 0, 1.5, and no case's outcome changed at any value. Hand set (recall_ab.py, 8 questions, 7 reachable): at 1.25 the rebase question's d0129 arrives at position 8, injection ON 7/8, bar MET (7/7 reachable cases hit); at 1.5 and at 0 it does not arrive, injection ON 6/8, bar NOT MET (6/7 reachable cases hit).
    part d0464 : Decision {
        :>> id = "8567eb75-5132-498a-ace8-999af89be50a";
        :>> title = "dominanceRuleOrDominanceBar: on today's tree D0364's no-regression rule and the hand-set bar cannot both hold - keep the rule and let the bar fail at 1.5, or weight the rule so 1.25 stands";
        :>> createdAt = "2026-09-12";
        :>> createdBy = "claudeFable5";
        :>> status = DecisionStatus::proposed;
        :>> context = "issue430 (2026-09-09) found that the dominant-source setting D0365 took, DOMINANCE 1.25, no longer holds the rule D0364 chose it by - the highest hit count on the two-hop arm subject to no regression on the one-hop arm's hits, median position and mean rows - because the one-hop set had grown cases the bonus touches. dcDominanceRechosenUnderItsOwnRule is its resolver: sweep both arms, apply the rule, and if the setting changes record it; if the rule itself is what moves, put that to the human. Both arms were swept at eight settings on one tree (research). Applying the rule as written: 1.1 and 1.25 through 1.45 each move the one-hop median from 2 to 3 (1.1 to 4) and are refused; 0 and 1.5 hold the one-hop set exactly and tie on the two-hop arm at 20/50, where the bench's own line says no case's outcome differs between them. So the rule admits only settings under which the mechanism buys nothing, and the boundary is sharp - the first setting that buys a single two-hop hit (1.45, 21/50) is the first that costs the near median. Then the hand set was read, afterwards and unchanged, as D0365 requires: the rule's admissible settings fail the bar recallRanksLinkedRecordsAsWellAsGrepDoes was written with (the hand set stays at 7/8 or better): the rebase question, the case D0365 was built for, is reached at 1.25 and at no admissible setting. The rule and the bar cannot both hold on this tree. Which of them gives is not in the numbers.";
        :>> decision = "OPTION A (the rule stands as D0364 wrote it): DOMINANCE moves to 1.5, the admissible setting that keeps the mechanism in force - it fires only where a top row scores one and a half times the second, and on both generated arms that changes no case's outcome, so nothing is claimed for it. recallRanksLinkedRecordsAsWellAsGrepDoes takes a failing result at HEAD (hand set 6/7 reachable, bar NOT MET) and reopens as the honest state; the rebase question's Decision is again reached by grep only. COST: a bar the human wrote is recorded failing on a setting whose only merit is that it changes nothing, and the one question that needed linked recall is answered by grep alone. OPTION B (the rule gains a weight): D0364's clause becomes - the highest two-hop hit count subject to the one-hop arm's hits and mean rows holding and its median position moving by at most one, and only where the two-hop arm gains at least three hits; a SupersedeClause on D0364 and the same on D0365's TAKEN clause carry it. Under that rule 1.25 stands (23/50 against 20/50, one-hop median 2 to 3, top-3 28 to 27), 1.1 is still refused (median 4), and the hand set reads 7/7. COST: a rule written before the sweep bends the first time it binds, by two clause reversals, and the near arm's median position is one worse than it was at off. DO NOTHING: 1.25 stays in force under a rule it fails, the constant's recorded provenance is false on today's tree, and issue430 stays open with no resolver that can close it.";
        :>> rationale = "WHY THIS IS A FORK AND NOT MINE: the rule was fixed before any sweep so that the setting would never be fitted to the questions, and the first tree on which the rule and the questions disagree is the first time that discipline costs something. Loosening the rule because the hand set wants it is exactly the fitting the rule exists to forbid - unless the human, who wrote the eight questions and is the searcher the near set stands in for, says the trade is worth it. Keeping the rule means telling them the mechanism built for the rebase question no longer reaches it. What decides it is a value only they hold: whether a near hit at position 3 rather than 2, in the half of searches the one-hop set models, is worth three far hits in fifty and the two-hop question in the half it does not. Nothing in the model answers that. My reading, labelled as mine: option B - hits and mean rows are held under it, one median position is the whole near-set cost, and the only human-written cases are met under B alone; but I hold the rule's author's reason for A too, that a criterion which bends the first time it binds is decoration. FALSIFIER: a setting that held the one-hop median at 2 while buying any two-hop hit would dissolve this fork; 1.45 and 1.5 were run to look for one and there is none in the measured grid. NOT A PROCESS CHANGE: the ranker constant and D0364's choosing rule are neither process definitions nor enforcement surface; recall_bench.py gates nothing (D0364).";
        :>> consequences = "Held proposed for the human through decision-surfacing, both sweeps and the hand-set readings in the research line as the evidence. Under A: knowledge.rs DOMINANCE 1.25 to 1.5 with the measurement in its provenance comment, a fail result on recallRanksLinkedRecordsAsWellAsGrepDoesDoD at HEAD, issue430 resolved. Under B: a SupersedeClause Decision on D0364 and D0365 carrying the weighted rule, the constant unchanged, knowledge.rs's provenance comment gaining the re-choice, a pass result on dcDominanceRechosenUnderItsOwnRuleDoD, issue430 resolved. Until they answer, the constant stays 1.25 and issue430 stays open; sprint 691 records the measurement, not a choice. The bench's tie line (COULD NOT CHOOSE with no case's outcome changed) is what made the tie between 0 and 1.5 a measurement rather than a reading of two equal summaries - D0415's line did its job here.";
    }
    #DependsOn dependency from d0464 to d0364;
    #DependsOn dependency from d0464 to d0365;
}
