// D0242 (status: the `status` field below is the truth) — the knowledge graph pushes facts before the model thinks, and travels with the engine
// Recorded via `keel record decision` (D0105 RMWX axis; issue054). Acceptance is a separate explicit
// human gate (method=confirmation, D0106): flip status + add the d0242Accept event on sign-off.
package ReferenceDecision0242 {
    private import EngineElement::*;
    private import EngineWork::*;
    private import EngineVerification::*;
    private import EngineRelationships::*;

    // #SafetyChange (D0070) - this Decision governs a process/schema change; the co-committed
    // change rides the process-change guard's hard lock.
    #SafetyChange part d0242 : Decision {
        :>> id = "7d935200-1d6b-4134-afba-41c3260a70a3";
        :>> title = "the knowledge graph pushes facts before the model thinks, and travels with the engine";
        :>> createdAt = "2026-08-27";
        :>> createdBy = "claudeOpus5";
        :>> status = DecisionStatus::accepted;
        :>> context = "D0161 built the knowledge store's COMMAND tier (`keel why`, `.knowledge/`, question-coverage, the multi-hop trap) in sprint 424, and the human reports no felt gain in answer quality or speed. Measured against the source process (`.engine/processes/knowledge-graph-memory.sysml`, from 'Applying Knowledge Graphs', Glitch Cat Club, captured 16 Aug 2026), seven of the eight spine steps are built and the missing one is the payoff: kgInjection — 'Inject the facts BEFORE the model thinks' — which the process itself describes as 'THIS STEP IS WHAT MAKES IT PUSH RATHER THAN PULL: a graph the model must decide to query is still pull, and inherits every cost this process exists to remove.' Verified: `keel hook user-prompt` is wired on `UserPromptSubmit` but its implementation takes only the ROOT and never reads the prompt — it emits a fixed routing reminder. No hook mentions why, knowledge, or recall. So recall is reachable only by the model CHOOSING to run `keel why`, which is the pull arrangement the process exists to replace. Two further defects in the recall payload: `seeds` are bare identifiers with no content, and `keel why <term> [ROOT]` takes no flags — there is no brief, budgeted, or content-bearing mode, so today's 40 identifier rows would be noise if injected as-is. `reached` does carry type, title, via, file and createdBy, which is usable material. Scale of what is unused: the typed corpus holds 6,625 declared parts, 2,505 typed edges, 241 decisions, 257 issues and 467 sprints, while `.knowledge/` declares 4 lexicon terms and 3 questions. How it got here, traceably: D0161 relaxed injection from mandatory to TIER-CONDITIONAL — 'a corpus the human queries directly needs a COMMAND (keel why), not a prompt hook' — and sprint 424 correctly built the command tier. Nobody revisited that choice for the corpus whose consumer is an AI rather than a human at a CLI, which is this one.";
        :>> decision = "Build the injection tier for this project's own corpus, in five parts, and make it portable by construction. 1. RECALL BECOMES CONTENT-BEARING AND BUDGETED. `keel why --brief` emits compact ranked lines (type, name, title, via, file) under a character budget, with the substantive text of the top-k elements. Ranking is by hops then declaration order. 2. RECALL SEEDS FROM A PROMPT, NOT A TERM. `keel recall --prompt -` reads the prompt on stdin and matches it against the lexicon, aliases and declared names before traversing. Zero model calls, as the process requires. This is the capability that does not exist today: recall currently requires already knowing the term. 3. THE PROMPT PATH INJECTS. `keel hook user-prompt` reads the prompt, calls recall, and emits the facts plus the VISIBLE recall count and elapsed time the process names as its produced artifact. Hard latency cap, fail-open: an unavailable or slow store must never cost the turn. 4. IT IS PROVEN ON THE TRAP, OR IT DOES NOT SHIP. The existing multi-hop trap suite is extended with questions whose answers span elements sharing no vocabulary, and the measure is TOOL CALLS TO FIRST CORRECT ANSWER with injection on versus off. 5. PORTABILITY. The mechanism rides the existing generation path: the `UserPromptSubmit` wiring is engine-generated (`claude_surface.rs`), so a payload change propagates to every project through `keel init` and `keel sync-claude` with no separate script. What a downstream project needs a SKILL for is the human-owned half — its own questions and vocabulary — because `.knowledge/` is instance data, not engine data. The `knowledge-graph-memory` skill is updated to deploy the injection tier and to walk the human through steps 1 and 2.";
        :>> rationale = "The human's question was whether this relies on diligence, and the answer is no: keel already has the pre-model forcing mechanism, already fires it every turn, and already uses it to push the D0064 routing contract — whose own source comment reads 'routing is structural, fired every turn rather than left to vigilance'. So part 3 is not building a mechanism; it is changing the PAYLOAD of a mechanism that already fires. That reframing is why this is a small change rather than a large one, and it is also why portability is nearly free. ALTERNATIVES for part 3: (A) leave it as a command and rely on the AI remembering to call it — rejected: that is the pull arrangement, and the process states it inherits every cost the method exists to remove. It is also the arrangement that produced the human's report of no felt gain. (B) inject unconditionally with no budget — rejected: 40 ranked titles on every turn is unrequested context that can degrade answers as easily as improve them, which is why part 4 measures rather than assumes. (C) add a Stop-level gate requiring the AI to cite recalled provenance — rejected as textbook Goodhart: it would train citation rather than use. Per invariant 7 that is an INDICATOR, monitored without an enforced threshold, not a requirement. CRITERIA: does the model take part in the finding (it must not); can a turn be made slower or more brittle by the store (it must not); and would we be able to tell whether it helped.";
        :>> consequences = "This changes the human's session on EVERY turn, which is why their explicit go was asked for and given: 'a few more things, and all of your ideas accepted.' The speed and quality claims are NOT inherited. The process is explicit that D0153's measured numbers 'were demonstrated on one corpus and one question, and this process reproduces the METHOD, not the numbers'. Ours start at zero and part 4 is the only thing that will make them real. If the trap shows no improvement in tool-calls-to-answer, the honest outcome is to record that and keep the command tier rather than ship injection because it was planned. Two known costs, stated: recall is ~1.3s today and re-derives from 531 files, so a cap and probably a cache are prerequisites rather than polish; and the lexicon's 4 terms are the binding constraint on part 2's seeding, which is human-owned work (the process's step 2 is explicit that the AI drafts and the human decides). The `UserPromptSubmit` wiring is part of the enforcement surface, so the change rides a co-committed marked Decision — this one.";
    }

    // acceptance event (D0121 review-queue sign-off; D0066/D0106 — human-judged, not fabricated)
    verification d0242Accept : Test { :>> id = "25fa263a-bc46-4684-947a-3e41b3a748e0"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0242AcceptR1 : TestResult { :>> id = "29818ae9-dbd5-4640-a490-742141412622"; :>> outcome = VerdictKind::pass; :>> judgedAgainst = "2bec54d"; :>> judgedAt = "2026-08-28"; :>> judgedBy = "wweatherholtz"; }
}
