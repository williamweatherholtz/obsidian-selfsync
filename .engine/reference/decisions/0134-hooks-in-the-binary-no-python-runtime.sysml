// D0134 — The in-loop hooks live in the keel BINARY. Python leaves the governance path entirely.
// Marked #ProspectiveChange (D0070): turns gated under the python wrappers stay valid.
package ReferenceDecision0134 {
    private import EngineElement::*;
    private import EngineWork::*;
    private import EngineVerification::*;
    private import EngineRelationships::*;

    #ProspectiveChange part d0134 : Decision {
        :>> id = "9a41c6d2-58be-4f37-b1e0-7c2d84a09f65";
        :>> title = "D0134: the in-loop hooks move into the keel binary; python leaves the governance path";
        :>> createdAt = "2026-08-14";
        :>> createdBy = "claudeOpus5";
        :>> status = DecisionStatus::accepted;
        :>> context = "The human challenged the dependency directly (2026-08-14): 'why are we using python to make code? i thought we were rust on the backend. we need to be careful about what we depend on. is this dependency defensible?' It was not. All four governance hooks were python wrappers (triage_reminder, out_of_band_check, stop_gate, and the edit_gate added minutes earlier). The CHECKING was always Rust — python only parsed the hook's stdin JSON and emitted the response — so the whole dependency bought pure glue. What it cost is the failure mode this engine had just spent a sprint eliminating: a SECOND RUNTIME on every contributor's machine, where absence means the gate silently does not run (issue076, and issue081's eight bypassed commits). D0129 puts five mixed-OS machines in scope, so each one would need python present for the governance layer to exist at all. It also cuts against D0112's accepted direction of REMOVING runtime dependencies from the validation path, and it was about to ship in a release.";
        :>> decision = "Move all four hooks into the binary as `keel hook <user-prompt|post-edit|stop>`, reading the payload on stdin and writing the hook protocol on stdout, and DELETE the four python wrappers (no tombstones). `keel` is already a hard requirement for these gates to mean anything and `serde_json` was already a dependency, so the dependency count goes DOWN by one with nothing added. The settings.json commands probe for the binary (PATH, then target/release, then target/debug) exactly as the portable git hook does, so a missing binary reports rather than silently no-opping. Behaviour is preserved exactly: post-edit runs the fast tier (validate + duplicate-identity + marker-vocabulary) and blocks on violations; stop runs validate + all guards and is loop-safe (a second consecutive red releases with a loud warning); user-prompt injects the route-first checklist plus the out-of-band-writes warning, ASCII-only because a non-UTF-8 Windows console would otherwise inject mojibake, and silent when the tree is clean.";
        :>> rationale = "A governance control must not depend on a runtime the governed machine may lack — a gate whose absence is silent is worse than no gate, which is the lesson issue076 and issue081 both taught at cost. Since the binary was already mandatory, python was a strictly additive risk for zero capability. SCOPE KEPT HONEST: python remains for the KERNEL validators (.engine/tools/validate/*) and a few utilities, and that is defensible on different grounds — those drive a JVM/Jupyter kernel that is itself being retired under D0112, they are opt-in rather than gating (D0132), and porting them would mean reimplementing a SysML oracle rather than deleting glue. The distinction that matters is ENFORCEMENT versus tooling: nothing that gates the agent now depends on python. ALTERNATIVE REJECTED: keep the wrappers and document the dependency — that is exactly the manual-vigilance non-control D0047 forbids, and it would have shipped in the release.";
        :>> consequences = "Adds `keel hook` with three events; removes .engine/tools/{triage_reminder,out_of_band_check,stop_gate,edit_gate}.py; rewires all three hook events in .claude/settings.json to the probing binary invocation. Python is no longer required to run ANY gate — only for the opt-in kernel validators. Verified: all six hook paths pipe-tested (non-sysml silent, clean silent, broken blocks, marker typo blocks, stop red blocks, stop loop-safe releases); user-prompt output confirmed 0 non-ASCII bytes; clippy clean; validate + all 23 guards green. Acceptance state is carried by `status` plus the d0134Accept event.";
    }

    verification d0134Accept : Test { :>> id = "b3f7e910-6c25-4a8d-97f1-42e0db5c8a13"; :>> title = "Human acceptance of d0134"; :>> createdAt = "2026-08-14"; :>> createdBy = "claudeOpus5"; :>> method = VerificationMethod::confirmation; :>> procedureText = "wweatherholtz challenged the dependency and directed the correction, 2026-08-14: 'why are we using python to make code? i thought we were rust on the backend. we need to be careful about what we depend on. is this dependency defensible?' The finding was accepted as stated (the dependency was NOT defensible for the governance path) and the remedy — moving the hooks into the binary and deleting the wrappers — follows directly from that direction, including the recorded scope limit that the opt-in kernel validators remain python."; }
    part d0134AcceptR1 : TestResult { :>> id = "c58a2d47-0e93-4b16-8f2a-6d71b409ce82"; :>> outcome = VerdictKind::pass; :>> judgedAgainst = "bb52d2a"; :>> judgedAt = "2026-08-14"; :>> judgedBy = "wweatherholtz"; }
}
