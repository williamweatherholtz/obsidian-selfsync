// D0138 — What a project has ADOPTED becomes a DECLARED fact (an activation manifest) instead of being
// inferred from whether a file happens to exist. Subsumes the issue089/issue090 patches.
// PROPOSED: this changes the MEANING of `keel guard` (a guard may now be skipped), which is §3a
// territory and cannot be self-accepted. Default behaviour is unchanged until a project opts in.
package ReferenceDecision0138 {
    private import EngineElement::*;
    private import EngineWork::*;
    private import EngineVerification::*;
    private import EngineRelationships::*;

    #ProspectiveChange part d0138 : Decision {
        :>> id = "5e93f7c1-4a08-4d62-b8e5-2c71a9046f3b";
        :>> title = "D0138: adoption is a declared fact — process activation manifests, with core guards not deactivatable";
        :>> createdAt = "2026-08-14";
        :>> createdBy = "claudeOpus5";
        :>> status = DecisionStatus::accepted;
        :>> context = "Delivers srPortActivationManifest under nProcessPortability (D0128, accepted). Issues 089 and 090 were the same question wearing different clothes — WHAT HAS THIS PROJECT ADOPTED? — and both were answered by INFERENCE from file presence: a marker counted as adopted because some file declared it; a rule counted as adopted because its file existed. Each fix was correct and neither addressed the inference. Inference cannot express intent: a project could not STATE what it had adopted, could not SEE what it had not, could not adopt a process as a unit, and enforcement shifted silently when a file moved. The human named this directly ('the answer should be through defining portable processes, no?'). There is a further problem the two patches created: 'rule absent -> control not adopted' means DELETING A FILE IS A WAY TO TURN OFF A GATE, which is indistinguishable from legitimate non-adoption. Declaring adoption separates the two.";
        :>> decision = "(A) `.engine/contracts/activation.toml` — a PROJECT declaration of which processes are active. (B) `.engine/contracts/process-units.toml` — an ENGINE FACT stating what each process brings: its deploying skills, its declared rules, and its guards. Two files because they are two different kinds of claim; merging them would make the engine's own structure editable as project config. Both follow the D0097 `critique-policy.toml` precedent (declared TOML read at runtime, never a baked-in map). (C) A guard named in a unit is PROCESS-BOUND: enforced only while its process is active. A guard named in NO unit is CORE and always runs. (D) CORE GUARDS ARE NOT DEACTIVATABLE — actors, charter, requirement-rootedness, marker-vocabulary, duplicate-identity, engine-lint, manifest-coverage, process-skill, process-change, hook-config-integrity. (E) A skipped guard is REPORTED as `NOT ACTIVE`, never silently dropped, and `orient` carries `inactive_processes`. (F) ABSENT MANIFEST MEANS EVERYTHING IS ACTIVE, so no existing project changes behaviour by upgrading. (G) `keel activate|deactivate <process>` change adoption in one step, and a first write MATERIALISES the current effective state before applying the change, so activating one process cannot silently deactivate the rest. (H) A new HARD guard `activation-manifest` fails loud on an unknown process or guard name or unparseable TOML; absent files are not a violation.";
        :>> rationale = "The decisive design question was not the file format but WHAT MUST NOT BE DEACTIVATABLE. A manifest that could switch off any guard would be a rebuilt version of the all-or-nothing bypass that issue081 cost eight commits to learn about — worse, because it would be a SANCTIONED bypass with a config file blessing it. Splitting core from process-bound is what makes activation safe: it stops enforcing PROCEDURES a project has not adopted (does it run sprints? does it critique elements? does it author decisions this way?) while leaving untouched every check on whether the record itself is TRUTHFUL — identity, provenance, vocabulary, rootedness, well-formedness. Those are not a way of working; they are the conditions under which any computed answer means anything. Verified adversarially rather than argued: with a hostile `active = []` the model still hard-fails on a duplicate id at exit 1. The second design commitment is that non-enforcement is never silent. A project running a deliberate subset must be able to see what it is not checking, or the manifest becomes a way to make a gate quietly disappear — which is the failure mode of every opt-out system. ALTERNATIVES: (i) keep inferring from file presence — REJECTED, it conflates 'not adopted' with 'file deleted to dodge a gate' and cannot express intent; (ii) put the process-to-controls mapping in the SysML model via a new edge marker — REJECTED for now, it needs a new marker and therefore a frozen-algebra CHANGE, when D0097 already established TOML contracts as the home for declared policy; worth revisiting if the mapping ever needs to be traced to; (iii) let the manifest govern ALL guards uniformly — REJECTED, see above, this is the sanctioned-bypass failure; (iv) CHOSEN. WHY PROPOSED AND NOT ACCEPTED: this changes the MEANING of `keel guard`, since a guard may now legitimately not run, and §3a reserves that to explicit human acceptance. The direction is already accepted (D0128/nProcessPortability) and default behaviour is bit-identical with no manifest present, but the semantics of the enforced gate are not mine to widen.";
        :>> consequences = "Adds keel-cli/src/activation.rs, the two contract files, `keel activation|activate|deactivate`, the `activation-manifest` guard (25 guards: 19 hard, 6 warning-only), activation-awareness in `guards::run_all`, and `inactive_processes` in orient's JSON. `keel guard <name>` run by name still performs the check but exits 0 when the guard is inactive, so the single-guard exit code cannot contradict the enforced gate. This SUBSUMES the issue089/issue090 patches conceptually — 'rule absent -> not adopted' becomes 'that process is not in your active set' — while leaving both patches in place, since they remain the correct behaviour for a project with no manifest. This repo declares no manifest, so its own gate is unchanged. Doc-sync: guards.md (count, catalogue entry, an adoption section), usage.md, CLAUDE.md §5. Four unit tests cover the two invariants plus fail-loud typos; the DoD criteria were additionally verified end-to-end on a fresh `keel init` project, including the adversarial `active = []` case and a proof that activating a process genuinely restores enforcement (the same model goes exit 0 -> exit 1).";
    }

    // acceptance event (D0121 review-queue sign-off; D0066/D0106 — human-judged, not fabricated)
    verification d0138Accept : Test { :>> id = "96186c96-161a-45f1-8e87-8d67cd36f054"; :>> method = VerificationMethod::confirmation; :>> procedureText = "adoption being declared leaves a paper trail, which means the logic is mineable"; }
    part d0138AcceptR1 : TestResult { :>> id = "a42ee1b0-edea-478f-9d63-8ec2714eb732"; :>> outcome = VerdictKind::pass; :>> judgedAgainst = "36187ea"; :>> judgedAt = "2026-08-14"; :>> judgedBy = "wweatherholtz"; }
}
