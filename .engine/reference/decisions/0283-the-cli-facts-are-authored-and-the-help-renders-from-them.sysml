// D0283 (status: the `status` field below is the truth) — The CLI facts D0271 defined are authored, keel --help renders from them, and a guard holds facts, help and dispatch equal
// Recorded via `keel record decision` (D0105 RMWX axis; issue054). Acceptance is a separate explicit
// human gate (method=confirmation, D0106): flip status + add the d0283Accept event on sign-off.
package ReferenceDecision0283 {
    private import EngineElement::*;
    private import EngineWork::*;
    private import EngineVerification::*;
    private import EngineRelationships::*;

    // #ProspectiveChange (D0070) - this Decision governs a process/schema change; the co-committed
    // enforcement-surface edit (guards.rs, guard 58) is what it authorises.
    #ProspectiveChange part d0283 : Decision {
        :>> id = "28e3e263-68f9-4ce5-896e-e7fad7113bac";
        :>> title = "The CLI facts D0271 defined are authored, keel --help renders from them, and a guard holds facts, help and dispatch equal";
        :>> createdAt = "2026-09-02";
        :>> createdBy = "claudeOpus5";
        :>> status = DecisionStatus::accepted;
        :>> context = "D0271 defined the CliCommand schema and deferred its 90 instances until the human ruled on the lens collapse - authoring them and then renaming 43 would have been work done twice. D0273 ruled (clean break), the collapse landed (65 commands, 35 show lenses, held equal to the dispatch by a unit test), and the instances were never authored: zero in the tree on 2026-09-02, while CLAUDE.md invariant 8 stated them as existing (issue344). The hand-written help catalogue in main.rs had meanwhile gone stale in exactly the way a table-plus-test cannot see - it still listed hardening, suspect and outstanding as top-level verbs a month after they moved under show, because the test only asked that every dispatched arm be NAMED somewhere in the text. The facts are also the source the computed control structure needs (dcControlStructureIsComputed, the human's stated first step): effect = writes is a control action the agent issues, reads is feedback.";
        :>> decision = "Author the 100 facts - 65 commands and 35 lenses - in .engine/cli/commands.sysml, each carrying name, family, effect, stability, invocation and synopsis; families are governance, authoring, gating, orientation, rendering, integration, distribution, channel, knowledge and lens. The .sysml is the home. A Rust mirror (cli_facts.rs) renders keel --help from the same fields, grouped by family, so a synopsis has one home and the help cannot describe a surface that does not exist. Guard 58, cli-surface-declared, holds three things equal both ways: the authored facts, the mirror (field by field), and the dispatch inventory (COMMAND_NAMES for commands, LENS_NAMES for lenses); an absent facts file is a violation. .engine/cli/ joins the check-engine instance set the day it is created. The hardening lens that measured help coverage by reading the CATALOGUE out of main.rs source now reads the rendered facts. Every enforced guard has a catalogue row in guards.md, kept complete by a test - six had none. CLAUDE.md invariant 8 is corrected to what is true and no longer carries a count.";
        :>> rationale = "WHY A MIRROR AND NOT THE .SYSML AT RUN TIME: keel --help must work in a directory with no .engine (before init, in a broken tree), so the binary carries the table; the guard makes carrying it safe by refusing any field-level drift between the two. That is the same shape COMMAND_NAMES already has with the dispatch - a mirror held equal by a control is not a second home, a mirror nobody checks is. WHY BOTH WAYS ON EVERY EDGE: the old test checked one direction (dispatched implies named) and that is how three lenses stayed listed as verbs - nothing asked whether a named thing was dispatched as what the help said it was. WHY THE EFFECT VALUES ARE JUDGMENTS WORTH RECORDING: actor, claim, deck, serve, sync, land, migrate, process, library and sync-claude are both because they read to decide and then write; advance is reads because the cursor is computed and --to refuses rather than stamps; hook, mint, version and github-decision-id are tooling. A status command that writes would now be a guard violation, which is the property D0270 built status to hold and nothing tested. ARMED before landing: a flipped effect on status and a deleted orient fact each failed naming the command and the disagreeing side.";
        :>> consequences = "issue344 resolves. The computed control structure has its source for the agent's actions and feedback. The stale help is gone and cannot recur without a red guard. A new command needs three edits - dispatch arm, fact, mirror row - and forgetting any one is a build or gate failure rather than an undiscoverable command; the cost is deliberate and small. The two-way guard over guards.md rows means the next guard cannot land undocumented. REMOVAL PATH (D0163): delete .engine/cli/, cli_facts.rs and the guard together, and restore a help block by hand - the facts carry nothing another view depends on yet; once the control structure view reads them, removal also removes that view's source and must say so.";
    }

    // acceptance event (D0121 review-queue sign-off; D0066/D0106 — human-judged, not fabricated)
    verification d0283Accept : Test { :>> id = "46c52e4a-fd7c-40d3-846d-1332af85f6c7"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0283AcceptR1 : TestResult { :>> id = "083dc677-b944-40d3-b6d5-0cce8bb2c97a"; :>> outcome = VerdictKind::pass; :>> judgedAgainst = "7459b45"; :>> judgedAt = "2026-09-02"; :>> judgedBy = "wweatherholtz"; }
}
