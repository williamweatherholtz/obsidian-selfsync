// D0365 (status: the `status` field below is the truth) — recallTakesASecondHopFromTheDominantRow: when one row dominates the ranked payload, its neighbours and theirs inherit its score
// Recorded via `keel record decision` (D0105 RMWX axis; issue054). Acceptance is a separate explicit
// human gate (method=confirmation, D0106): flip status + add the d0365Accept event on sign-off.
package ReferenceDecision0365 {
    private import EngineElement::*;
    private import EngineWork::*;
    private import EngineVerification::*;
    private import EngineRelationships::*;

    part d0365 : Decision {
        :>> id = "b5fb3b5c-262c-41ae-8435-6a2ef2501fab";
        :>> title = "recallTakesASecondHopFromTheDominantRow: when one row dominates the ranked payload, its neighbours and theirs inherit its score";
        :>> createdAt = "2026-09-07";
        :>> createdBy = "claudeOpus5";
        :>> status = DecisionStatus::accepted;
        :>> context = "issue367 / recallRanksLinkedRecordsAsWellAsGrepDoes. After D0325 the payload met the criterion's first clause (49/50 against grep-plus-one-hop's 47/50, in 13 ranked rows against 14 unranked candidates) and failed its second at 6/8 on the eight hand-written questions. The criterion named three candidate mechanisms; two had been measured and rejected, and the third - a source-then-neighbours listing when one seed dominates - was untried. Diagnosed on the failing case with a per-component ranking dump: for 'why must we never rebase or force-push?' the payload's top row scores 31.5 against the second's 17.1, the governing Decision d0129 sits at rank 63 on its own lexical score alone, and it is two edges behind that top row as requirement --satisfy--> need <--derivedFrom-- decision. Every lift in the ranker is keyed to the SEED ordering, and that requirement is only the fourth seed by raw lexical score while the one-hop inheritance reaches the top three - so the mechanism that should have carried it never applied to it.";
        :>> decision = "After the seed-keyed signals are folded, the ranker reads its own ranking: if the top row scores at least DOMINANCE = 1.25 times the second, that row is the SOURCE, its neighbours inherit its score at DOM_HOP1 = 1.0 and their neighbours at DOM_HOP2 = 0.7 divided by the root of the intermediate's degree, and each element takes the larger of this and what it already had. Chosen on the generated two-hop arm (D0364) by a rule fixed before the sweep - the highest hit count there subject to no regression on the one-hop arm's hits, median position and mean rows. Measured two-hop then one-hop: off 15/50 median 8, then 49/50 median 3; 1.25 -> 22/50 median 5, then 49/50 median 3, TAKEN; 1.1 -> 27/50 but 48/50 and median 4; 1.0 -> 36/50 but 45/50 and median 5. DOM_HOP2 was indifferent on the deciding arm at 0.4, 0.7 and 1.0 and keeps the middle value with nothing claimed for it; DOM_HOP1 below 1.0 cost top-three placements, 9/22 down to 4/22. The KEEL_RECALL_* knobs both harnesses have passed through since D0325 are now READ by the binary, and KEEL_RECALL_DEBUG=1 prints the whole ranking with each component broken out.";
        :>> rationale = "Why the dominance test rather than a blanket second hop: the blanket form was measured under D0325 and rejected - neutral at small factors and 45-46/50 at large ones - because it spends the payload's rows on a flat field of candidates. The test is what makes the second hop conditional on there being one record the payload is clearly about, and the sweep shows the cost of relaxing it: at 1.1 and 1.0 the far cases are bought with near ones, and the pre-stated rule refuses that trade rather than trading it off by judgment after the fact. Why it reads the folded ranking rather than the seed ranking: that is the entire finding - the row a payload is about is frequently not the best lexical match, and every earlier mechanism could only ever lift what the words had already named. Degree normalisation is applied to the two-hop ring but not to the source's own neighbours, because the claim being made about those is precisely that they come with the source.";
        :>> consequences = "The criterion's second clause is met: the hand set reads 7/8, stable across three consecutive runs, with the rebase question's d0129 arriving at position 8. It was read only after the mechanism was chosen and no parameter was moved afterwards. The remaining miss is the obligation question, whose ground-truth Decision uses the word once and is not reached by any mechanism; issue391 already records that as a measurement-definition question for the human and it stays open, unchanged by this. recallRanksLinkedRecordsAsWellAsGrepDoes passes and issue367 is resolved. The one-hop arm's top-three placements fall from 30/49 to 28/49, which the pre-stated rule did not count and which is recorded here rather than omitted. NOT A FORK: this Decision chooses one course; the settings it names are measurements that rejected the others.";
    }

    // D0303: this is the second clause of a layered change - D0364 supplies the arm that chose it.
    #DependsOn dependency from d0365 to d0364;

    // acceptance event (D0121 review-queue sign-off; D0066/D0106 — human-judged, not fabricated)
    verification d0365Accept : Test { :>> id = "f245a161-132d-47de-9db2-63b8f00e8cff"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0365AcceptR1 : TestResult { :>> id = "2de01734-3cfe-465f-9aeb-f3241dac55aa"; :>> outcome = VerdictKind::pass; :>> judgedAgainst = "018315a"; :>> judgedAt = "2026-09-07"; :>> judgedBy = "wweatherholtz"; :>> createdBy = "claudeOpus5"; }
}
