// D0188 — PROPOSED. The exact assertion behind "decisions carry their scaffolding": an accepted
// #ProspectiveChange Decision must be reachable by a tracked-item edge by the close of its landing
// sprint, forward-only. #ProspectiveChange (D0070).
package ReferenceDecision0188 {
    private import EngineElement::*;
    private import EngineWork::*;
    private import EngineVerification::*;
    private import EngineRelationships::*;

    #ProspectiveChange part d0188 : Decision {
        :>> id = "894c5859-f2fe-4a78-aa11-b0ff7665680a";
        :>> title = "D0188: an accepted #ProspectiveChange Decision must be reachable by a tracked-item edge by the close of its landing sprint - forward-only, guard-enforced";
        :>> createdAt = "2026-08-21";
        :>> createdBy = "claudeOpus5";
        :>> status = DecisionStatus::accepted;
        :>> context = "THEIR TWO NOTES FROM THE 2026-08-21 DECK REVIEW. On issue174 (st015): 'the scaffolding under a decision isn't being made - is there no downstream backlog items? user stories? verification test cases to those items? sounds like we're not following processes again.' On issue173 (st014): 'depends on what is being asserted.' The second note is the design constraint on the first: before anything is enforced, the assertion must be NAMED, narrowly enough to be defensible. THE MEASUREMENT EXISTS FIRST: `keel decision-follow-through` (sprint 383) computes, for every accepted Decision, its downstream tracked items by typed edge and its gaps - currently 64 of 168 accepted Decisions have zero downstream items, most of them early-era Decisions that predate work-tracking edges and many legitimately needing no work. That mix is exactly why the raw gap count is a view to read, never a verdict, and why this Decision asserts a SUBSET.";
        :>> decision = "PROPOSED, this assertion exactly: a Decision that is (a) marked #ProspectiveChange and (b) accepted ON OR AFTER this Decision's acceptance date must be reachable by at least one tracked-item edge (charteredby, derivedfrom, resolves, or satisfy) BY THE CLOSE OF THE SPRINT THAT LANDS ITS ACCEPTANCE. Enforced as guard 41 (decision-scaffolding, HARD), computing over the same edge logic as `keel decision-follow-through`. Forward-only: the boundary is D0188's own acceptance date, read from its recorded acceptance event - the 64 historical gaps are never retro-failed, and the guard's doc row names the boundary. The 'close of the landing sprint' grace exists because acceptance and the chartered work land in one commit in this repo's practice, but a multi-contributor project may accept in one integration and charter in the next; operationally the guard fails a tree where a post-boundary accepted #ProspectiveChange Decision has zero inbound tracked-item edges AND is not the most recently accepted decision awaiting its landing sprint.";
        :>> rationale = "WHY #ProspectiveChange DECISIONS ONLY: their marker MEANS 'this Decision changes process or schema going forward' - a promise of work by definition - while plain Decisions include 'we will not do X' records that rightly need nothing (invariant 4). Scoping to the marker answers st014 with a class whose members all assert the same thing. WHY AN EDGE RATHER THAN AN ARTIFACT CHECK: the hardening lens already checks DECLARED artifact promises; edges are what the model itself can verify without a registry, and they are what the follow-through view computes - guard and view stay one truth. ENFORCEMENT TIER, COMPOSED WITH D0188'S PARALLEL SIBLING: this proposal first said hard-from-day-one, citing the retro-backlog guard's history (issue189: warning-tier process controls get satisfied vacuously). The concurrently proposed D0180 says advisory-to-blocking promotions cite at least three sprints of measured evidence. REVISED TO COMPOSE rather than conflict: guard 41 lands WARNING-tier; its promotion to hard follows D0180's measurement rule if D0180 is accepted, and otherwise happens after one sprint with zero violations - and in either path the promotion is a recorded review, not a default, because issue189's lesson is that an unreviewed warning tier is where controls go to be ignored. WHY FORWARD-ONLY: retro-failing 64 historical records would force either fabricated edges or a permanent bypass - the D0132 lesson both ways.";
        :>> consequences = "IF ACCEPTED: guard 41 lands WARNING-tier (GUARD_NAMES, dispatch, guards.md row, CLAUDE.md counts), computing the post-boundary check from the model's edges, with its promotion to hard following the composed rule in the rationale; the first sprint after acceptance is its own first test, since D0188 itself is #ProspectiveChange and must be reachable by an edge - dcDecisionScaffoldingGuard's #DerivedFrom already satisfies it. COSTS, stated: a genuinely work-free future #ProspectiveChange Decision must either carry a superseding edge structure (a Decision that resolves an Issue counts via `resolves`) or record why in a tracked item - one item of overhead where today there is none; and the landing-sprint grace is judgment encoded in a guard, which will need a tightening review if it is ever gamed. IF REJECTED: the follow-through view remains the oversight surface and the gaps stay a human-read list. REMOVAL PATH (D0163): delete guard 41 and its registrations, supersede this Decision; the view is untouched.";
    }

    // acceptance event (D0121 review-queue sign-off; D0066/D0106 — human-judged, not fabricated)
    verification d0188Accept : Test { :>> id = "96f9e008-342c-43cc-b155-b6e621aa9ccd"; :>> method = VerificationMethod::confirmation; :>> procedureText = "Their words, verbatim: 'accepted all'. Said in response to the presented queue of fifteen proposed Decisions - D0174 through D0188 - so 'all' is that queue and this acceptance covers d0188 as one of the fifteen. Guard 41 therefore lands WARNING-tier per the composed rule with D0180, whose acceptance is recorded in the same sign-off."; }
    part d0188AcceptR1 : TestResult { :>> id = "6a66323a-1f99-468d-912a-2b79242a8b3a"; :>> outcome = VerdictKind::pass; :>> judgedAgainst = "a3160ea"; :>> judgedAt = "2026-08-21"; :>> judgedBy = "wweatherholtz"; }
}
