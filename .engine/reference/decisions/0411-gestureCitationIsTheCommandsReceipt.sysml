// D0411 (status: the `status` field below is the truth) — gestureCitationIsTheCommandsReceipt: a gesture citation in an acceptance record is written by the surface that observed the gesture and re-verifiable from the record, never typed into a note
// Recorded via `keel record decision` (D0105 RMWX axis; issue054). Acceptance is a separate explicit
// human gate (method=confirmation, D0106): flip status + add the d0411Accept event on sign-off.
package ReferenceDecision0411 {
    private import EngineElement::*;
    private import EngineWork::*;
    private import EngineVerification::*;
    private import EngineRelationships::*;

    // #ProspectiveChange (D0070) - this Decision governs a process/schema change; the co-committed
    // change rides the process-change guard's hard lock.
    #ProspectiveChange part d0411 : Decision {
        :>> id = "5d8034ff-3cd5-413a-8640-44187c4b56d8";
        :>> title = "gestureCitationIsTheCommandsReceipt: a gesture citation in an acceptance record is written by the surface that observed the gesture and re-verifiable from the record, never typed into a note";
        :>> createdAt = "2026-09-09";
        :>> createdBy = "claudeOpus5";
        :>> status = DecisionStatus::accepted;
        :>> context = "issue426, found by stpa-self run 2 (UCA-AC1, ucaAcceptGestureIsTyped) and tracked as dcGestureCitationsAreWrittenByTheCommand. The delegated-acceptance substance rule (D0192, acceptQuotesDelegatedWords) accepted a record whose note quoted the human OR named a gesture - the words console, deck, a GitHub URL, or the TTY phrase - and the command's channel layer (verdict_channel_refusal, main.rs) read the same function before the write. The gesture words were meant to be the console's, the deck's and the terminal's own citations (issue235, D0315), but nothing distinguished a citation the surface wrote from one a recorder typed: an agent session with agent markers and no terminal could run keel accept --note 'approved at the console' under the delegation and the record passed every gate. The console's own tag, [device <12 chars> HMAC-verified], was text too - the server verified the HMAC and then discarded it, so no reader could check the tag later.";
        :>> decision = "NOT A FORK: the DoD names the property and each surface has exactly one way to make its citation true. A gesture citation is written by the surface that observed the gesture and is re-verifiable from the record. The console (and every device-bound tap: gate result, disposition, reject, test result) appends the receipt [device <full id> hmac=<hex> HMAC-verified] beside its citation, and device::reverify recomputes the signature from the record's own fields - kind, target, judgedAt, judgedBy and the note as signed - against the machine-local device store; the console gesture and the receipt are stripped before the check because the tap signed the note before either was added. The terminal path is unchanged: keel accept with stdin a TTY cites it in the form the command writes (D0315). In an agent-marked session with no terminal, verdict_channel_refusal classifies the note before the write: a quoted span records under the delegation (with read-back, D0201 B); a gesture word with no quoted span is refused naming the mechanism and --words as the remedy; neither is refused as before. The substance rule gains a second date, acceptQuotesDelegatedWords(2026-08-22, 2026-09-09): from it a DELEGATED record (recorder differs from judge, or no recorder stamped) evidences its channel only by a quoted span or by the observed-TTY citation; console, deck and GitHub words are text, and the KEEL_TTY_GESTURE stand-in, which names itself asserted rather than observed, does not count. Self-recorded records stay exempt (issue287) - that is where the console's and deck's own records fall. Both dates read raised to the adopting project's adoption date (D0319).";
        :>> rationale = "A citation is evidence only if the party that could have fabricated it could not have written it. The console writes its record with recorder == judge and now leaves the signature it verified in the record, so the claim device X signed this tap can be re-run by anyone holding the store; the terminal path writes its phrase only when it observed a terminal, and the agent arm refuses the same phrase typed. A gesture word in a delegated record has no such writer - the surfaces it names never produce a delegated record - so from the strict date it is read as the text it is. The cutoff is forward-only by the issue068 rule: every earlier record was made under the rule as it then read, and the six GH#53 acceptances and the TTY test's own record stay green. The stand-in's exclusion costs nothing real: it exists so a test can exercise the TTY path without a terminal, and its record says so in its own words.";
        :>> consequences = "keel-cli/src/device.rs gains CONSOLE_GESTURE, receipt_tag, parse_receipt, reverify and reverify_against with a unit test; serve.rs appends the receipt at all five tap sites and on every console acceptance; view/mod.rs gains NoteReceipt and note_receipt; main.rs verdict_channel_refusal refuses a gesture-word-only note with the remedy named; view/checks.rs gains quotes_delegated_words_strict and the two-date reading of acceptQuotesDelegatedWords, raise_cutoffs raises every date a term carries; .engine/rules/rules.sysml carries the second date; keel-cli/tests/gesture_citation_is_the_commands.rs shows the refusal on accept and reject and the --words path recording, and device_bound_taps.rs re-verifies a live console record from the store and shows an altered one refused. The substance rule is a gating rule and the command arm is a control: this Decision is the SafetyChange the keystone lock requires (D0209 clause 2) and, as a process change, is outside standing consent (D0337) - it stays proposed for the human. STATED LIMIT, unchanged from D0192: a hand edit of a decision file that inserts a quoted span is not caught by this; the receipt closes the gesture path, not the quote path.";
    }

    // acceptance event (D0121 review-queue sign-off; D0066/D0106 — human-judged, not fabricated)
    verification d0411Accept : Test { :>> id = "a148e9a2-f95a-4d8f-9129-627787e07cac"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0411 (D0201 B); recorded as given (D0423)."; }
    part d0411AcceptR1 : TestResult { :>> id = "2f5b8019-70c8-4e8e-af55-0f1661835cc5"; :>> outcome = VerdictKind::pass; :>> judgedAgainst = "3e6c518"; :>> judgedAt = "2026-09-11"; :>> judgedBy = "wweatherholtz"; :>> createdBy = "claudeOpus5"; }
}
