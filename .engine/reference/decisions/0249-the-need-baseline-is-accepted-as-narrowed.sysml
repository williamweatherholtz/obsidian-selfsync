// D0249 (status: the `status` field below is the truth) — The Need baseline is accepted as narrowed, one item leaves the tier, and the ungrounded ratio becomes a trigger
// Recorded via `keel record decision` (D0105 RMWX axis; issue054). Acceptance is a separate explicit
// human gate (method=confirmation, D0106): flip status + add the d0249Accept event on sign-off.
package ReferenceDecision0249 {
    private import EngineElement::*;
    private import EngineWork::*;
    private import EngineVerification::*;
    private import EngineRelationships::*;

    // #ProspectiveChange (D0070) - this Decision governs a process/schema change; the co-committed
    // change rides the process-change guard's hard lock.
    #ProspectiveChange part d0249 : Decision {
        :>> id = "de16561a-5fb8-4816-924c-8347e13d4452";
        :>> title = "The Need baseline is accepted as narrowed, one item leaves the tier, and the ungrounded ratio becomes a trigger";
        :>> createdAt = "2026-08-28";
        :>> createdBy = "claudeOpus5";
        :>> status = DecisionStatus::accepted;
        :>> context = "KEEL-ND-0001 v0.2 put the fourteen derived Needs to the human as five decisions, following D0157: ask what is WIDER than they meant, never whether the set is good. They returned the page's Copy-for-AI digest with a selection in every tab and one note. The selections are quoted verbatim in engineNeedsAcceptAttest1; the acceptance itself is engineNeedsAccept, judged by wweatherholtz against commit 32149b5. This is the gate the business-architecture workflow holds Phase 2 behind, and it is the SECOND attempt at it. The first was refused by me: an earlier one-word 'proceed.' was recorded as an instruction and explicitly NOT as an attestation (D0248), because a confirmation asserts that a human judged a specific claim and 'proceed.' is consistent with the document never having been opened. The difference between the two replies is exactly what the gate exists to detect - and the difference produced a real correction, which is the evidence that refusing the first one was right rather than pedantic.";
        :>> decision = "Four clauses. CLAUSE A - THE SET IS ACCEPTED AS NARROWED. Thirteen of the fourteen stand as Needs. Their note - 'Repo holds several projects is a use case, not a need' - is applied: nRepoHoldsSeveralProjects LEAVES the Need tier and is authored as the use case ucRepoHoldsSeveralProjects, carrying its #DerivedFrom to us029 and receiving the #Implicates edge that pointed at the Need. Their reading is correct on this project's own test: a Need is an OUTCOME a stakeholder wants, a UseCase is a concrete USAGE that exercises Needs, and 'several projects in one repository' describes how the engine is used rather than something anyone needs from it. CLAUSE B - ONE CLAUSE OF THE FORMER NEED IS PARKED, NOT DROPPED. 'The engine gates every project the act touches and NAMES THE ONES IT SKIPPED, rather than gating one and appearing to gate all' is an honest-state property about coverage, not a usage. It is carried on the use case's extensions so it stays visible and searchable. Whether it earns its own Need is an OPEN QUESTION recorded here and not decided. CLAUSE C - THE UNGROUNDED RATIO BECOMES A TRIGGER, MONITORED AND NOT GATED. rootedness's decision-ungrounded count becomes the computed trigger for the latent-need derivation process: the number says WHEN to run the process, and nothing gates on its value. This is the option the human selected over gating it with a declared threshold, and it is the same answer nMonitoredNotGated states in general - no defensible boundary exists for this ratio today, and gating an unjustifiable number converts it into the target. CLAUSE D - PHASE 2 OPENS IN FULL. SystemRequirements with measurable thresholds satisfy-linked to the thirteen accepted Needs, the architecture Decisions for the genuine forks, then sprint design with Gherkin scenarios and tests authored before implementation.";
        :>> rationale = "WHY THE NARROWING IS THE POINT, not an inconvenience. D0157 records a Need that was not wrong, only wider than the demand, whose wide half a later reader decomposed into work nobody had asked for. The read-back asks what is WIDER precisely so that outcome is caught before requirements are derived. Here it caught something better than a wide clause: an item in the WRONG TIER. Had 'proceed.' been recorded as acceptance, nRepoHoldsSeveralProjects would now be a must-priority Need with SystemRequirements being derived beneath it, and the correction would have cost a supersession chain instead of an edit. WHY THE PRIORITY ANSWER IS RECORDED WITH ITS DISCREPANCY. They selected 'priorities stand as set: 12 must, 2 should' against the FOURTEEN-item set, and their own note removes one of those twelve musts from the tier. The eleven remaining musts and two shoulds keep the priorities they had; only the tally moves. No priority was reassigned on their behalf, and the discrepancy is stated in the quote receipt rather than silently reconciled - a tally corrected without saying so is how a reader comes to believe a human ratified a number they never saw. WHY THE TRIGGER IS NOT A GATE. The obvious objection is that a gated threshold would have caught this years earlier, and it is a fair one. But no threshold is defensible today: nobody can say what fraction of decision-chartered work SHOULD be Need-rooted, and this project has already been burned once by an all-or-nothing gate on a number it could not justify. A trigger gets the recurrence without the Goodhart failure, and the process it triggers is where judgment belongs. WHY THE QUOTE RECEIPT IS JUDGED BY ME AND THE ACCEPTANCE BY THEM. The acceptance is the human's judgment and carries their id. The receipt is MY transcription of what they sent and carries mine. Recording both under the human would make my transcription look like their attestation - a small thing that is exactly the confusion D0198 introduced quote receipts to prevent. COST OF NOT DECIDING. Phase 2 stays shut, thirteen accepted Needs sit without requirements, and the reclassification the human asked for is left in conversation rather than the model.";
        :>> consequences = "The Need tier goes from 14 gaps to 13; ucRepoHoldsSeveralProjects is a UseCase and no longer counts as an undecomposed Need. tier-satisfaction's denominator drops by one accordingly. engineNeedsAccept is a passing method=confirmation result judged by wweatherholtz, with engineNeedsAcceptAttest1 carrying their selections verbatim. guard confirmation-authenticity passes over 242 scanned records. D0248's refusal stands as recorded and is NOT retracted: it was correct when written, and this Decision does not make the earlier 'proceed.' into an acceptance retroactively. The Business-to-Architecture gate is now OPEN for the thirteen. Requirements may be recorded against them and not against anything else. OPEN, and deliberately not closed here: whether the gate-names-what-it-skipped property earns its own Need (clause B), and D0247's own acceptance, which is separate from this one and still outstanding.";
    }

    // acceptance event (D0121 review-queue sign-off; D0066/D0106 — human-judged, not fabricated)
    verification d0249Accept : Test { :>> id = "ea979b66-6f36-46df-97a1-fb8d4b660992"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0249AcceptR1 : TestResult { :>> id = "f035eaa9-845d-4cb6-80d3-93aaf2b22290"; :>> outcome = VerdictKind::pass; :>> judgedAgainst = "cf6415a"; :>> judgedAt = "2026-08-29"; :>> judgedBy = "wweatherholtz"; }
}
