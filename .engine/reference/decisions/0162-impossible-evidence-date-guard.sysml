// D0162 — PROPOSED. Guard 36 (impossible-evidence-date) and its forward-only line. Recorded because
// adding a hard commit gate is a §3a CHANGE, and because the grandfather line exempts thirteen existing
// facts — an exemption no guard should grant itself.
package ReferenceDecision0162 {
    private import EngineElement::*;
    private import EngineWork::*;
    private import EngineVerification::*;
    private import EngineRelationships::*;

    part d0162 : Decision {
        :>> id = "a52e7d64-8b03-4f19-9c76-2d10ba85e7f3";
        :>> title = "D0162: a judgment may not cite a commit that postdates it — guard 36, hard-blocking, forward-only from 2026-08-18";
        :>> createdAt = "2026-08-18";
        :>> createdBy = "claudeOpus5";
        :>> status = DecisionStatus::accepted;
        :>> context = "I FABRICATED AN ATTESTATION MECHANICALLY AND EVERY EXISTING CONTROL STAYED GREEN. Stamping evidence SHAs for sprint 343 I ran a blanket replace of judgedAgainst = PENDING across three files. One of the results it rewrote was a method=confirmation from the DAY BEFORE, judged by wweatherholtz: it then asserted they had attested something at a commit created today that they had never seen. The same replace pointed their RETRACTION at the commit containing the fix — claiming they observed the failure against the build that fixes it — and rewrote a prose sentence whose entire point was that the result was unstamped. validate, attestation-substance, attestation-authority and confirmation-authenticity all passed, because each field remained individually well-formed. THOSE GUARDS ASK WHETHER AN ATTESTATION IS SUBSTANTIVE AND AUTHORISED; NONE ASKED WHETHER IT WAS POSSIBLE. §4 of the response contract forbids fabricating an attestation and I did not intend to — which is precisely the argument for a control, because D0047 is explicit that intent and vigilance are not controls. D0108's ownership rule (only the owner edits its fields) already forbade this in words and had no mechanism behind it for the batch-rewrite case.";
        :>> decision = "PROPOSED: add guard 36, `impossible-evidence-date`, HARD-BLOCKING in GUARD_NAMES. A TestResult whose `judgedAgainst` commit has an author date LATER than its `judgedAt` is a violation, because a judgment cannot be made against a commit that did not yet exist. Day granularity, strictly-later to violate, so a same-day stamp — the normal case — never fires. Unresolvable SHAs are SKIPPED rather than flagged: `evidence-resolves` owns that failure, and one field reporting two different errors teaches nothing. THE FORWARD-ONLY LINE IS 2026-08-18 AND IS KEYED ON THE CITED COMMIT'S DATE, NOT ON judgedAt. That distinction is the whole design and I got it wrong first: keying on judgedAt exempted the very defect the guard exists for, because a day-old judgment stamped at today's commit is OLD by judgedAt and BRAND NEW by evidence. Keying on the commit means every stamp made from now on is in scope no matter how old the judgment it is attached to, while genuinely historical evidence stays exempt. WHAT THE LINE EXEMPTS, stated exactly: thirteen results in two commits, each exactly one day out — 2026-06-16 judged against a 2026-06-17 commit (eight results, claudeOpus) and 2026-06-21 against a 2026-06-22 commit (five results, wweatherholtz). Both are sessions that crossed midnight, which is benign.";
        :>> rationale = "WHY HARD AND NOT WARNING-LEVEL, against this repo's own D0102 promote-once-low-noise pattern: a warning would not have blocked the write that motivated it, and the failure it catches is not incompleteness but a false claim about a HUMAN's word — the single class §4 treats as never acceptable. The noise argument that justifies warning-level introductions does not apply, because the check is exact and arithmetic: it compares two dates from git and the model, with no heuristic and no judgment. Measured cost is one `git show` per DISTINCT SHA, memoised across 3799 results. WHY THE THIRTEEN ARE GRANDFATHERED RATHER THAN CORRECTED: five of them are the human's own attestations, and D0108 makes only the owner competent to edit an item's fields, so 'fixing' their judgedAt to match the commit would be me editing their record to satisfy my new guard — the exact inversion of what this Decision is for. Grandfathering costs nothing here because the exempted set is closed: it is thirteen named results in two commits that will never grow, since the line is keyed on commit date. WHY THIS IS NOT MERELY A DATE CHECK: it is the only control in the inventory that asks whether a recorded judgment was POSSIBLE rather than whether it is well-formed or authorised, and the defect it caught was invisible to all three existing attestation guards simultaneously. A bulk transform over provenance fields is the general hazard; this is the general control, and it does not care which tool did the writing.";
        :>> consequences = "IF ACCEPTED: 36 guards, 27 hard-blocking and 9 warning-only. A batch stamp can no longer relocate anyone's judgment forward in time without the commit gate refusing. THE COST TO ME IS REAL AND WORTH NAMING: any future correction to a genuinely mis-stamped historical result must now either be same-day or be recorded as a NEW result rather than an edit to the old one, which is the honest shape anyway. IF REJECTED: the guard comes out and the recorded position is that a bulk provenance rewrite is prevented by care alone, which D0047 already rejects in general terms — so a rejection should say what control replaces it. EXPLICITLY NOT INCLUDED: a check on `judgedBy` matching the actor performing a stamp, which would be the tighter control but lives in the write path rather than in the model, and would not catch a stamp made by direct file editing. The guard checks the OUTCOME instead, which is tool-independent.";
    }

    // acceptance event (D0121 review-queue sign-off; D0066/D0106 — human-judged, not fabricated)
    verification d0162Accept : Test { :>> id = "47eac166-c017-4e68-ad2d-215502e7b6bc"; :>> method = VerificationMethod::confirmation; :>> procedureText = "ACCEPT - submitted in the obligations deck review of 2026-08-20 (verdict recorded with no per-item note)"; }
    part d0162AcceptR1 : TestResult { :>> id = "81325575-cf71-4183-b719-f5bae9738fd0"; :>> outcome = VerdictKind::pass; :>> judgedAgainst = "b7e000d"; :>> judgedAt = "2026-08-20"; :>> judgedBy = "wweatherholtz"; }
}
