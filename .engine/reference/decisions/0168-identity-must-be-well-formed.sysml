// D0168 — PROPOSED. Guard 38 enforces that an `id` is SHAPED like a UUID. Invariant 3 already says
// identity IS a UUID; nothing checked it, and an id of "not-a-uuid-at-all" passed every gate.
// Adding a hard-blocking guard is a gate change, so it needs sign-off. #ProspectiveChange (D0070).
package ReferenceDecision0168 {
    private import EngineElement::*;
    private import EngineWork::*;
    private import EngineVerification::*;
    private import EngineRelationships::*;

    #ProspectiveChange part d0168 : Decision {
        :>> id = "7e40b1c5-2d86-4f93-a07b-51ce38da6427";
        :>> title = "D0168: guard 38 `identity-well-formed` — an id must be shaped 8-4-4-4-12, with the 15 historical malformations grandfathered as an explicit list rather than a date";
        :>> createdAt = "2026-08-20";
        :>> createdBy = "claudeOpus5";
        :>> status = DecisionStatus::accepted;
        :>> context = "FOUND BY MY OWN DEFECT, WHICH IS THE ONLY REASON IT WAS FOUND AT ALL. Authoring three UserStory items I produced two mangled ids - the strings 'a period-placeholder' and '64bc17ea5device' appeared inside them - and `keel gate --fast` reported 391 files clean. Tested deliberately afterwards: an id of literally 'not-a-uuid-at-all' passes `keel validate` AND all 37 guards. Invariant 3 states that identity is an immutable UUID. `identity-present` (guard 37, shipped hours earlier) checks that an id EXISTS; `duplicate-identity` checks that two items do not SHARE one. THE MIDDLE PROPERTY - that the string is an identifier at all - was enforced by nothing, and the two guards flanking it made it look covered. WHY A MALFORMED ID IS SILENT RATHER THAN LOUD, which is the whole reason it survived: it is still UNIQUE. It collides with nothing, every view resolves it happily, every edge referencing it by NAME still resolves, and no gate has any reason to look. The corruption surfaces only when something outside this repository tries to join on it - which is to say, at the moment it is most expensive. WHAT CAUGHT IT was reading my own tool output, which is exactly the manual vigilance D0047 says is not a control.";
        :>> decision = "PROPOSED: guard 38 `identity-well-formed`, hard-blocking, over `.tracking` and `.engine`. An `id` must be five groups of 8-4-4-4-12 characters drawn from [0-9a-z]. SHAPE, NOT STRICT HEXADECIMAL, and the corpus is the reason: 9119 id declarations were measured BEFORE the guard was written, and 78 of them deliberately carry a mnemonic suffix - the intake process steps are `4b78e0c1-3f52-4d96-a814-000000000i01` and up - which is UUID-shaped but not hex. Those are intentional and readable, they make a process file navigable, and a guard failing them would demand a migration nobody asked for to enforce a property nobody needs. Shape catches every actual defect: the two ids that prompted this, plus 15 historical malformations with 7- and 9-character first groups that shape finds and hex would merely also find. THE GRANDFATHER SET IS AN EXPLICIT LIST OF 15 NAMED STRINGS, and this is the part I would defend hardest. Guard 36's first version keyed its exemption on a DATE and thereby exempted the very defect the guard existed to catch - a mistake made in this same session. Fifteen named strings cannot absorb a sixteenth: a new malformed id fails no matter when it is written. Its size is asserted by a test, so growing the list means deliberately editing a failing test rather than quietly accommodating a defect. THE 15 ARE NOT REWRITTEN: section 1.3 makes identity IMMUTABLE, so an id is wrong there and changing it would be a second wrong, not a fix.";
        :>> rationale = "WHY THIS IS A GUARD AND NOT A CONVENTION: D0047 - a defect revealing a recurrable gap becomes a tracked Issue AND an automated control, never a reminder. I will mangle an id again; heredoc quoting has corrupted my authoring three separate times this session, and each time the corruption was caught by me happening to look. WHY THE FLANKING GUARDS MADE IT WORSE, which is the transferable lesson: `identity-present` and `duplicate-identity` between them make identity LOOK guarded, and I shipped the first of them hours before writing an id with a space in it. A property split across two guards leaves a gap exactly where neither one's name suggests it should be, and the more guards there are the more confidently that gap is assumed covered. WHY SHAPE RATHER THAN A FULL UUID PARSE: the guard path must stay kernel-free and dependency-light (D0048), the group lengths ARE the specification, and a strict RFC parse would reject the mnemonic convention while adding nothing - there is no version or variant bit anything in this engine reads. Uppercase is rejected: one id with two spellings is not one identity.";
        :>> consequences = "MEASURED, per the rule sprint 347 set after a guard of mine tripled `keel assured`: 215-253ms across three runs with `Model::build was never called` - a text scan, so `keel assured` does not slow down. 9119 id declarations scanned, 0 violations on a clean tree. VERIFIED BOTH WAYS, on the real defects rather than invented ones: 'not-a-uuid-at-all' FAILS, '3a86f04d-...-64bc17ea5device' FAILS, '4b07d2f6-9e35-4c81-a period-placeholder' FAILS, the clean tree PASSES, and the mnemonic convention PASSES. Three unit tests cover the predicate's near-misses, the multiple-ids-per-line case (a sprint record declares an item and its result on one line, so stopping at the first id would blind the guard to where most ids live), and the grandfather set's size. WHAT THIS DOES NOT DO: it does not check that an id is a genuine random UUID, only that it is shaped like one - a deliberately-chosen readable id still passes, which is what keeps the 78 mnemonic ids legal. It also cannot check ids in files it does not scan. REMOVAL PATH, per D0163: delete `identity_well_formed`, its two helpers, its dispatch arm and its GUARD_NAMES entry, decrement the array size to 37, delete `identity_form_tests`, and remove the guards.md row. Nothing depends on it - a guard is a pure predicate over text, so removing it can only make the gate more permissive. IF REJECTED: invariant 3's UUID clause stays unenforced, and the next mangled id enters the model silently and stays there, because identity is immutable once written.";
    }

    // acceptance event (D0121 review-queue sign-off; D0066/D0106 — human-judged, not fabricated)
    verification d0168Accept : Test { :>> id = "65b2f1bc-0688-4780-b34e-c9ab5ae6fd47"; :>> method = VerificationMethod::confirmation; :>> procedureText = "Their words, verbatim: 'accept all. proceed'. Said in response to the queue of six proposed Decisions presented for signature - D0167, D0168, D0169, D0170, D0171, D0172 - so 'all' is that queue and this acceptance covers d0168 as one of the six. For D0170 the acceptance includes the Decision's stated lean, retire."; }
    part d0168AcceptR1 : TestResult { :>> id = "7ab666d9-1faa-4932-9f79-18da6f0888da"; :>> outcome = VerdictKind::pass; :>> judgedAgainst = "3abc583"; :>> judgedAt = "2026-08-20"; :>> judgedBy = "wweatherholtz"; }
}
