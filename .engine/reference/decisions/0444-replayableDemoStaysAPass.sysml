// D0444 (status: the `status` field below is the truth) — replayableDemoStaysAPass: a demo whose RAN receipt is a command a machine can re-run stays a pass, and keel reverify --demos re-runs it
// Recorded via `keel record decision` (D0105 RMWX axis; issue054). Acceptance is a separate explicit
// human gate (method=confirmation, D0106): flip status + add the d0444Accept event on sign-off.
package ReferenceDecision0444 {
    private import EngineElement::*;
    private import EngineWork::*;
    private import EngineVerification::*;
    private import EngineRelationships::*;

    // #ProspectiveChange (D0070) - this Decision governs a process/schema change; the co-committed
    // change rides the process-change guard's hard lock.
    #ProspectiveChange part d0444 : Decision {
        :>> id = "4a84a7a1-8a54-4d2f-b2ed-6019bc195d73";
        :>> title = "replayableDemoStaysAPass: a demo whose RAN receipt is a command a machine can re-run stays a pass, and keel reverify --demos re-runs it";
        :>> createdAt = "2026-09-11";
        :>> createdBy = "claudeOpus5";
        :>> status = DecisionStatus::accepted;
        :>> context = "D0312 option B drew the line between an EXERCISED claim and an EXAMINED one at the method: an AI's pass on method=test stands on its RAN receipt (refused without one, issue448), an AI's pass on demo, analyze or inspect lands VerdictKind::proposed (dcProposedOutcomeTier, sprint 663). B also said what separates it from option A: a demo whose receipt is REPLAYABLE - a command a human or CI can re-run - is exercised in substance and should stay a pass, because the receipt is not the AI's word, it is a procedure anyone can repeat. Today write.rs proposed_tier knows exactly one replayable form, D0323's ci-run id=<id> workflow=<name>, and every other demo receipt - including `// RAN: keel show control-structure . --svg` on the 169 demo Tests this tree holds - is testimony to it. keel reverify (D0101) re-runs the commands in .engine/contracts/reverify.toml for drift-suspect deliverable tasks and stamps a pass only after the real command exited 0; it never reads a result's own receipt, so a demo receipt that names a command is written once and run by nobody. The human's words that chartered this line of work, 2026-09-11: 'all the test is in terms of I did X process and the guards worked great but the actual meat of the content seems to have gone downhill' - a demo that a machine re-runs is meat; a demo a human must read is a checklist item.";
        :>> decision = "A `// RAN:` receipt on a method=demo result is REPLAYABLE when it IS the command and nothing else: the trimmed receipt is one line, it begins with one of the prefixes .engine/contracts/reverify.toml declares under [demo] replayable (this project: 'keel ', 'cargo test', 'python scripts/probes/'), and every space-separated token is drawn from the command alphabet (letters, digits, and _ . / : = @ -) and is not one of the sixteen English function words a narrative needs (a, an, and, at, for, from, in, is, of, on, per, the, then, to, was, with) - or it is a ci-run receipt (D0323). The shape rule is measured, not guessed: a census of this tree's 283 receipts that begin with a declared prefix found 282 narratives ('keel suite 571 passed, 0 failed'), which a prefix rule alone would have classed replayable and --demos would have failed every one; the alphabet rule alone admitted one narrative ('keel validate . 762 clean and keel check-engine . clean at 829e0f0 per VERIFIER_RECEIPT 2026-09-11'); alphabet plus the function words admitted none. A fail's evidence begins 'replay of', so a recorded failure is never itself replayable. An AI-judged demo pass with a replayable receipt is recorded pass by proposed_tier, exactly as a ci-run receipt is; a demo with a prose receipt or none lands proposed like any other examined claim. `keel reverify --demos` reads every demo Test whose latest result is a pass carrying a replayable receipt, re-runs the command at HEAD from the project root (a leading `keel ` is the running binary itself, so the replay and the gate are the same engine, D0230), and on exit 0 appends a fresh pass carrying the same receipt; on a non-zero exit it appends a FAIL whose evidence names the command and its exit code, so the replay is exercised and its verdict is a line, not an assertion. The attestation census counts demoReplayable apart from demoProposed. The D0443 sample pool is proposed results PLUS replayable demo passes no human has judged, so a demo that replays green for the wrong reason keeps a reader; proposed stays the count of proposals alone and sampled is never below judged.";
        :>> rationale = "The line B drew is exercised versus examined, and a command receipt is the exercised kind whoever typed it: what makes a pass stand is that someone else can produce the same verdict, and a prefix list declared in the project's own reverify contract is how that someone knows the command is safe to run. Reusing reverify rather than a new verb keeps one re-run path with one isolation rule (its own CARGO_TARGET_DIR, so a replay never fights the running image, issue150). Keeping replayable demos in the sample pool is B's own risk statement: a replay proves the command still exits 0, not that the demo shows what its title says. NOT A FORK: D0312 B chose this clause; the Decision is its write path and the one rule the clause left open, which receipts count as replayable.";
        :>> consequences = "Process-change: the write path's tier rule, a new reverify flag and a new contract key - held proposed for the human's word (D0337). keel-cli/src/write.rs: proposed_tier consults reverify::is_replayable(root, evidence) for demo. keel-cli/src/reverify.rs: the [demo] replayable prefixes, is_replayable, replay_demos (the --demos run: latest-result scan, the re-run, the pass or fail append with the receipt or the exit code). keel-cli/src/attestation.rs: Proposal gains its kind, the pool grows by replayable demo passes, the JSON gains demoReplayable and demoProposed. keel-cli/src/cli_facts.rs and .engine/cli/commands.sysml declare the flag. .engine/contracts/reverify.toml declares the prefixes; keel init ships the section with this project's three. D0388 pair in write.rs: known-positive - an AI demo pass with evidence 'keel show control-structure . --svg' lands pass; known-negative - the same with evidence 'looked at the picture' lands proposed, and with 'rm -rf target' (no declared prefix) lands proposed. Integration test: a scaffolded project with a demo whose receipt is a command exiting 0 stays pass and reverify --demos re-stamps it; the same with a command exiting 1 appends a fail naming the command. What this does not do: it does not touch the 169 standing demo results (forward-only, D0312 B) and it does not make reverify --demos run in any hook or CI - when it runs is the human's to schedule, by a later Decision if they want it in CI.";
    }
    #DerivedFrom dependency from d0444 to st116;

    // acceptance event (D0121 review-queue sign-off; D0066/D0106 — human-judged, not fabricated)
    verification d0444Accept : Test { :>> id = "97bf83fb-f6b6-4389-936f-aa045205304d"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0444 (D0201 B); recorded as given (D0423)."; }
    part d0444AcceptR1 : TestResult { :>> id = "baaaa3f2-400d-4400-bbea-22f4b1843464"; :>> outcome = VerdictKind::pass; :>> judgedAgainst = "3e6c518"; :>> judgedAt = "2026-09-11"; :>> judgedBy = "wweatherholtz"; :>> createdBy = "claudeOpus5"; }
}
