// D0267 (status: the `status` field below is the truth) — Unattended distribution: two Needs, seven use cases, five contracts — and the rollback everything else rests on
// Recorded via `keel record decision` (D0105 RMWX axis; issue054). Acceptance is a separate explicit
// human gate (method=confirmation, D0106): flip status + add the d0267Accept event on sign-off.
package ReferenceDecision0267 {
    private import EngineElement::*;
    private import EngineWork::*;
    private import EngineVerification::*;
    private import EngineRelationships::*;

    // #ProspectiveChange (D0070) - this Decision governs a process/schema change; the co-committed
    // change rides the process-change guard's hard lock.
    #ProspectiveChange part d0267 : Decision {
        :>> id = "1c16692e-53e6-4e28-8d41-8e6429e00378";
        :>> title = "Unattended distribution: two Needs, seven use cases, five contracts — and the rollback everything else rests on";
        :>> createdAt = "2026-08-30";
        :>> createdBy = "claudeOpus5";
        :>> status = DecisionStatus::accepted;
        :>> context = "The human asked for a plan with Needs and use cases fleshed out, then to push forward. The direction came from three recorded utterances: st047 (an issues pull+ingest pipeline; private acts, public plans; can it deploy globally; how do other projects pull the skill), st048 (a Django-migrations equivalent; antiquated data with no indication what process authored it), st049 (auto-update consent gated, IF correctness can really be guaranteed). THE CONDITION IN st049 WAS TESTED RATHER THAN ASSUMED, and it changed the plan. The gate they liked - auto-apply when the migration plan is empty - is VACUOUS: when the plan is empty `migrate` returns at migrate.rs:739, before `restamp_pin` at :828, so auto-applying an empty plan achieves nothing including advancing the pin; and any real upgrade plans at least the engine resync, so the criterion never fires where it matters. Worse, an empty plan says nothing about safety: a new engine can ship guards the project's existing tree violates, which is the issue089/issue090 class that blocked two downstream projects outright.";
        :>> decision = "THE BUSINESS LAYER, consolidated by the human's own principle (three statements spanning issue pulls, library sync, vintage archaeology and update consent became TWO Needs, not seven): nUnattendedCurrency - a project stays current without the human driving each step, and can SEE where it is behind. nAutonomyBoundedByProof - automatic action extends exactly as far as it can be proven safe, and asks beyond that. One principle, two surfaces: untrusted input plans rather than acts, and an unverifiable update reverts rather than survives. Seven UseCases, three of them FAILURE paths, because an autonomy boundary exercised only on the happy path is a claim rather than a boundary. Five SystemRequirements with thresholds a run either meets or does not. THE GATE IS REVERSIBLE-AND-VERIFIED, NOT EMPTY-PLAN. Record the pre-update commit; apply; run the project's own gate; on green retain and report what moved; on any red or interruption restore and report. The tree after an unattended update is either verified-green or byte-identical to before - no third outcome. This is a stronger guarantee than the one asked for and it is one I can actually make, because migrate already refuses a dirty tree and requires git, so the pre-state is ALWAYS a commit. FIRST INCREMENT, BUILT HERE: srMigrationIsReversible. D0252 promised a rollback and none existed - the only recovery was an error message advising `git checkout -- .`. Two failure classes, and only one is addressable in-process: a DETECTED failure restores its own writes; an INTERRUPTION runs no code at all, so a marker holding the pre-migration sha is written before the first byte and the NEXT run detects and restores. The unverified-re-plan path now rolls back too - 'migrated but NOT verified, inspect git diff' was precisely the state reversibility exists to refuse.";
        :>> rationale = "WHY THE MARKER, AND WHY IT IS MACHINE-LOCAL. A killed process cannot roll itself back; nothing else can recover it either unless something durable records that a run started. `.keel/migrate-in-progress` describes an interrupted RUN, not a fact about the model, so it belongs in machine-local state and not in the tracked tree. WHY RECOVERY RUNS BEFORE THE PRECONDITIONS. Found by the test, not by inspection: an interrupted migration leaves the tree DIRTY, and the dirty-tree precondition would refuse - so a genuine interruption could never be recovered by the command that recovers it. The ordering is the fix and the test is what exposed it. WHY FAULT INJECTION AND NOT A UNIT TEST. A rollback never observed to run is a claim (D0253). One case makes a planned target read-only so a write genuinely fails mid-apply with other files already written, and it PANICS if the platform allowed the write anyway rather than passing on a fault that was never injected.";
        :>> consequences = "Two Needs, seven UseCases and five SystemRequirements authored; four tasks planned in dependency order with `#Verify` edges to the contracts they discharge. Migration is reversible: 3/3 fault-injected cases, clippy clean, federation 11/11 unaffected. After a failed or interrupted migration `git status --porcelain` over .engine and .tracking is EMPTY. NEEDS ARE UNACCEPTED. Per D0157 the human is asked what is WIDER than they meant, never whether the set is good - so these are proposed and the acceptance gate is theirs. The three tasks after this one (auto-update, drift report, scheduled currency) do not depend on that acceptance to be built, but the Needs they satisfy remain unconfirmed until asked.";
    }

    // acceptance event (D0121 review-queue sign-off; D0066/D0106 — human-judged, not fabricated)
    verification d0267Accept : Test { :>> id = "f83e2331-bbc2-4197-a23d-97b9570d2779"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0267AcceptR1 : TestResult { :>> id = "13f210c6-96b3-48c0-88cf-d9163602924d"; :>> outcome = VerdictKind::pass; :>> judgedAgainst = "bf999fd"; :>> judgedAt = "2026-08-31"; :>> judgedBy = "wweatherholtz"; }
}
