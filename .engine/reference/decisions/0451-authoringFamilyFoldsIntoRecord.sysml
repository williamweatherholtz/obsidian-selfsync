// D0451 (status: the `status` field below is the truth) — authoringFamilyFoldsIntoRecord: the nine authoring verbs become sub-verbs of keel record, named for the fact each writes; the top-level names are removed in the same commit as their call sites
// Recorded via `keel record decision` (D0105 RMWX axis; issue054). Acceptance is a separate explicit
// human gate (method=confirmation, D0106): flip status + add the d0451Accept event on sign-off.
package ReferenceDecision0451 {
    private import EngineElement::*;
    private import EngineWork::*;
    private import EngineVerification::*;
    private import EngineRelationships::*;

    // RESEARCH: Measured 2026-09-11 against .engine/cli/commands.sysml and keel-cli/src/main.rs at 1419069 (re-runnable census over the CliCommand facts and a grep for keel followed by a family verb). The authoring family holds ten facts: record (writes; already a router over decision, issue, statement, story) and the nine this Decision folds - add-task, new, append-result, append-gate-result, apply-review, record-measurement, snapshot-indicators, reverify (all writes) and mint (tooling: it prints UUIDs and writes nothing). Call sites of the nine outside target/: engine-authored surface 41, .claude generated 10, root docs 7, Rust source 14, Rust tests 8, .engine/decisions 18 and .tracking 87 (the last two not rewritten). reverify is the most cited at 27 files; new is used in one shape only, new sprint. The write API's receipts (D0232, D0424) and the D0301 no-result rule for --fill are behaviour of the functions, which this fold does not touch.
    // #ProspectiveChange (D0070) - this Decision governs a process/schema change; the co-committed
    // change rides the process-change guard's hard lock.
    #ProspectiveChange part d0451 : Decision {
        :>> id = "78070a58-972f-4202-9d68-67713c1bcbbd";
        :>> title = "authoringFamilyFoldsIntoRecord: the nine authoring verbs become sub-verbs of keel record, named for the fact each writes; the top-level names are removed in the same commit as their call sites";
        :>> createdAt = "2026-09-11";
        :>> createdBy = "claudeOpus5";
        :>> status = DecisionStatus::accepted;
        :>> context = "d0399 option A, the human's own word on 2026-09-11, folds five CLI families into their routers in the sprint 512 shape (D0273): a D0067 transform, a byte-equality baseline captured from the pre-fold binary, call-site rewrites in the SAME commit, no alias window. keel record already routes four writers by the fact they record; the other nine authoring verbs each write one kind of fact too and differ only in having kept a top-level name. This Decision fixes the mapping so the transform has a stated target and every write to the tree reads as keel record <fact>.";
        :>> decision = "The nine authoring verbs fold into keel record, each named for the fact it writes and each keeping its flags unchanged: keel add-task becomes keel record task; keel new sprint <N> <slug> becomes keel record sprint <N> <slug>; keel append-result becomes keel record result; keel append-gate-result becomes keel record gate-result; keel apply-review becomes keel record review; keel record-measurement becomes keel record measurement; keel snapshot-indicators becomes keel record indicator-snapshot; keel reverify becomes keel record reverify; keel mint [N] becomes keel record mint [N]. The nine top-level names are REMOVED from the dispatch, from COMMAND_NAMES, from the CliCommand facts and from cli_facts.rs, and the record fact's invocation names all thirteen sub-verbs. Each arm is MOVED verbatim into cmd_record, its function untouched, and the criterion is byte equality of the written file and of the printed receipt against a fixture tree exercised by the pre-fold binary, since a writer's output is the file it changes. Every call site under .engine (skills, processes, docs, contracts, views, tools), .claude, the root docs, the Rust source and tests is rewritten by the committed transform or by hand in the one commit that removes the names; .engine/decisions and .tracking are not rewritten. NOT A FORK: d0399 option A chose the course; this Decision states the mapping that course lands on for one family.";
        :>> rationale = "Every write to the tree through one verb is what makes the write API legible as one thing: a reader who knows keel record decision already knows how to record a result or a task. The sub-verbs are named for the fact written rather than for the old verb because append-result and add-task named the operation where record names the record, and record is the verb the family already uses. mint keeps its word as a sub-verb because it mints the ids the other writers use and has no better name; it is the one sub-verb that writes nothing, stated so nobody reads keel record mint as a write. The names are removed rather than aliased under D0273's own rule. Byte equality on the written file is the criterion because a writer that produces a different file after the fold has changed a fact, not a spelling.";
        :>> consequences = "One sprint, three points: the transform under .engine/tools/migrations/ with a dry run that reconciles counts before --apply, the dispatch, cli_surface and cli_facts edits by hand, and the fixture comparison. keel show hardening helpCoverage.dispatched falls by nine and the sprint's implement gate reads the number back. CLAUDE.md section 4 and guards.md name the new spellings in the same commit; keel sync-claude regenerates .claude from the rewritten skills; the reverify.toml demo receipts (D0444) that name a folded verb are rewritten as call sites, and keel reverify --demos becomes keel record reverify --demos. Downstream projects holding skills that name these verbs must update engine and skills together, which the D0252 clause A handshake makes visible by name.";
    }

    // D0303 layering: the mapping for one family under the program d0399 option A chose
    #DependsOn dependency from d0451 to d0399;

    // acceptance event (D0121 review-queue sign-off; D0066/D0106 — human-judged, not fabricated)
    verification d0451Accept : Test { :>> id = "66dbe240-e30d-4047-bb6b-dfd145d2fb8a"; :>> method = VerificationMethod::confirmation; :>> procedureText = "PLAN-COVERED under d0399 step 'the authoring writers become keel record <what>': the human signed the plan itself and this enumerated step does not re-ask (D0375 option C / D0396). The plan's judge: wweatherholtz."; }
    part d0451AcceptR1 : TestResult { :>> id = "11a7b8ec-244f-4853-9bfb-5ffc7a76a236"; :>> outcome = VerdictKind::pass; :>> judgedAgainst = "1419069"; :>> judgedAt = "2026-09-11"; :>> judgedBy = "wweatherholtz"; :>> createdBy = "claudeOpus5"; }
}
