// D0182 (status: the `status` field below is the truth) — D-P5b: run records, post-run gates, the headless-ask mapping, and single-writer-per-tree during a run
// Recorded via `keel record decision` (D0105 RMWX axis; issue054). Acceptance is a separate explicit
// human gate (method=confirmation, D0106): flip status + add the d0182Accept event on sign-off.
package ReferenceDecision0182 {
    private import EngineElement::*;
    private import EngineWork::*;
    private import EngineVerification::*;
    private import EngineRelationships::*;

    part d0182 : Decision {
        :>> id = "0e0a7402-e12b-4123-a333-41148f87d7a9";
        :>> title = "D-P5b: run records, post-run gates, the headless-ask mapping, and single-writer-per-tree during a run";
        :>> createdAt = "2026-08-21";
        :>> createdBy = "claudeFable5";
        :>> status = DecisionStatus::accepted;
        :>> context = "The agent bridge records nothing today - no run ledger, no post-run verification, no transcript persistence; a launched run's only trace is an SSE stream and a log line. The panel's failure-modes critic showed the naive fixes are each wrong: index-based gating is vacuous for uncommitted runs, fork-point diffs smear prior residue, tracked per-run files in shared files merge-conflict, and ownership evaluated at merge time launders the run's writes into the merging human's identity. Reviewed by a 9-member adversarial panel (2 pessimists, 2 optimists, 3 correctness critics, 1 reduction advocate, 1 systems engineer) across three rounds under an honesty rule; round 3 verdict 9 ACCEPT / 0 OBJECT, uncompelled. Full evidence and finding-to-resolution map: docs/proposals/2026-08-21-production-readiness-design.md sections 10-12. NOTE per the 2026-08-14 panel precedent (.tracking/panel-critiques.sysml): the panelists are subagent contexts of the authoring model, a rigor framing, NOT independent critics - this record claims convergence, never critic-independence.";
        :>> decision = "Committed mode is in-place execution: launch REFUSES on a dirty tree and snapshots the tree fingerprint at spawn; launcher concurrency pins to 1 with single-writer-per-tree during a run (consequence stated: consecutive launches serialize behind human review/commit of the prior run - the console grows a commit action for pending human-attested writes so accept-then-launch does not detour through the freeform path). Per run: a machine-local log (.keel/runs/<id>.jsonl - transcript path, duration, turn count, exit status; schema-declared machine-local, exempt from existence checks) plus ONE tracked summary fact per non-empty-diff run, one file per run, written by the launcher AFTER the post-run gate UNDER THE RUN'S STAMPED ACTOR, carrying the run-start fingerprint and judgedAgainst. The post-run gate is form-only: validate + guards + rules over the run-start-snapshot-to-working-tree diff, ownership evaluated against the run's actor, non-run-session writes flagged never folded in, red means run recorded failed - and the diff routes to human review UNCONDITIONALLY, green or red (hollow-pass history: D0050, issue092, issue099). The gate reads the fire-ledger for the run's session as evidence against ACCIDENTAL enforcement loss (not tamper-proofing), conditional on the transcript containing matched tool calls. Headless ask maps to a console proxy when up (ask-pending ledger entry written BEFORE blocking, wait bounded at hook-deadline-minus-margin, expiry means deny plus obligation - the harness timeout never decides), else auto-deny plus recorded obligation; per-process pre-approved write scopes are control-plane data - widening one is a governed change, never a quiet config edit. Minimal completion check: the run recorded its outputs through the write API, bounded re-prompt on failure; full artifact contracts wait for typed producedArtifact (P3b trigger). Spawn hardening: absolute KEEL_BIN injection, explicit permission mode, per-run wall-clock timeout with timed-out status, duration/turns recorded (quota burn visible, D0094). Worktree-per-run is the target state for concurrency above 1, DEFERRED behind a named DoR: KEEL_BIN proven, per-worktree actor stamping, snapshot gating, a run-branch policy Decision, Windows worktree smoke test.";
        :>> rationale = "A launched run that cannot be verified at exit is a freeform agent with a nicer start page; a gate that cannot attribute the diff is worse than none because it launders foreign writes into green run records. Every constraint here traces to a concrete panel-derived failure scenario, and the recorded-status completion wording and the worktree deferral are a matched pair - re-strengthening one requires delivering the other.";
        :>> consequences = "Runs become verifiable, attributable, quota-visible facts with unconditional human review. Charters p5RunRecords, p5PostRunGate, p5CompletionCheck, p5SpawnHardening.";
    }

    // acceptance event (D0121 review-queue sign-off; D0066/D0106 — human-judged, not fabricated)
    verification d0182Accept : Test { :>> id = "898181fa-b43d-49b4-b81d-493cb6982341"; :>> method = VerificationMethod::confirmation; :>> procedureText = "Their words, verbatim: 'accepted all'. Said in response to the presented queue of fifteen proposed Decisions - D0174, D0175, D0176, D0177, D0178, D0179, D0180, D0181, D0182, D0183, D0184, D0185, D0186, D0187, D0188 - so 'all' is that queue and this acceptance covers this Decision as one of the fifteen. The open fork stated in the proposal (section 8-A, strict default for provably empty directories) was named to them alongside the queue with the invitation to object on D0174; they accepted without objection, so D0174 is accepted AS WRITTEN including its stated strict-for-empty default."; }
    part d0182AcceptR1 : TestResult { :>> id = "62c6bc27-ab13-4bea-84e8-eb28dd2d8109"; :>> outcome = VerdictKind::pass; :>> judgedAgainst = "10b66bd"; :>> judgedAt = "2026-08-21"; :>> judgedBy = "wweatherholtz"; }
}
