// D0264 (status: the `status` field below is the truth) — An issue pull pipeline whose autonomy follows repository visibility: private acts, public plans, undetermined fails closed
// Recorded via `keel record decision` (D0105 RMWX axis; issue054). Acceptance is a separate explicit
// human gate (method=confirmation, D0106): flip status + add the d0264Accept event on sign-off.
package ReferenceDecision0264 {
    private import EngineElement::*;
    private import EngineWork::*;
    private import EngineVerification::*;
    private import EngineRelationships::*;

    // #SafetyChange (D0070) - this Decision governs a process/schema change; the co-committed
    // change rides the process-change guard's hard lock.
    #SafetyChange part d0264 : Decision {
        :>> id = "b6f63f45-f2f2-4182-aeb0-c3b03db12e9f";
        :>> title = "An issue pull pipeline whose autonomy follows repository visibility: private acts, public plans, undetermined fails closed";
        :>> createdAt = "2026-08-30";
        :>> createdBy = "claudeOpus5";
        :>> status = DecisionStatus::accepted;
        :>> context = "The human asked for an issues pull-and-ingest pipeline for projects generally, with autonomy split by repository: auto-act on private repos, plan-only on public ones with decisions proposed rather than implemented. They also asked whether it can be deployed globally and how other projects would pull the skill. WHY THE SPLIT IS THE RIGHT ONE, stated because it is the load-bearing part rather than a preference. An issue on a PUBLIC tracker can be filed by anyone with a browser. Text arriving from an unauthenticated stranger, fed to an autonomous agent that then changes the project, is prompt injection with a filing form - and the filing form makes it worse, because the channel is sanctioned and the words arrive looking like work. A PRIVATE repository's issues come from people who were granted access, so acting on them is acting on a colleague's request. WHAT THIS DESIGN DOES NOT CLAIM. Visibility is a PROXY for trust, not a measurement: a private repository with forty collaborators is not forty trusted people, and a public repository's maintainer filing on their own project is not a stranger. The proxy is used because it is the one signal that is always available, cheap, and not forgeable by the reporter.";
        :>> decision = "THE PULL. `keel github-pull --repo O/N --by ACTOR --at DATE [--limit N] [--trust T]` enumerates open issues and ingests each one no Statement already cites. Idempotency is the ingestion path's own - a re-ingest REFUSES on the URL - so a pull is safe to repeat and REPORTS what it skipped instead of silently doing nothing. Pull requests are skipped: a PR carries a diff, not a report, and ingesting one would record a patch as somebody's words. THE TIER, AND WHERE IT LIVES. `SourceTrust { trusted; untrusted; }` joins the schema and `sourceTrust` joins Statement as `[0..1]`. It is RECORDED ON THE UTTERANCE, not decided at act time, for two reasons: a repository's visibility can change after an issue is filed, so re-deriving it later answers a different question than the one that mattered; and without it a stranger's words are indistinguishable from a maintainer's, which is precisely the distinction an autonomous pass must never have to guess. Derived from `gh api repos/O/N --jq .private`, overridable by `--trust`, and UNDETERMINED RESOLVES TO UNTRUSTED - the failure modes are not symmetric, since a wrongly-trusted stranger gets autonomous action while a wrongly-distrusted maintainer gets asked. THE BOUNDARY, ENFORCED. Guard 56 `untrusted-routing`: a UserStory descending from an untrusted Statement, ALREADY ROUTED via `#Implicates`, must have a Decision among its targets. Untrusted input may plan; a human accepts before anything is built. Armed by five probes - the refuse case, the routed-through-a-decision allow case, a decision-alongside-work case, an unrouted case that must NOT fire, and a trusted-source case that must not fire either. THE PROCESS carries it: githubIntake gains `giPull` and `giBoundary`, and the skill states the tier table and the reason.";
        :>> rationale = "WHY THE GUARD CHECKS ROUTING AND NOT JUDGMENT. It fires only on a story already routed to work with no Decision among its targets. An untriaged story is never a violation - a guard that fired the moment an issue was ingested would make ingestion itself feel like a fault, which is how a control gets bypassed rather than obeyed. What the guard cannot check is whether the plan is any good; that is what the human's acceptance is for, and pretending otherwise would be the over-claiming this project has convicted itself of before. WHY NOT REFINE TRUST BY AUTHOR. `author_association` (OWNER, MEMBER, COLLABORATOR, NONE) is a strictly better signal than repository visibility, and it would let a public project's maintainer act on their own issues. It is NOT adopted here because it WIDENS a security boundary the human drew explicitly, and widening a stated boundary uninvited is the wrong direction to be inventive in. It is named here as the obvious next increment, to be taken deliberately or not at all. WHY THIS IS A SAFETY CHANGE. It adds a guard and it defines an autonomy boundary. Both are enforcement surface.";
        :>> consequences = "56 guards. `keel github-pull` ships in the binary; the process and skill travel as the `github-intake` library unit, so any project gets the capability with an engine version plus `keel process import --from-library github-intake`. DEPLOYED GLOBALLY IN THE ONLY SENSE THAT IS SAFE: available in every project, run BY each project against its own repository. There is deliberately no central daemon polling many repositories - one process holding credentials for a fleet is a single point of compromise, and the blast radius of a bad ingest would be every project at once instead of one. DEMONSTRATED LIVE, not fixtured: a pull against this repository read it as PUBLIC, printed the plan-only verdict, ingested four open issues at `untrusted`, and skipped the one already recorded. RESIDUAL, named: this repository is public, so its own issues are untrusted by this policy - including the human's. `--trust trusted` is the deliberate override, and the author-association refinement above is the principled fix if the friction proves real.";
    }

    // acceptance event (D0121 review-queue sign-off; D0066/D0106 — human-judged, not fabricated)
    verification d0264Accept : Test { :>> id = "8fa4bc9b-09aa-4ee4-aaba-8dbee396f45c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0264AcceptR1 : TestResult { :>> id = "84a384b6-d919-47eb-8ed6-dcc908dd7026"; :>> outcome = VerdictKind::pass; :>> judgedAgainst = "3381eef"; :>> judgedAt = "2026-08-30"; :>> judgedBy = "wweatherholtz"; }
}
