// D0160 — ACCEPTED AS A DEFERRAL (wweatherholtz, 2026-08-18): rung 1 stands as the only console control;
// rungs 2 and 3 wait for a solution that does not put a Node toolchain on the local gate. The human asked
// whether Playwright would have caught issue141 — it would, and my claim that nothing could was false.
// #ProspectiveChange (D0070): records a verification-lane decision; changes no schema and no process.
package ReferenceDecision0160 {
    private import EngineElement::*;
    private import EngineWork::*;
    private import EngineVerification::*;
    private import EngineRelationships::*;

    #ProspectiveChange part d0160 : Decision {
        :>> id = "7c41e9b5-2d38-4a06-b19f-58e0a3c7f412";
        :>> title = "D0160: how the console gets tested — a text guard now; the DOM and browser rungs deferred for want of a Node-free option";
        :>> createdAt = "2026-08-17";
        :>> createdBy = "claudeOpus5";
        :>> status = DecisionStatus::accepted;
        :>> context = "I CLAIMED SOMETHING FALSE AND THE HUMAN CAUGHT IT. Closing issue141 I recorded that 'no automated check in this engine can read a browser, so there is no gate that would have caught a DOM index bug and none that would catch the next one'. They asked: playwright wouldnt fix? It would. The claim conflated an ABSENCE (this repository has no browser test, no package.json, no node_modules, and not one test that reads the console asset) with an IMPOSSIBILITY, which is the exact error I corrected three times during the critique backfill — asserting a gap after looking in one place. MEASURED STATE: the console is roughly 470 lines of JavaScript embedded by include_str, reachable by 12 serve tests none of which touch it, and its two defects this week were both found by the human using it — the pipe that killed the server, and the off-by-four card binding.";
        :>> decision = "ACCEPTED AS A DEFERRAL, after evaluating the condition the human attached ('defer for now if there is not a good solution out there'). RUNG 1 STANDS, built and in the enforced test set: a Rust test over the include_str-embedded CONSOLE_HTML asserting the console binds card targets by data-attribute identity and contains no positional group-selection of every card. It costs no toolchain, it catches the anti-pattern that produced issue141, and it is proven in the failing direction. RUNG 2 (a DOM-level test under jsdom or linkedom) and RUNG 3 (Playwright, a real browser) are DEFERRED — not rejected. THE CONDITION WAS EVALUATED AND FAILED: there is no off-the-shelf option that is both DOM-capable and Node-free. jsdom and Playwright both require a Node toolchain; the only Rust-native route is a JS engine such as boa_engine plus a hand-written DOM shim, which is a project rather than a dependency, for one 470-line console. Against a current dependency footprint of eleven lean crates and no JS engine, neither price is worth paying today. THE TRIGGER for revisiting: a third console defect that a DOM-level test would have caught, or a Node-free DOM option becoming available. If either arrives, rung 2 is the rung — and it runs in CI, opt-in locally, never on `keel gate --fast`.";
        :>> rationale = "WHY DEFER RATHER THAN REJECT: the need is real and demonstrated — two console defects in two days, both found by a human — so recording a rejection would assert that browser-level testing is unwanted, which is false. A deferral with a named trigger says what is true: it is wanted, and the available prices are wrong. WHY THE PRICE IS WRONG: D0118 chose a buildless SPA with vendored dependencies and no CDN; D0048 requires validation-path tools to be kernel-free where possible; and D0112 demoted the JVM kernel to opt-in after issue081 showed that an all-or-nothing heavy oracle gets bypassed wholesale rather than selectively. A browser download on the commit path invites exactly that bypass, and `keel init` must not require Node for a downstream project to run its gate. WHY RUNG 1 WAS BUILT WITHOUT ASKING: it needed no decision — a unit test over an embedded string, which would have caught the actual defect. Declining to build it while a toolchain question sat open would have left the cheap control unbuilt for the length of a conversation. WHAT RUNG 1 CANNOT DO, stated in the test's own doc comment: it is a TEXT assertion, so it catches a named anti-pattern and not a wrong destination that is bound correctly.";
        :>> consequences = "CONSOLE BEHAVIOUR IS VERIFIED BY THE HUMAN USING IT, and that is now stated in the console's own requirements rather than left implicit — which is the obligation this Decision's own text created for the deferral branch. Concretely: the console has one structural test and no behavioural coverage, so a wrong destination, a dead control or a broken render reaches the human before it reaches a gate, and the two defects this week are the evidence. That is an ACCEPTED RISK with a named trigger, not an oversight. The correction to my false claim stands recorded in issue141 and in sprint 339's review gate, with what I asserted, why it was wrong, and who caught it.";
    }

    // acceptance event (D0121 review-queue sign-off; D0066/D0106 — human-judged, not fabricated)
    verification d0160Accept : Test { :>> id = "f2c8b41d-70e6-4a93-85b1-9de03a7c26f4"; :>> method = VerificationMethod::confirmation; :>> procedureText = "wweatherholtz, 2026-08-18, verbatim: 'let s defer for now if there is not a good solution out there.' THE CONDITION THEY ATTACHED WAS EVALUATED BY ME, and the evaluation is recorded so they can disagree with it rather than only with the outcome: the repository carries eleven dependencies and no JS engine or HTML parser; jsdom and Playwright are both DOM-capable and both require a Node toolchain; the only Node-free route is boa_engine plus a hand-written DOM shim, which is bespoke work of significant size for one 470-line console. No option is both DOM-capable and Node-free, so the condition failed and the deferral applies. This attests the DEFERRAL and its trigger. It does NOT attest that browser testing is unwanted — the Decision records the opposite — and it does not attest rung 1, which needed no acceptance and was built before this exchange."; }
    part d0160AcceptR1 : TestResult { :>> id = "3a6e05c9-8b72-4d14-9f68-c051e7b2a43d"; :>> outcome = VerdictKind::pass; :>> judgedAgainst = "PENDING"; :>> judgedAt = "2026-08-18"; :>> judgedBy = "wweatherholtz"; }
}
