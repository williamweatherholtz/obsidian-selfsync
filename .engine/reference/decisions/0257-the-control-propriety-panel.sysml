// D0257 (status: the `status` field below is the truth) — The control-propriety panel: five adversarial lenses, a named defeater per verdict, and its first round convicted two of its author's own controls
// Recorded via `keel record decision` (D0105 RMWX axis; issue054). Acceptance is a separate explicit
// human gate (method=confirmation, D0106): flip status + add the d0257Accept event on sign-off.
package ReferenceDecision0257 {
    private import EngineElement::*;
    private import EngineWork::*;
    private import EngineVerification::*;
    private import EngineRelationships::*;

    // #ProspectiveChange (D0070) - this Decision governs a process/schema change; the co-committed
    // change rides the process-change guard's hard lock.
    #ProspectiveChange part d0257 : Decision {
        :>> id = "e6e9a928-9599-4acc-a01e-59673acba352";
        :>> title = "The control-propriety panel: five adversarial lenses, a named defeater per verdict, and its first round convicted two of its author's own controls";
        :>> createdAt = "2026-08-29";
        :>> createdBy = "claudeOpus5";
        :>> status = DecisionStatus::accepted;
        :>> context = "The human directed (st032, verbatim): for each existing and proposed solution, hold a panel to assess solution propriety - is it overfit; does it prevent the class or just this example; is it robust to future change or inappropriately dependent; can it be circumvented; can it be objectively measured - research best practices for this kind of critique panel, define a process, then critique, defining the work well first. The research pass grounded each question in an existing practice: OVERFIT is mutation testing's question - a control must kill VARIANTS of the defect, not the specimen that motivated it; CLASSCOVERAGE is variant analysis; CHANGEROBUSTNESS is the change-detector-test antipattern; CIRCUMVENTABILITY is control validation as practiced by breach-and-attack simulation - attack the control, never inventory it; MEASURABILITY is the D0232 receipt-versus-testimony split. The panel's epistemics are eliminative induction from the assurance-case literature (Goodenough/Weinstock/Klein): confidence comes from defeaters SOUGHT AND ELIMINATED, never from affirmation, so every verdict carries a named defeater - sound names what was tried, conditional names what stands, unsound names the demonstration.";
        :>> decision = "Five clauses. CLAUSE A - THE PROCESS. controlPropriety (.engine/processes/control-propriety.sysml) with five steps: inventory in tranches sized to be done well; assess adversarially per lens; record one atomic ProprietyFinding per target x lens with its defeater; route every unsound to an Issue and every accepted conditional to a disposition; state the panel's independence honestly. Deployed by the control-propriety skill. CLAUSE B - THE VOCABULARY IS A NEW NON-CORE SCHEMA PACKAGE. EnginePropriety (.engine/schema/propriety/) declares ProprietyLens (the human's five questions, verbatim), ProprietyVerdict (sound/conditional/unsound, eliminatively defined), and ProprietyFinding (target, lens, verdict, rationale, defeater). NOT new CritiqueLens members: schema/core is frozen (invariant 5), and the five questions do not map onto the requirement-quality canon without force-fitting - the intake rule generalises, a kind the vocabulary cannot express is a change to the vocabulary, never a forced fit. The schema/safety precedent shows a non-core package carries new vocabulary without touching the frozen surface. CLAUSE C - FINDINGS ARE COMPUTED INTO VIEW. keel view propriety (a declared TOML view over ProprietyFinding) - no new Rust view code; coverage (which targets carry all five lenses) is computable from the findings. CLAUSE D - ROUND 1 RAN, AND ITS TWO UNSOUND VERDICTS ARE FIXED UNDER THIS DECISION. Forty findings over the session's eight solutions (.tracking/propriety.sysml). pf02: guard 53 killed the absolute-path specimen and its shape variants but PASSED a traversal key (../../elsewhere escapes the project identically) - issue307, fixed by adding the segment test to the same predicate. pf33: provenBy was a receipt-shaped testimony - nothing verified the named test file exists, in the very contract that separates receipts from testimonies - issue308, fixed by guard 54 resolving every provenBy path against the tree. Both fixes proven armed by injection: 84/1 and 23/1 FAIL on planted defects, PASS restored. This clause is the keystone-lock charter for the guards.rs edits. CLAUSE E - INDEPENDENCE IS STATED, NOT CLAIMED AWAY. Every round-1 target was authored by the assessor, so every sound verdict in round 1 is a TESTIMONY (D0080/D0232). The round's own evidence is that eliminative self-audit still convicts - two unsound verdicts against the assessor's own week-old work - but sound verdicts on Critical controls should be re-judged by a non-author critic when one exists.";
        :>> rationale = "WHY A PROCESS RATHER THAN A ONE-TIME SWEEP: D0040 - the panel recurs on every new control, and a recurring task without a process leaks its method into conversation history where it cannot be enforced or improved. WHY TRANCHES: a sweep that covers everything shallowly certifies nothing, and the session's repeated lesson is that the honest number is the one that got worse. WHY THE DEFEATER IS MANDATORY: a verdict without one is unfalsifiable praise or blame; the defeater is the actionable artifact, and eliminative induction is the only epistemics under which a self-audit's sound verdict means anything at all. WHY ROUND 1 TARGETED THE SESSION'S OWN SOLUTIONS FIRST: newest controls have had the least scrutiny, the author's bias is at its maximum, and if the method could not convict its own author's fresh work it would be decoration - it convicted twice. COST OF NOT DECIDING: controls keep being assessed by the informal standards of whoever ships them, and the arming contract keeps accumulating claims (provenBy) that nothing checks.";
        :>> consequences = "The panel exists as a process, a skill, a schema package, a view, and forty findings. Two High issues found and fixed same-day; guard 53's predicate now covers traversal; guard 54 scans 22 (16 event bindings + 6 proof pointers). Standing conditionals worth reading (the view lists all): guard 54 reconciles only the EVENT-EMITTING subclass of implemented-but-undeclared (pf07, disposition candidate); its control harvest is naming-convention-dependent (pf08); the write-lock probe proves the lock, not that every write path takes it (pf12); the pre-write probe covers strict, and this project runs guided (pf22); --no-verify bypasses the hook class by git's design, backstopped remotely (pf24). Tranches 2 (the fifteen mapped controls) and 3 (the proposed solutions D0250-D0252) are inventoried and not yet run - defined work, not silent scope.";
    }

    // acceptance event (D0121 review-queue sign-off; D0066/D0106 — human-judged, not fabricated)
    verification d0257Accept : Test { :>> id = "b04faeaf-59a5-42d5-b2e0-c140d09c2de8"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0257AcceptR1 : TestResult { :>> id = "29d3f9c0-fa58-40ad-8cdd-4cdd6bd95623"; :>> outcome = VerdictKind::pass; :>> judgedAgainst = "5fcaad7"; :>> judgedAt = "2026-08-29"; :>> judgedBy = "wweatherholtz"; }
}
