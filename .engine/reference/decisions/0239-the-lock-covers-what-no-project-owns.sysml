// D0239 (status: the `status` field below is the truth) — the keystone lock covers the surface no project owns, and adherence sees every project
// Recorded via `keel record decision` (D0105 RMWX axis; issue054). Acceptance is a separate explicit
// human gate (method=confirmation, D0106): flip status + add the d0239Accept event on sign-off.
package ReferenceDecision0239 {
    private import EngineElement::*;
    private import EngineWork::*;
    private import EngineVerification::*;
    private import EngineRelationships::*;

    // #SafetyChange (D0070) - this Decision governs a process/schema change; the co-committed
    // change rides the process-change guard's hard lock.
    #SafetyChange part d0239 : Decision {
        :>> id = "3ac3b6b7-8264-4a64-8107-102db5c1408c";
        :>> title = "the keystone lock covers the surface no project owns, and adherence sees every project";
        :>> createdAt = "2026-08-27";
        :>> createdBy = "claudeOpus5";
        :>> status = DecisionStatus::accepted;
        :>> context = "D0238 made the workspace gate RUN across every project. The remaining question was whether it could be WEAKENED without a signature, and the panel's other two Criticals are both that question. issue276: in a workspace the repo-root enforcement surface belongs to no project — the ONE .githooks/pre-commit that gates every project, and .github/workflows/ — and the keystone lock matches project-relative paths, so the lock could never fire on it. Verified: that single hook replaced with a two-line `exit 0`, staged alone with no Decision, and `gate --workspace` reported 2 projects gated clean, exit 0 — after PRINTING a line that NAMED the unowned file. Also verified: staging the deletion of an entire project, 447 paths including every process definition and its guards, passed silently. issue277: issue272 relaxed the keystone lock to exempt ADDED locked files, and D0234 justified the residual by naming audit-adherence's guard-state monotonicity as the compensating control. That check derived its signature from repo-root-relative pathspecs, which match nothing when projects live one directory down. Verified with an identical unsigned rule weakening: single-project FAIL exit 1; two-project workspace PASS exit 0. So a control was weakened while citing another that did not work in the arrangement the same Decision introduced.";
        :>> decision = "1. The workspace gate applies the KEYSTONE LOCK to what no project gate covers, and exits non-zero. Two rules: an unowned staged path that `guards::is_locked_path` claims, and any staged DELETION of a path under an `.engine/` directory at any depth. The second is not a special case of the first — deleting a project makes its directory stop satisfying `is_project`, so its paths become unowned at exactly the moment they are removed. 2. `audit-adherence` iterates the discovered project set, prefixing each pathspec with the project label and qualifying each signature key with it, so monotonicity is PER PROJECT. A project at the repository root keeps an empty prefix and unqualified keys, so a single-project repository's signature is unchanged. 3. `audit-adherence` ANCHORS to the repository root before reading anything path-scoped. 4. A marked Decision recorded in ANY project in the repository authorises the repository's own locked surface, in both the gate and the audit.";
        :>> rationale = "ALTERNATIVES for issue276: (A) make one project own the root surface — rejected: ownership would be arbitrary, and deleting that project takes the lock with it. (B) require a project at the repository root — rejected: it contradicts the layout D0238 settled on, where a workspace is peers with nothing at the root. (C) check unowned paths at the workspace level — CHOSEN. CRITERIA: does the lock still hold when a project is deleted; is ownership derivable rather than declared; and does it change single-project behaviour. Clause 4 is the clause I nearly got wrong, and it was caught by running the DoD's third verification rather than only its first two. Requiring the root-relative `.engine/decisions/` form made the block work perfectly and made the shared root hook PERMANENTLY UNCHANGEABLE: with no project at the repository root there is no `.engine/decisions/` there, so no Decision could ever authorise a change to the surface. That is a different failure from the one being fixed and just as wrong — a control with no legitimate path to change is not a control, it is a dead end. The human signing a Decision is the same human whichever project it is filed in. Clause 3 is the same class of error as issue277 itself, one layer down. `ls-tree` pathspecs and `show --name-only` resolve relative to the directory git was invoked in, not the repository root, so the project prefix was applied ON TOP of git's own implicit prefix (`alpha/alpha/.engine/rules/`), matched nothing, and the audit reported PASS on a tree carrying eight unsigned rule downgrades. Measured: FAIL from the repository root, PASS from one directory down, same commit. The DoD asked for 'FAILS in a workspace at every depth' and only the every-depth clause caught it.";
        :>> consequences = "Verified end to end against real git repositories, all five cases: - the unsigned exit-0 hook replacement is BLOCKED (exit 1), where it previously passed at exit 0; - staging the deletion of an entire project is BLOCKED (447 deletions, 402 keystone events); - a legitimately signed change to the same surface PASSES (exit 0); - the unsigned rule weakening FAILS from the repository root, from inside the project, and from a directory deeper still — three depths, exit 1 at each, where one directory down previously passed; - a signed weakening PASSES, so the audit does not simply refuse everything. Single-project behaviour is unchanged, measured rather than asserted: this repository's own `audit-adherence` still reports PASS with no project-qualified keys in its output, `project_prefixes` returns exactly `['']` here, and the full test suite passes across 11 suites. The issue272 added-file exemption's stated compensation now exists in the arrangement it was claimed for. The DoD offered a fallback — gate the exemption on a single-project repo until the real fix lands — and it is deliberately NOT taken, because the real fix landed. Still open from the same panel: issue279-284, none of them Critical. The two remaining that touch enforcement are dcLandGatesBeforeThePush, where `land` pushes before it gates so nothing is gated on the success path, and dcOneGateDefinition, where three bodies of the gate carry three different bars and the push gate is the weakest. Both are about the gate's SHAPE rather than whether it can be disarmed unsigned, which is what this Decision closes.";
    }

    // acceptance event (D0121 review-queue sign-off; D0066/D0106 — human-judged, not fabricated)
    verification d0239Accept : Test { :>> id = "bbc4625b-107f-47ae-aa29-da7633a16d0b"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0239AcceptR1 : TestResult { :>> id = "0ba0c52b-b13c-4f1f-ad4b-e450ff0e0af0"; :>> outcome = VerdictKind::pass; :>> judgedAgainst = "3576bba"; :>> judgedAt = "2026-08-27"; :>> judgedBy = "wweatherholtz"; }
}
