// D0131 — A sprint retro's avoidable issues become TRACKED, PRIORITIZED
// items, or the retro states why none is needed. A lesson that terminates in prose is not retained.
// Marked #ProspectiveChange (D0070): sprints closed under the prior retro step stay valid.
package ReferenceDecision0131 {
    private import EngineElement::*;
    private import EngineWork::*;
    private import EngineVerification::*;
    private import EngineRelationships::*;

    #ProspectiveChange part d0131 : Decision {
        :>> id = "5c0e9a41-7b3d-4e26-9f18-2a7c60d5b834";
        :>> title = "D0131: a retro's avoidable issues become tracked, prioritized items — or the retro records why not";
        :>> createdAt = "2026-08-13";
        :>> createdBy = "claudeOpus5";
        :>> status = DecisionStatus::accepted;
        :>> context = "issue085, raised by the human on 2026-08-13: 'the sprint retro should identify any potential recurring or serious issues and put it properly prioritized backlog items to resolve them.' The trigger was real: sprint 247's retro named THREE avoidable issues and only one had a control — the other two (piping `git commit` into a pager, which hung the kernel JVM for five minutes; a bare `cat >` blocking on stdin) were written into CLAUDE.md prose and the AI's own memory. Outside the model they carry no severity, no priority, no resolver and no id; they are invisible to orient, whats-next, coverage and the burndown; and agent memory is per-agent and unreviewable, so for the distributed team of D0129 those lessons effectively do not exist. That is precisely the prose-shadow-truth D0018 exists to prevent, committed INSIDE the ceremony meant to prevent recurrence. ROOT CAUSE, found on inspecting the process definition: the retrospective had exactly ONE step, `retroPromote`, whose actionText was 'Create a Decision; update Process/schema if needed' and whose owner was `Owner::human` — stale since D0049 made the retro AUTONOMOUS and AI-recorded. The obligation to TRACK a finding was never defined anywhere; it existed only as an expectation in the sprint-retro skill's description. So a retro that merely DESCRIBED a lesson passed its gate identically to one that TRACKED it, and there was no artifact to check.";
        :>> decision = "Define the obligation in the process, and check it. (A) PROCESS: the retrospective becomes three ordered steps — `retroIdentify` (name what was AVOIDABLE, distinguishing avoidable from merely difficult, including findings against this thread's own earlier work), `retroTrack` (for EACH avoidable issue, either record a tracked Issue with severity PLUS its resolving backlog action placed at its correct PRIORITY — declaration order IS priority per D0052, so ranking it means putting it in the right place in the file rather than calling it important — or state explicitly why no item is needed), and `retroPromote` (where a finding changes future behavior, record a Decision through the Change Request path). All three are `Owner::ai`, correcting the stale `Owner::human` on the old single step: D0049 already made the retro autonomous. (B) FORBIDDEN, explicitly: writing a lesson into a doc, a commit message, or agent memory INSTEAD of tracking it. A lesson that terminates in prose has not been retained. (C) CHECK: a WARNING-level, git-diff-aware guard (`retro-backlog`, the D0113 doc-sync shape) flags a staged sprint record whose retro names a finding while the commit records no tracked Issue or backlog action and gives no reason. It is satisfied EITHER by co-recording an item OR by stating why none is needed, so what it enforces is that the choice is EXPLICIT — not that an item always exists. (D) Where the avoidable issue has a recurrable class, D0047 continues to require a permanent automated control on top of the tracked item.";
        :>> rationale = "The failure was not that the retro found nothing — it found the right things and then dropped them. So the fix is about the DESTINATION of a finding, not about looking harder. Making the obligation a defined process STEP matters more than the guard: a check with no process behind it is unowned (D0059), and the previous state is the proof — the expectation lived only in a skill description, so nothing could be pointed at when it was skipped. ALTERNATIVES: (i) require an Issue for EVERY finding — REJECTED, it would manufacture duplicates when a control already exists, and a guard that produces noise gets ignored, which is how doc-sync's own lesson (D0113) was learned; (ii) leave it to the sprint-retro skill's description — REJECTED, that is exactly the state that failed, and D0047 is explicit that manual vigilance is not a control; (iii) hard-block the commit — REJECTED, the check is a prose heuristic and a legitimate no-item case exists, so it follows the D0102 promote-once-low-noise pattern; (iv) CHOSEN — define the step, then check it at warning level, with an explicit escape that must be SAID rather than assumed. Accepting a heuristic here is deliberate: the alternative to an imperfect check is the status quo, which is no check at all.";
        :>> consequences = "Rewrites the retrospective in `.engine/processes/agile-workflow.sysml` from one human-owned step into three AI-owned steps (retroIdentify / retroTrack / retroPromote) and updates the sprint-retro skill so the deploying skill matches the process (D0059). Adds the `retro-backlog` guard (22 guards; 17 hard + 5 warning-only). Sprints closed under the prior single-step retro stay valid (#ProspectiveChange, D0070) — this is forward-only and does not retro-fail earlier records. The two sprint-247 lessons that escaped into prose are NOT retrospectively converted into Issues: they are already recorded in CLAUDE.md §6 as durable guidance and re-tracking them now would be theatre; issue085 remains the record that they escaped. Cost: one more warning-level guard on every commit and a slightly longer retro. Acceptance state is carried by `status` plus the d0131Accept event and is not restated here (decisionNoVerdictProseRule).";
    }

    // Acceptance event (D0066/D0106 — human-judged). Substantive per issue083/dcAttestationSubstance:
    // what was said, and the context that makes it an attestation to THIS Decision.
    verification d0131Accept : Test { :>> id = "687c475e-ce29-445e-a3ba-e97a70067010"; :>> title = "Human acceptance of d0131"; :>> createdAt = "2026-08-13"; :>> createdBy = "claudeOpus5"; :>> method = VerificationMethod::confirmation; :>> procedureText = "wweatherholtz attests acceptance of d0131 (a retro's avoidable issues become tracked, prioritized items — or the retro records why none is needed; the retrospective becomes retroIdentify/retroTrack/retroPromote, all Owner::ai, backed by the warning-level retro-backlog guard). Attested 2026-08-13 in session with the words 'accept on all counts', given in direct response to an enumerated list naming exactly three outstanding items: the frozen-schema sign-off, D0131 and D0132 acceptance, and the per-sitting review. Batched acceptance is sanctioned by D0019."; }
    part d0131AcceptR1 : TestResult { :>> id = "d991baa9-19aa-44ee-a45a-d3bf918aaa50"; :>> outcome = VerdictKind::pass; :>> judgedAgainst = "8df2822"; :>> judgedAt = "2026-08-13"; :>> judgedBy = "wweatherholtz"; }
    part d0131AcceptR2 : TestResult { :>> id = "bb3c9722-00ea-4704-a087-0f4d8603f484"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences acceptance-state sentence replaced at ee2512d - editorial, the agreed substance unchanged. Their standing words, verbatim: 'issues raised are automatically accepted. they can be customizedly changed post-fact.'"; }
}
