// D0265 (status: the `status` field below is the truth) — The governance traversal is batched: the antiquated-data question goes from never-answered to 46 seconds
// Recorded via `keel record decision` (D0105 RMWX axis; issue054). Acceptance is a separate explicit
// human gate (method=confirmation, D0106): flip status + add the d0265Accept event on sign-off.
package ReferenceDecision0265 {
    private import EngineElement::*;
    private import EngineWork::*;
    private import EngineVerification::*;
    private import EngineRelationships::*;

    // #ProspectiveChange (D0070) - this Decision governs a process/schema change; the co-committed
    // change rides the process-change guard's hard lock.
    #ProspectiveChange part d0265 : Decision {
        :>> id = "165b8c99-04fa-48e9-bac1-e0422530b1d9";
        :>> title = "The governance traversal is batched: the antiquated-data question goes from never-answered to 46 seconds";
        :>> createdAt = "2026-08-30";
        :>> createdBy = "claudeOpus5";
        :>> status = DecisionStatus::accepted;
        :>> context = "The human chose proposal #1 from the vintage panel and named the goal it serves: better DISTRIBUTION management - projects pushing and pulling processes easily, with pinned engine versions. That is the right frame for this work. When `keel process import --update` brings a project a NEWER process version, the question that immediately follows is which prior work the OLD version governed - and that is precisely what `reprocess-candidates` answers. MEASURED BEFORE, twice: it did not finish. 240 seconds, exit 124, zero bytes. Per item the resolver costs a pickaxe search over full history plus one `merge-base` for every process-change Decision; a single item was timed at ~15 seconds, so 501 stories is roughly two hours. The answer existed and was unobtainable, which is the D0261 shape - a metric only readable by someone who already suspects the answer is not a control.";
        :>> decision = "A batched index, built once per corpus run, replacing per-item git subprocesses with in-memory lookups: ANCESTRY. One `git rev-list --parents HEAD` builds the child map; for each MARKER commit (every process-def change, every Decision's effective commit) a forward reachability set is computed once. `is_ancestor(marker, item)` becomes a set lookup instead of a `merge-base` subprocess. INTRODUCTION. One `git log -p -U0 -- .tracking/delivery` pass tokenises ADDED lines and records the OLDEST commit in which each known name appears - faithful to the `git log -S` pickaxe it replaces, which finds the first commit where the string occurs. CHARTERS, DECISION COMMITS, DEF TOUCHES. The `#CharteredBy` edges are read from the WORKING TREE rather than by `git grep` per item; decision-introduction commits come from one `--diff-filter=A` log over `.engine/decisions`; and one `--name-only` log over processes and workflows gives both commit-to-defs and def-to-commits. NOTHING ABOUT THE DERIVATION CHANGES. The same facts are read from the same history, once instead of once per item.";
        :>> rationale = "WHY EQUALITY IS ASSERTED AND NOT ASSUMED. A fast lens that quietly answers differently is worse than a slow correct one, and far harder to notice - the speed-up is visible and the divergence is not. `governing_version_via_index` exists solely so the two paths can be compared, and the test compares them BYTE-FOR-BYTE on three real corpus items chosen across vintages, because a single item could agree by luck. WHY THE SLOW PATH STAYS. For ONE item the index is more expensive than the resolve it replaces - building it costs a full `git log -p` over delivery history. So `governing-version <item>` keeps the per-item path and the corpus lens uses the index. Two paths that must agree is a cost; the test is what makes it a controlled one. WHY NOT A CACHE ON DISK. It would be a second truth to invalidate, and the whole reason this design beats a stored vintage stamp (pf51/pf54) is that it derives from git and cannot drift. A cache would reintroduce exactly the drift the derivation avoids, to save 46 seconds on a command nobody runs in a loop.";
        :>> consequences = "`reprocess-candidates` completes in 46 seconds and returns 142KB of answers where it previously returned nothing. The question the human asked - what antiquated data is out there and under what process was it authored - is now askable on this corpus for the first time. Two paths exist and must agree; `batched_governance_agrees.rs` holds that, and also asserts the corpus lens is NON-VACUOUS, since an empty result on a corpus that HAS safety changes and items predating them would be a mis-aimed lens rather than a clean bill of health. NOT FIXED HERE and still open: issue317, the unconditional Delivery fallback that answers confidently for item types the resolver does not cover. Batching a resolver does not widen its coverage, and conflating the two would have let a performance change smuggle in a semantic one.";
    }

    // acceptance event (D0121 review-queue sign-off; D0066/D0106 — human-judged, not fabricated)
    verification d0265Accept : Test { :>> id = "4061ca16-670b-4110-8eff-538c7c741960"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0265AcceptR1 : TestResult { :>> id = "89db53d0-4f84-43c8-897a-e5c8e1428dc7"; :>> outcome = VerdictKind::pass; :>> judgedAgainst = "2ca2acb"; :>> judgedAt = "2026-08-30"; :>> judgedBy = "wweatherholtz"; }
    part d0265AcceptR2 : TestResult { :>> id = "72332946-6091-442d-a966-e2c539e33437"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences guard count renumbered 8 to 7 at 2ca2acb - editorial, the agreed substance unchanged. Their standing words, verbatim: 'issues raised are automatically accepted. they can be customizedly changed post-fact.'"; }
}
