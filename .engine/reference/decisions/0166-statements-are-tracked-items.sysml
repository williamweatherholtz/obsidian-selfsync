// D0166 — PROPOSED. What the human SAYS becomes a tracked item, and everything derived from it points
// back. Touches frozen schema/core (invariant 5), so it needs explicit sign-off and is NOT applied.
// #ProspectiveChange (D0070): adds one item type and one coverage view.
package ReferenceDecision0166 {
    private import EngineElement::*;
    private import EngineWork::*;
    private import EngineVerification::*;
    private import EngineRelationships::*;

    #ProspectiveChange part d0166 : Decision {
        :>> id = "8c15b7a0-4d62-4e39-9f74-2a80ce163bd5";
        :>> title = "D0166: a human statement is a tracked item, translated into a UserStory, and every downstream item cites the story it came from";
        :>> createdAt = "2026-08-20";
        :>> createdBy = "claudeOpus5";
        :>> status = DecisionStatus::accepted;
        :>> context = "THE HUMAN ASKED WHETHER PARSING THEIR STATEMENTS INTO USER STORIES AND TRACKING THEM IS ALREADY IN THE SCHEMA. PARTLY, AND THE MISSING HALF IS THE IMPORTANT ONE. What exists: a business layer with `Need` (a native requirement def carrying `source`, a solution-free `statement`, `marketJustification` and MoSCoW `priority`), `Persona` (description, goals) and `UseCase` (description, mainSuccess, extensions). What does NOT exist: any item holding what a human ACTUALLY SAID, with provenance. `Need.statement` is a REFINED, solution-free outcome authored by someone; it is not the utterance. And keel's `Story` is a delivery work item carrying estimatedPoints, actualPoints and actualHours - it has no narrative fields at all, so it is not a user story in the agile sense and the name collision is worth stating plainly. THIS SESSION IS THE EVIDENCE THAT THE GAP MATTERS. D0164 exists because a requirement was buried in an ACCEPTANCE NOTE ('viewpoints should be activateable/disableable just like processes'). issue137's record was corrected by a note in a review deck ('viewer on a single machine is still 1'). D0161 was redesigned three times by one-line questions. Every one of those arrived as a human statement, and every one was captured by ME copying it by hand into a procedureText - which means the model holds my transcription and the conversation holds the original. D0018 says that if resuming requires knowledge it belongs in the model, and the thing most often needed on resume is what they asked for.";
        :>> decision = "PROPOSED: one new item type and one computed view. THE TYPE, `Statement :> Element`, holds ONLY the utterance and its provenance - `text` (verbatim, never paraphrased), `saidBy` (an Actor), `saidAt`, and `channel` (where it was said: a console note, a deck note, a chat turn). IT CARRIES NO INTERPRETATION, which is the whole design: the reading of a statement is a SEPARATE authored item - a Need, a Story, an Issue, a Decision - linked back by a `#DerivedFrom` edge. THE INVARIANT THAT MAKES IT WORTH HAVING: a Statement is NEVER edited to agree with what was derived from it. If I misread them, the correction is a NEW derived item citing the same Statement, and the misreading stays visible as a superseded interpretation. That is D0108 ownership and §4 in one rule - their words are theirs, my reading is mine, and the two are separately auditable. THE VIEW, `keel statements`, reports two numbers that do not exist today: UNPARSED - statements with no derived item, meaning direction they gave that nothing acts on; and UNSOURCED - Needs, UserStories, SystemRequirements, Issues and Decisions with no `#DerivedFrom` reaching a Statement, meaning work I invented rather than work they asked for. THEIR SECOND PASS RETURNED THIS NEEDS WORK WITH ONE INSTRUCTION, verbatim: 'Every user story - let's use user story instead of story'. THEY WERE OBJECTING TO MY OWN TITLE, which read 'every Need or Story derived from one cites it' - the bare word 'Story' being exactly the collision the same Decision spends a paragraph warning about. A Decision that names the ambiguity and then commits it is not a small slip: `Story` is a live type used 356 times, so a reader meeting 'Story' in this text would reasonably think the delivery work item was meant. THE RULE, now binding on this Decision and anything implementing it: the concept is always USER STORY in prose and `UserStory` in the model, never the bare word 'story', and keel's existing `Story` is always written with its full name when it is what is meant. TWO READINGS OF 'Every user story' AND BOTH ARE HONOURED: the chain applies to EVERY user story rather than a selected subset - there is no tier of story that skips implication routing - while the narrower rule about which STATEMENTS get recorded (directive ones) stays as it was, because a statement and a user story are different links and only the second is universal. THEIR REFINEMENT, WHICH CHANGES THE SHAPE AND IS FOLDED IN HERE RATHER THAN PROPOSED SEPARATELY: 'I do like a parsed-but-verbatim user statement that gets faithfully translated into a user story and downstream items created. that could allow us much stronger processes - e.g. does a user story implicate a need? use case? requirement? bug?' So the chain is THREE links, not two. (1) `Statement` - verbatim, no interpretation. (2) A USER STORY - the faithful translation, which is where `asA`/`iWant`/`soThat` belongs and which is NOT keel's `Story`: that name is taken by a delivery work item carrying estimatedPoints/actualPoints/actualHours, used 356 times across the sprint records with 38 recording actual hours, and it holds no narrative at all. Their read of it is correct - it is agile sprint planning metadata. The new type is therefore `UserStory`, and the collision is stated so nobody later assumes the two are the same thing. (3) IMPLICATION ROUTING: for each UserStory, which downstream items does it implicate - a Need, a UseCase, a SystemRequirement, an Issue, a Decision, or nothing? That is the link that makes this a PROCESS rather than a filing cabinet, and it is the same question §3's route table already asks about a REQUEST; asking it about a recorded UserStory means the routing decision becomes a tracked fact instead of a paragraph I write at the top of a reply. THE PAYOFF IS A COMPUTED GAP: a UserStory implicating nothing is either genuinely inert or unrouted work, and a downstream item implicated by no user story is mine rather than theirs - the same `unsourced` number, now with a middle term that says WHY. WHAT THIS IS NOT: it is not a transcript. Only statements that carry DIRECTION get recorded - a request, a correction, a constraint, a priority - because a log of everything said is a second corpus with no questions attached, which is exactly the mistake draft 1 of D0161 made.";
        :>> rationale = "WHY THE UTTERANCE AND THE READING MUST BE SEPARATE ITEMS: this session records me over-reading a two-word phrase into a confirmation ('confirmed otherwise'), and separately reading three field reports about a DESTINATION as reports about a CLICK. In both cases the human's words were exactly right and my interpretation was wrong, and in both cases the only record was my interpretation. If the utterance had been a tracked item with the reading pointing at it, the disagreement would have been visible in the model instead of surfacing three turns later. WHY `UNSOURCED` IS THE NUMBER I EXPECT TO BE UNCOMFORTABLE, and the reason to build this rather than the reason not to: most of the 355 sprints in this repository were charted by me, not requested. Some of that is correct - they hired an engine to run the process - but nobody can currently tell the ratio, and a project where the AI's inventions outnumber the human's requests by an unknown factor cannot answer 'is this building what was asked for'. That is a traceability question and this engine already answers the equivalent question for requirements (`keel rootedness`). WHY NOT REUSE `Need`: a Need is solution-free, refined and prioritised - it is already an interpretation, authored deliberately. Folding the raw utterance into it would destroy the distinction that makes the pair useful, and would put words in their mouth in the field named `statement`. WHY `UserStory` IS A NEW TYPE RATHER THAN FIELDS ON `Need`: I argued the opposite in the first draft of this Decision and their question changed it. A Need is already an interpretation - solution-free, prioritised, source-tagged - so putting the narrative there would fuse the translation step INTO one of its possible outcomes, and a statement that turns out to implicate a BUG rather than a need would have nowhere to land. The three-link chain keeps the translation independent of what it turns out to imply, which is the whole reason to ask the implication question at all. keel's `Story` is untouched: renaming a type used 356 times to free the word is a migration with no benefit, and the two are distinguished by name rather than by hoping nobody conflates them.";
        :>> consequences = "IF ACCEPTED: `schema/core` gains one `part def` - which is a FROZEN-SCHEMA change (invariant 5) and the reason this is proposed rather than applied - plus one computed view, one marker in the edge vocabulary if `#DerivedFrom` needs widening, and a doc-sync pass. The recording cost is one item per directive statement, which at this session's rate is a handful per sitting; the read cost is zero, because it is all computed. THE HONEST LIMIT: nothing can force a statement to be recorded. A guard can report Needs and Decisions with no `#DerivedFrom`, which makes the OMISSION visible, but it cannot know about a statement nobody wrote down - so `unparsed` is a floor, never a total, and the view must say so rather than implying completeness. REMOVAL PATH, per D0163: delete the recorded Statements and UserStories and the view; nothing else reads them, the `#DerivedFrom` edges become ordinary dangling-free edges to nothing only if the targets are deleted too, so remove edges with their statements. Needs, keel `Story` records and Decisions are unaffected - they were never dependent on having a source, which is also why this degrades gracefully if adoption lapses. IF REJECTED: their statements stay in conversation history, my transcriptions stay in procedureText fields, and the question 'how much of this backlog did anyone ask for' stays unanswerable - which is survivable, and worth being a recorded position rather than an accident.";
    }

    // APPLIED 2026-08-20, sprint 356. Recorded here rather than only in the sprint because the
    // `process-change` guard requires a process-def change to be co-committed with the marked Decision
    // that authorizes it - and it is right to: a process file changing with no Decision in the same
    // commit is exactly how a process drifts from its governance. WHAT LANDED, and one thing did NOT
    // land as written: `constraint` and `requirement` are SysML KEYWORDS, so the kernel rejects them as
    // enum members. The Rust parser accepts both, which is the gap CLAUDE.md section 5 names, and
    // `validate_schema.py` caught it because it blocks on schema changes. They are `scopeConstraint` and
    // `verifiedRequirement` in the model; the human's words map to those members and the intake skill
    // and the process both state the mapping, so their vocabulary is preserved rather than silently
    // altered. 17/17 schema files pass the kernel.
    // acceptance event (D0121 review-queue sign-off; D0066/D0106 — human-judged, not fabricated)
    verification d0166Accept : Test { :>> id = "73078db3-c54d-4956-b369-253c9a46779e"; :>> method = VerificationMethod::confirmation; :>> procedureText = "ACCEPT, with the instruction that produced the revision, verbatim: 'Every user story - lets use user story instead of story'. Submitted in the obligations deck review of 2026-08-20 after the Decision was revised to use USER STORY in prose and UserStory in the model throughout, and to stop using the bare word story for the new concept - which their previous NEEDS WORK verdict had objected to in the Decision's own title."; }
    part d0166AcceptR1 : TestResult { :>> id = "ebfde215-7489-4549-b08f-14e37440c73a"; :>> outcome = VerdictKind::pass; :>> judgedAgainst = "986a5a7"; :>> judgedAt = "2026-08-20"; :>> judgedBy = "wweatherholtz"; }
}
