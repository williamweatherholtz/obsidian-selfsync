// D0414 (status: the `status` field below is the truth) — slowHookFireExplainsItself: the fire-ledger's frozen schema gains one additive field, phases, written only on a hook fire at or past the slow threshold and naming what the fire spent its time on, longest step first, with the remainder no counter covered stated as unattributed
// Recorded via `keel record decision` (D0105 RMWX axis; issue054). Acceptance is a separate explicit
// human gate (method=confirmation, D0106): flip status + add the d0414Accept event on sign-off.
package ReferenceDecision0414 {
    private import EngineElement::*;
    private import EngineWork::*;
    private import EngineVerification::*;
    private import EngineRelationships::*;

    // #ProspectiveChange (D0070) - this Decision governs a process/schema change; the co-committed
    // change rides the process-change guard's hard lock.
    #ProspectiveChange part d0414 : Decision {
        :>> id = "de20c44f-70e0-452f-9171-b964565f2c7e";
        :>> title = "slowHookFireExplainsItself: the fire-ledger's frozen schema gains one additive field, phases, written only on a hook fire at or past the slow threshold and naming what the fire spent its time on, longest step first, with the remainder no counter covered stated as unattributed";
        :>> createdAt = "2026-09-09";
        :>> createdBy = "claudeOpus5";
        :>> status = DecisionStatus::accepted;
        :>> context = "issue429, tracked as dcSlowHookFireExplainsItself, opened on the human's words 'kind of seems like keel is still crazy slow' (2026-09-09). The ledger held the answer's shape and not its content: an idle full stop-hook run measures 2 650-2 990 ms, a receipt hit 217 ms, and the tails - 28 s, 35 s, 38 s, the 120 s watchdog - each wrote a line saying ms and nothing else. Every phase cost was measurable under KEEL_PERF=2, but only in a run someone was watching, and the slow fires are by construction the ones nobody watched. D0180 froze the ledger schema at six fields; bin and build were later added beside them as additive fields (issue378), so an additive field is the established form.";
        :>> decision = "NOT A FORK: the DoD names one field with one trigger and forbids the two adjacent changes (shortening priority-inversion, moving guards off the stop hook). A hook process collects its phases whether or not KEEL_PERF is set (perf::collect_phases at hook entry; the counters stay relaxed atomics). A fire whose total ms reaches pm::SLOW_FIRE_MS, 3 000 ms, writes a phases field into its ledger line: an array of name and ms rows in two parts - the wall-clock steps longest first (every hook:* serial phase, the longest guard:* phase labelled critical path since the guards run in parallel and only the longest bounds the wall clock, and unattributed = total minus the sum of the hook:* steps, reported rather than omitted), then the cross-cutting counters that are not steps and never lead (git xN summed across threads, parse). A fire under the threshold carries no field. The reader in pm.rs accepts phases beside bin and build as the additive set and treats a slow line without it as recorded before this Decision.";
        :>> rationale = "A total that cannot be attributed produces a fourth guess, and this codebase has already paid for three wrong attributions from wall clock alone (perf.rs). The fire that needs explaining is the one no one measured, so the measurement has to ride in the record of the fire itself, written by the process that was slow. Collecting phases costs one Instant and a map insert per named step, which is nothing against the steps; writing the field only past the threshold keeps every fast line the size it was. Naming the remainder as unattributed is what keeps the field honest: a phase no counter covers appears as a number, so a tail this attribution cannot explain says so in the line, and the next counter is aimed at a measured gap. The summed counters follow the steps because a summed wait across twenty threads can exceed the fire's total, and a line whose first entry exceeds its own total would be read as a defect in the line.";
        :>> consequences = "perf.rs gains collect_phases, the HOOK_PHASE prefix, attribution and the pure attribute with its probe pair; pm.rs gains SLOW_FIRE_MS, LEDGER_ADDITIVE_FIELDS, slow_fire_phases and a slowFires section in enforcement-report (threshold, count, the last 25 rows by phase, a pre-D0414 line stated as unattributed); main.rs names each hook's serial steps as phases and ledger_emit attaches the field; guards.rs times every guard and records the run's critical path, which the guard receipt stores as critical_path and KEEL_PERF=1 keel guard prints; CLAUDE.md section 5 states the field. Hook source and guard source are the enforcement surface (D0209 clause 2), so this Decision is the co-committed change record and, as a process change, stays proposed for the human (D0337). STATED LIMIT: attribution covers the phases the hook process names; time spent before main runs (loader, antivirus on the binary) or in the harness between fork and exec is inside unattributed and cannot be named from within the process. The threshold is a constant chosen from one host's idle measurement; a host whose idle run is slower will attribute every fire, which costs a field per line and misleads no one.";
    }

    // acceptance event (D0121 review-queue sign-off; D0066/D0106 — human-judged, not fabricated)
    verification d0414Accept : Test { :>> id = "4fd997d7-2251-4011-a8a3-1037829f075a"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0414 (D0201 B); recorded as given (D0423)."; }
    part d0414AcceptR1 : TestResult { :>> id = "235815fa-00fb-48cf-bbc1-d37f12a55ec6"; :>> outcome = VerdictKind::pass; :>> judgedAgainst = "3e6c518"; :>> judgedAt = "2026-09-11"; :>> judgedBy = "wweatherholtz"; :>> createdBy = "claudeOpus5"; }
}
