// D0150 — ACCEPTED (wweatherholtz, 2026-08-15): the binary DERIVES its vocabulary from the schema,
// and an undeclared attribute becomes a hard gate failure. Adds a 33rd guard (§3a: a gate change) —
// sign-off is the d0150Accept event below.
package ReferenceDecision0150 {
    private import EngineElement::*;
    private import EngineWork::*;
    private import EngineVerification::*;
    private import EngineRelationships::*;

    part d0150 : Decision {
        :>> id = "b81f4a26-7c95-4e08-a3d1-6e2b90f7c541";
        :>> title = "D0150: schema vocabulary is DERIVED, and an undeclared attribute fails the gate";
        :>> createdAt = "2026-08-15";
        :>> createdBy = "claudeOpus5";
        :>> status = DecisionStatus::accepted;
        :>> context = "Requested by wweatherholtz, 2026-08-15, verbatim: 'do a holistic pass against the new schema. we keep being surprised that the new elements aren't being picked up - pass over all existing hooks to make sure they reconcile. we should be throwing errors if there are schema mismatches, or if we're telling on bespoke data hooks instead of intrinsic ones'. THE AUDIT FOUND TWO CLASSES, both proven by probe rather than argued. FIRST, ATTRIBUTE NAMES WERE NEVER CHECKED AT ALL. The engine validates MARKERS (D0133) and ENUM MEMBERS, but a `CodeElement` authored with `codeHsah` and `riskClas` passed `keel validate`, all 32 guards AND the fast edit gate — 329 files reported clean — while silently losing its risk classification: the element sat in the `arch criticality` frontier as `correctness` when its author had written `dataLoss`, and reported UNAUDITED when its author believed a hash was recorded. That is the whole 'new elements aren't being picked up' surprise. SECOND, THREE CONSTANTS RESTATED SCHEMA VOCABULARY WITH NOTHING RECONCILING THEM, and one had already drifted in both directions: `KNOWN_EDGES` rejected `derivedFrom`, `covers`, `dispositions` and `specialize` — declared in the `EdgeKind` enum and used by 166 edges in the model — while accepting three kinds the schema never declared, so a declared view over `derivedFrom` failed with 'references unknown edge kind'. The `EdgeKind` enum itself was INERT: no code read it. `ENGINE_MARKERS` was missing the three markers shipped with the codeaudit module. `RISK_ORDER` agreed with `RiskClass` only because the same author wrote both in the same hour.";
        :>> decision = "ACCEPTED, with the human choosing derivation over a reconciliation guard when asked: (1) DERIVE the vocabulary. A new `schema` module parses the `.engine/schema` already embedded in the binary by `include_dir!` and exposes edge kinds, enum members in declaration order, and per-type attributes following `:>` inheritance. `KNOWN_EDGES`, `ENGINE_MARKERS` and `RISK_ORDER` are deleted as literals and computed from it, which makes that drift UNREPRESENTABLE rather than merely detectable. The EMBEDDED schema is read and never the downstream project's on-disk copy — reading the project's is exactly what caused issue090's 566-violation lockout — so the engine's vocabulary travels with the engine. (2) ADD a 33rd hard guard, `attribute-vocabulary`: every `:>> name =` on an ENGINE-typed element must name an attribute that type declares, with a nearest-name hint. A type the engine schema does not declare is a PROJECT type and is SKIPPED ENTIRELY, never judged, for the same issue090 reason.";
        :>> rationale = "WHY DERIVATION RATHER THAN A RECONCILIATION GUARD, which was the alternative offered: a guard reports drift after it has been authored, while derivation removes the second place that could drift at all. The cost is a small text scan of the embedded schema at first use, which is bounded and cached. WHY THE GUARD IS HARD-BLOCKING AND NEEDED NO GRANDFATHERING: run against the corpus it scans 40355 assignments and finds ZERO violations, so every file written to date already complies and the control is forward-only by construction (issue068) without a baseline or an exemption list. A defect that silently deletes an authored value is not a warning-level concern — the author believes the fact is recorded and every gate agrees the model is honest. ALTERNATIVES REJECTED: deleting the `EdgeKind` enum in favour of markers alone was offered and not chosen, because it discards a frozen-core declaration a downstream project may already cite; leaving `EdgeKind` inert was not an option once found, since an unread declaration is precisely what D0142 removed and D0144's consumer check exists to prevent.";
        :>> consequences = "If ACCEPTED: 33 guards, 24 hard-blocking; a misspelled attribute is refused at the edit gate with the type it was authored on and the nearest declared name; `derivedFrom`, `covers`, `dispositions` and `specialize` become traversable in declared views, so the 166 edges already in the model are reachable from the view layer for the first time; adding an enum member, a marker or an attribute to the schema needs NO corresponding code edit. If REJECTED: the three constants must be restored and reconciled by hand on every schema change, and a misspelled attribute keeps passing every layer while silently discarding the value. Tracked as issue118, issue119 and issue120.";
    }

    // acceptance event (D0121 review-queue sign-off; D0066/D0106 — human-judged, not fabricated)
    verification d0150Accept : Test { :>> id = "543bb173-8800-43f4-8a77-6c64f22d108f"; :>> method = VerificationMethod::confirmation; :>> procedureText = "wweatherholtz, 2026-08-15, verbatim: 'approved'. Given in direct reply to the holistic schema-audit report, which presented the two proven findings (a misspelled attribute passing validate + all 32 guards + the fast gate while silently discarding the value; KNOWN_EDGES drifted from the EdgeKind enum in both directions, leaving 166 model edges unreachable from the view layer), the built implementation with its gate results, and the explicit statement that D0150 adds a hard-blocking gate and therefore needs sign-off under section 3a. The human had already chosen derivation over a reconciliation guard when asked the architecture question directly."; }
    part d0150AcceptR1 : TestResult { :>> id = "57c7048c-68ff-4aca-8e2a-c1f5723bd113"; :>> outcome = VerdictKind::pass; :>> judgedAgainst = "344807f"; :>> judgedAt = "2026-08-15"; :>> judgedBy = "wweatherholtz"; }
}
