// D0434 (status: the `status` field below is the truth) — processStepDeclaresItsCheck: ProcessStep carries checkedBy naming the guard or declared rule that checks it, guard step-check-resolves holds that the name exists, and hardening reports enforcement per step
// Recorded via `keel record decision` (D0105 RMWX axis; issue054). Acceptance is a separate explicit
// human gate (method=confirmation, D0106): flip status + add the d0434Accept event on sign-off.
package ReferenceDecision0434 {
    private import EngineElement::*;
    private import EngineWork::*;
    private import EngineVerification::*;
    private import EngineRelationships::*;

    // #ProspectiveChange (D0070) - this Decision governs a process/schema change; the co-committed
    // change rides the process-change guard's hard lock.
    #ProspectiveChange part d0434 : Decision {
        :>> id = "8fd9baa4-4368-4e57-b74e-efdf109be3e4";
        :>> title = "processStepDeclaresItsCheck: ProcessStep carries checkedBy naming the guard or declared rule that checks it, guard step-check-resolves holds that the name exists, and hardening reports enforcement per step";
        :>> createdAt = "2026-09-10";
        :>> createdBy = "claudeOpus5";
        :>> status = DecisionStatus::accepted;
        :>> context = "D0321 measured 37 processes of which only agile-workflow's ceremony steps carry a per-step check, and found seven processes whose steps an existing guard already checks with nowhere to write that fact: controlDefect (control-defect-registry), decisionSurfacing (judgment-request-quality), libraryStewardship (unit-extras-present), migration (marker-census), stpaDiagram (viewpoint-renderer), stpaSelf (stpa-currency), and githubIntake's routing steps (untrusted-routing, untrusted-taint). The human chose option A on 2026-09-05 in their words 'd0321 A': the attribute on the step, not a contract beside it (C) and not yet analytical facts as structure (B). This is the schema clause of that choice; dcAdvanceRefusesAnyBoundStep, the advance generalisation, is its own item and Decision (D0303). The core schema is frozen (section 1.5), so this Decision carries the marker and waits for the human's word under D0337.";
        :>> decision = "NOT A FORK: the option was chosen in D0321 and this records its schema clause. `action def ProcessStep` in .engine/schema/core/process.sysml gains `attribute checkedBy : String [0..1];` - the name of the guard (a GUARD_NAMES entry) or declared rule (a `part <name> : EdgeRule|ElementRule` in .engine/rules/rules.sysml) whose predicate checks that the step was done. It is applied as a D0067 migration: the committed transform .engine/tools/migrations/2026-09-10-step-checked-by.py, dry-run by default, idempotent, binds seven steps - cd4Register, dsGround, lsStock, sd0Compute, stpa5Trigger, giRoute, giBoundary - and reconciles the control totals of processes and steps before and after. D0321 named an eighth, migration's mig2DryRunReconcile to marker-census, and the guard's first live run refused it: marker-census is a lens (commands.sysml, family lens), not a guard, so nothing runs it on the step - the migration process stays unbound (issue465). Guard step-check-resolves FAILS a checkedBy that names no guard and no rule, anchored to EHZ5: a step that claims a check nothing runs is an enforcement point that is silently dead. keel show hardening gains stepEnforcement: per step, checked (a resolving checkedBy) / declaredJudgment (its process is declared checkable = false in process-enforcement.toml) / undeclared, with the counts beside the per-process figures it reports today - an indicator, never a gate, for the same Goodhart reason the per-process ratio is one.";
        :>> rationale = "The gap D0321 measured is a place to write the fact, not a missing check: the guards exist, the steps exist, and only prose joins them. An attribute on the step is the one home (D0105) - a contract beside the process is a second file a rename orphans silently, which is the shape that made process-enforcement.toml a stopgap. Making the binding resolvable by a guard is what makes it a fact a control can read rather than a comment: a step naming a retired guard would otherwise claim enforcement that no longer runs, the EHZ5 shape. Per-step reporting is the honest surface for a process that is checked at one step and judgment at five - the per-process ENFORCED bucket reads that as fully enforced today. Optional multiplicity is the EXPAND step: every existing step stays valid unbound, and nothing here contracts.";
        :>> consequences = "process.sysml gains the attribute; the migration script and its dry-run receipt land in .engine/tools/migrations/; seven steps across six process files carry checkedBy, and migration's reconcile step is the tracked gap (issue465, resolver dcMigrationReconcileIsAGuard); guards.rs gains step_check_resolves and GUARD_NAMES grows by one, with keel version, guards.md, control-map.sysml (gStepCheckResolves to ehz5) and the attribute vocabulary following; hardening.rs gains stepEnforcement with a test that its counts equal a hand count over the process files and a fixture test that a ghost name fails the guard. STATED: a binding names the control and does not make it good (D0254), and a step whose guard is warning-tier is checked only as far as a warning goes - the lens reports the guard's name so a reader can see which. The agile-workflow ceremony steps are bound in dcAdvanceRefusesAnyBoundStep, where their binding becomes the data advance reads; until then advance is unchanged.";
    }

    // acceptance event (D0121 review-queue sign-off; D0066/D0106 — human-judged, not fabricated)
    verification d0434Accept : Test { :>> id = "ead05b8f-16f7-4216-b28e-792538c3b95b"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0434 (D0201 B); recorded as given (D0423)."; }
    part d0434AcceptR1 : TestResult { :>> id = "3ecaed07-c7c2-4814-b4d5-c9e55c121165"; :>> outcome = VerdictKind::pass; :>> judgedAgainst = "3e6c518"; :>> judgedAt = "2026-09-11"; :>> judgedBy = "wweatherholtz"; :>> createdBy = "claudeOpus5"; }
}
