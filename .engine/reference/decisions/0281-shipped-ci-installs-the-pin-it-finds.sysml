// D0281 (status: the `status` field below is the truth) — Every CI workflow keel ships installs the version the project PINS, and builds from source only where the crate exists
// Recorded via `keel record decision` (D0105 RMWX axis; issue054). Acceptance is a separate explicit
// human gate (method=confirmation, D0106): flip status + add the d0281Accept event on sign-off.
package ReferenceDecision0281 {
    private import EngineElement::*;
    private import EngineWork::*;
    private import EngineVerification::*;
    private import EngineRelationships::*;

    // #SafetyChange (D0070) - this Decision governs a process/schema change; the co-committed
    // change rides the process-change guard's hard lock.
    #SafetyChange part d0281 : Decision {
        :>> id = "57ecabe1-e40a-4673-8e0a-3319910156d0";
        :>> title = "Every CI workflow keel ships installs the version the project PINS, and builds from source only where the crate exists";
        :>> createdAt = "2026-09-01";
        :>> createdBy = "claudeOpus5";
        :>> status = DecisionStatus::accepted;
        :>> context = "Two shipped-CI defects found downstream by a peer session and verified here at file:line (issue326, issue327). The decision-channel unit ships two workflows as extras that ran `cargo build -p keel-cli` - a crate no consumer has - so every project importing it acquired two permanently red workflows. And `keel init` scaffolded a gate workflow whose install step was three echo lines that installed nothing, so every fresh project's own gate failed on its first push with `keel: command not found` - reading as the placeholder nobody deleted rather than as a gate that is not running. One root under both: every CI workflow keel shipped was written for the engine's own repository and had never been observed to run anywhere else. This is step 5 of the D0275 migration plan, and it is what makes steps 1 to 4 visible downstream at all.";
        :>> decision = "One install step, correct in both homes. If `keel-cli/Cargo.toml` exists the workflow builds from source, because the engine's in-workflow gate exists to gate recorder commits with the code IN that commit. Otherwise it reads `.engine/contracts/engine-version.toml`, downloads `keel-linux-x86_64` from the release tagged with that exact version, and fails loudly if the pin is absent. The binary lands at `target/release/keel` either way, so nothing downstream in the workflow changes. The Rust toolchain and cache steps are gated on the same file existing. `keel init`'s scaffolded gate uses the download half and puts the binary on PATH, then runs `keel version` before any gate step trusts it.";
        :>> rationale = "WHY THE PIN AND NOT LATEST, which is the non-obvious half and the reason the placeholder could never have been filled in naively: the project's pin is BINDING under D0251, and validate/guard REFUSE under engine-version skew on a gate surface. A runner installing latest against a project pinned to an older version would go from `command not found` to a refusal - still red, now for a subtler reason. Reading the pin is the only correct behaviour, and it is also why migration (pm3Reconcile) needs no edit to the workflow: the workflow reads the pin at run time, and migration re-stamps the pin. WHY ONE FILE AND NOT A CONSUMER VARIANT, which the peer offered: unit extras ship a file from path X to path X, so two variants at one destination would need a from/to mapping in unit-extras.toml - a contract change to carry two copies of a file that a three-line conditional handles. WHY THE ENGINE REPO MUST STILL BUILD: its decision-channel workflows gate RECORDER commits, and a recorder commit must be gated by the code in that commit, not by the last release. Downloading here would make the in-workflow gate test yesterday's binary against today's tree. FEASIBLE AS OF TODAY, verified rather than assumed: the repository is PUBLIC (`gh repo view`), so no secret is needed; release.yml attaches `keel-linux-x86_64` per tag; and the step was RUN against the pin - `0.3.1` read from a fresh scaffold, an 11.6 MB x86-64 ELF downloaded from that release. The download half is proven; only execution on a GitHub runner is beyond reach from here.";
        :>> consequences = "A project that imports decision-channel gets two workflows that can run. A fresh `keel init` project's first push runs its own gate instead of failing on an echo. Three controls hold it: the scaffolded template is checked for a real install that reads the pin and names the exact asset; both shipped workflows are checked for the conditional build, the pin read, the asset name, the shared binary path, and the gated toolchain steps; and the realistic migration fixture gains its fourth property - a project's own CI survives migration and still installs the pin, because it reads the pin at run time. THE HONEST LIMIT, stated as the DoD stated it: none of this is a live green run in a consumer's GitHub Actions. That evidence can only come from downstream, and pm5FeedBack in the project-migration process exists for exactly that - the first downstream project to report a green keel-gate run is the arming this Decision cannot supply for itself. Until then it is verified by construction and by a real download, which is more than the placeholder ever had and less than the claim deserves.";
    }

    // acceptance event (D0121 review-queue sign-off; D0066/D0106 — human-judged, not fabricated)
    verification d0281Accept : Test { :>> id = "fc23dc91-e057-4e8e-b631-4708834a9d4c"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0281AcceptR1 : TestResult { :>> id = "2e6623f8-89d9-4257-9498-637fb71fd9d6"; :>> outcome = VerdictKind::pass; :>> judgedAgainst = "42d80f5"; :>> judgedAt = "2026-09-02"; :>> judgedBy = "wweatherholtz"; }
}
