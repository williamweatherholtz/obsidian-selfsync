// D0312 (status: the `status` field below is the truth) — verificationByAuthority: what a passing verification MEANS by authority and method - machine, proposed, human - and how the human judges in sets
// Recorded via `keel record decision` (D0105 RMWX axis; issue054). Acceptance is a separate explicit
// human gate (method=confirmation, D0106): flip status + add the d0312Accept event on sign-off.
package ReferenceDecision0312 {
    private import EngineElement::*;
    private import EngineWork::*;
    private import EngineVerification::*;
    private import EngineRelationships::*;

    // RESEARCH: Measured 2026-09-05 (keel attestation): 5024 AI-judged results, 13 percent of the exercised ones carry a receipt, 3698 AI-examined are testimony; 323 human-judged; method mix inspect 2408, test 1342, critique 915, analyze 591, confirmation 289, demo 207. The human's words (st065, 2026-09-02): an automatic test verifies itself and satisfies its parent; otherwise default to human verification on evidence the AI proposes, in sets so they are not hammered; leverage analysis, demonstration, inspection, test; an AI demonstration is feasible evidence; pair it with a strong STPA process. Prior art in this tree: D0232 (a pass is a receipt or a testimony; guard 52), D0298 (controls prove arming by test), D0284/D0285 (the control structure and STPA diagram now exist, which this proposal was told to wait for), issue158 (a COUNT accepted as a card - why sets must still record each item). Outside: DO-178C's independence and credit rules for verification by analysis/review/test; ISO 26262's confirmation measures by ASIL - both bind WHO may credit a method to the consequence of being wrong, which is the shape asked for here.
    part d0312 : Decision {
        :>> id = "10c49303-0250-4ada-89d2-190eb53eb869";
        :>> title = "verificationByAuthority: what a passing verification MEANS by authority and method - machine, proposed, human - and how the human judges in sets";
        :>> createdAt = "2026-09-05";
        :>> createdBy = "claudeOpus5";
        :>> status = DecisionStatus::accepted;
        :>> context = "Today every result is a pass regardless of who judged it and how: an AI-judged inspect with no receipt counts exactly as a CI-verified test. The human asked for a revamp (st065): automatic tests self-verify; everything else defaults to human judgment on evidence the AI proposes, in sets; the method kinds are leveraged; an AI demonstration is feasible evidence. This is a Change Request against the verification model and touches the frozen VerificationMethod vocabulary and the meaning of `done` - a FORK the human owns. The control structure it binds authority to now exists (D0284).";
        :>> decision = "OPTION A (three tiers, proposal sets): MACHINE - method test whose receipt CI can re-run (the dcExternalFactGate mechanism) is self-satisfying and satisfies its parent. PROPOSED - demo, analyze, inspect recorded by an AI carry outcome `proposed` with their evidence, count as done for nothing until a human judges; the human judges a SET (one sitting, one card) but each item is recorded individually with its own quote receipt, so issue158 cannot recur. HUMAN - confirmation, unchanged. COST: a new outcome value (schema, frozen), a `proposed` state in orient's done computation and every view that reads outcomes, a set-judgment write path and console card, guards 52 and confirmation-authenticity adjusted; the 5024 standing AI results grandfathered by date and never re-judged; the human's load becomes one set per sprint (about 6 items each at today's rate) instead of zero. OPTION B (the same tiers, AI demo stands): as A, but an AI-judged demo with a REPLAYABLE receipt (a command CI or the human can re-run) stays a pass; the human samples rather than judges every set. COST: A's schema and view changes, plus a replay mechanism and a sampling policy that must be declared in attestation-policy.toml; the human's load falls to a sample; the risk is a demo receipt that replays green for the wrong reason, which only sampling catches. OPTION C (status quo, receipts mandatory): no tiers; every AI method must carry a receipt (guard 52 widened from test to all methods) and the human's role stays optional pull-audit (D0204). COST: smallest - one guard change and a forward-only cutoff - but it does not do what st065 asked: an AI inspect with a receipt still self-certifies, and nothing becomes the human's to judge.";
        :>> rationale = "WHY NOT DECIDE THIS AUTONOMOUSLY: it changes the frozen schema and what done means, and it sets the human's own load - the two things standing consent does not cover. WHAT I RECOMMEND, AND WHAT WOULD CHANGE IT: OPTION B. A is the purest reading of st065 but makes every AI inspect and analyze a human's pending item; at today's rate that is the hammering the human said they do not want, and sets only batch it. B keeps the human as the authority over what cannot be machine-verified while letting a replayable demonstration - which the human explicitly called feasible evidence - stand on its receipt, with sampling as the STPA-style control gap check they also asked for. C is what exists plus a wider receipt rule and changes no authority; I would take it only if the human wants no new judging load at all. It stops recommending B if the human wants to judge every non-machine item personally (then A), or wants none (then C). Under any option the 5024 standing results are grandfathered by date: re-judging them is the D0129 class.";
        :>> consequences = "Until accepted: nothing changes; dcVerificationByAuthority's own DoD is this proposal and passes once judgment-request-quality accepts it. On acceptance: a schema Decision naming the outcome value and fields, a D0067 migration for the outcome vocabulary, the set-judgment write path and card, guard changes, and the attestation census gaining a `proposed` column. dcStpaProcessForKeel is the companion the human asked for in the same breath and is proposed separately.";
    }

    // acceptance event (D0121 review-queue sign-off; D0066/D0106 — human-judged, not fabricated)
    verification d0312Accept : Test { :>> id = "9ad7ce1e-7a69-4510-9d2f-ed9f06cb4e42"; :>> method = VerificationMethod::confirmation; :>> procedureText = "OPTION B chosen (same tiers, AI demo with a replayable receipt stands; the human samples). their words, verbatim, two lines with the line break rendered as ' / ': 'd0312 B / d0321 A'"; }
    part d0312AcceptR1 : TestResult { :>> id = "e98933a9-1a3b-44f2-a81d-8cc83f8b596f"; :>> outcome = VerdictKind::pass; :>> judgedAgainst = "811be12"; :>> judgedAt = "2026-09-05"; :>> judgedBy = "wweatherholtz"; :>> createdBy = "claudeOpus5"; }
}
