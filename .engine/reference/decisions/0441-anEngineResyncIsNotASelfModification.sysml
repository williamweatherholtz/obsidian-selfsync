// D0441 (status: the `status` field below is the truth) — anEngineResyncIsNotASelfModification: process-change leaves a locked file alone when its new text is the engine embedded in the judging binary, outside the self-build
// Recorded via `keel record decision` (D0105 RMWX axis; issue054). Acceptance is a separate explicit
// human gate (method=confirmation, D0106): flip status + add the d0441Accept event on sign-off.
package ReferenceDecision0441 {
    private import EngineElement::*;
    private import EngineWork::*;
    private import EngineVerification::*;
    private import EngineRelationships::*;

    // #ProspectiveChange (D0070) - this Decision governs a process/schema change; the co-committed
    // change rides the process-change guard's hard lock.
    #ProspectiveChange part d0441 : Decision {
        :>> id = "5f44b9f3-7e4c-461b-bac9-b58c0fd9b2b2";
        :>> title = "anEngineResyncIsNotASelfModification: process-change leaves a locked file alone when its new text is the engine embedded in the judging binary, outside the self-build";
        :>> createdAt = "2026-09-10";
        :>> createdBy = "claudeOpus5";
        :>> status = DecisionStatus::accepted;
        :>> context = "The keystone lock (D0070, D0209 clause 2) refuses a change to a process definition or the enforcement surface with no co-committed marked Decision, because a silently self-modified control is the issue236 class. keel migrate resyncs .engine/ from the engine embedded in the binary (D0275) and skills, contracts and rules under .engine/ are locked paths - so every resync writes locked files, and no Decision in the project authored them. Under the staged read that refusal fell only at the downstream project's post-migrate commit, in its pre-commit hook. D0440 made the five diff-reading guards read the working tree outside a hook, and the same refusal now falls inside keel migrate's own D0336 gate: the update is written, process-change reads the resynced skill file as an unsigned locked-file change, the gate goes red and the update is reverted byte-for-byte - six migration fixture tests went red on 2026-09-10 the first time the touched set ran (issue475). The lock was never meant to bind the engine arriving on a project; it was written for an author changing a control by hand, and it could not tell the two apart.";
        :>> decision = "NOT A FORK: this names what the lock already meant. process-change drops from its locked set every path under .engine/ whose text under the current read - the index blob inside a hook, the file on disk outside it - equals, line endings normalised, the file the judging binary embeds at the same relative path, and says so in one warning line naming the paths. Two exclusions: the self-build (a tree holding keel-cli/Cargo.toml), where the embedded engine is the tree itself and a rebuild after an edit would launder any change - keel migrate refuses the self-build for the same reason; and a deleted locked file, which has no text to compare and stays under the lock. The exemption is decided by content, never by the pin: engine-version.toml moving is not evidence, because a pin is one line anyone can write.";
        :>> rationale = "The lock protects the project from a control changed without a human's word. The engine's own published text is not that: it is the same text every adopter of this version holds, shipped in the binary the human chose to run, and the migration path already runs the project's whole gate over the result (D0336) and refuses a red. Deciding by content equality is the narrowest possible exemption - a resynced file with one edited byte is back under the lock - and it is decidable in both read modes with what the binary already carries. Blinding migrate's gate to the working tree instead (running it in the hook shape) would have kept the fixture green and left the downstream post-migrate commit refused by the pre-commit hook, which is where this refusal has stood since D0209 and where no test looked. What would change it: an engine release that ships a weakened control, which this exemption would carry through - the check for that is audit-adherence's monotonicity in CI, not the keystone.";
        :>> consequences = "Process-change (D0337) - the marker rides the commit that carries this text with D0440. A downstream project runs keel migrate, its own gate passes over the resynced files, the update is retained, and its pre-commit hook passes the same files at the commit. A hand edit to any locked engine file is refused as before, in both reads. The self-build gains nothing and loses nothing: the exemption is inert there. guards.md's process-change row names the exemption and its two exclusions; tests/resync_is_not_a_self_modification.rs is the D0388 pair - known-positive: a project whose locked skill file is overwritten with the embedded text passes process-change at the terminal with no Decision; known-negative: the same text with one line appended fails naming the file; a third case pins the self-build exclusion. issue475 resolves through dcResyncIsNotASelfModification, delivered in sprint 666 beside D0440 because the two cannot land apart: the read without the exemption reverts every migration, and the exemption without the read has nothing to exempt outside a hook.";
    }

    // acceptance event (D0121 review-queue sign-off; D0066/D0106 — human-judged, not fabricated)
    verification d0441Accept : Test { :>> id = "c804ecc3-dc71-4076-851c-6efa5e526bb7"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0441 (D0201 B); recorded as given (D0423)."; }
    part d0441AcceptR1 : TestResult { :>> id = "9b8101cb-21bd-4d22-83c7-dc2a5e6df7f2"; :>> outcome = VerdictKind::pass; :>> judgedAgainst = "3e6c518"; :>> judgedAt = "2026-09-11"; :>> judgedBy = "wweatherholtz"; :>> createdBy = "claudeOpus5"; }
}
