// D0132 — The kernel's per-file instance validator leaves the BLOCKING
// commit path; `keel check-engine` is the enforced gate for .engine instance references.
// A gate bypassed 100% of the time provided no assurance AND destroyed every other layer's.
// Marked #ProspectiveChange (D0070): commits gated under the prior arrangement stay valid.
package ReferenceDecision0132 {
    private import EngineElement::*;
    private import EngineWork::*;
    private import EngineVerification::*;
    private import EngineRelationships::*;

    #ProspectiveChange part d0132 : Decision {
        :>> id = "8b4d2f60-1c93-4a58-bd07-6e5f1a92c4de";
        :>> title = "D0132: retire the kernel per-file instance validator from the blocking commit path; check-engine is the enforced gate";
        :>> createdAt = "2026-08-13";
        :>> createdBy = "claudeOpus5";
        :>> status = DecisionStatus::accepted;
        :>> context = "issue081. `.engine/tools/validate/validate_instances.py` runs as a BLOCKING pre-commit step whenever `.engine/(decisions|processes|skills|docs|views)/*.sysml` is staged. It validates each instance file IN ISOLATION, so any reference to an element declared in ANOTHER file cannot resolve. It consequently FAILS ELEVEN FILES THAT ARE ALREADY COMMITTED AND CORRECT — decisions 0114 and 0116-0125 — on diagnostics like `Couldn't resolve reference to Element 'd0014'`, `'nViewerTemporalState'`, and `Couldn't resolve reference to Type 'DerivedFrom'`. Since those commits exist, the gate was bypassed with SKIP_VALIDATE=1, and SKIP_VALIDATE=1 skips EVERY layer — validate, all guards, check-engine and clippy — not merely the failing one. Measured this sitting: the bypass was used on every single `.engine` commit (eight occasions across sprints 247-253). So the arrangement did not merely fail to add assurance; each use actively removed the assurance of four working layers. This is the dynamic issue076 describes — a gate that blocks correct work teaches contributors to disable it — and it is far more dangerous with the distributed team of D0129, where each contributor learns the same habit independently. Two corroborating facts: (a) `keel check-engine` (D0112 phase 2, KERNEL-FREE) resolves references ACROSS files and passes all eleven cleanly, so the kernel step adds no assurance here while costing a ~20s JVM start and orphaning JVMs; (b) the kernel likewise cannot resolve `DerivedFrom`, independently confirming issue077's undeclared-marker finding.";
        :>> decision = "Remove `validate_instances.py` from the BLOCKING pre-commit path and make it OPT-IN behind `KEEL_KERNEL_VALIDATE=1`. `keel check-engine` becomes the enforced gate for `.engine` instance reference resolution — it already runs on every `.sysml` commit, is kernel-free, resolves references across files, and exits non-zero on a genuine unresolved reference (verified by negative test: injecting `part d0131 : ThisTypeIsNotDeclaredAnywhere` produced `ERROR: ...:11 — unresolved type reference` and exit 1; restoring the file returned exit 0). SCOPE IS DELIBERATELY MINIMAL: only the instance validator moves. `validate_schema.py` and `validate_workflows.py` stay BLOCKING — they are not proven broken, they fire only on the rare `.engine/schema` or `.engine/workflows` change, and demoting them would be an unforced loss of the deep type-conformance oracle. The kernel therefore remains the authoritative SysML oracle for the deeper residual (D0112 phase 3); what changes is that it no longer gates ordinary instance commits.";
        :>> rationale = "A gate bypassed 100% of the time is not a gate — and this one was worse than absent, because the only available bypass is all-or-nothing. Each use silently disabled validate, guard, check-engine and clippy for that commit. Removing it from the blocking path therefore INCREASES total enforcement, which is the counter-intuitive core of this decision: the safest configuration is the one people do not route around. ALTERNATIVES: (i) fix validate_instances.py to register all instance packages before validating, the two-pass shape that fixed issue079 — REJECTED for now as the wrong investment: it requires loading the whole instance set into one kernel session, it is squarely against the accepted D0112 JVM-retirement direction, and check-engine already performs the cross-file resolution correctly and in milliseconds; the option stays open if the deeper residual ever needs to gate commits again; (ii) keep it blocking and fix the 11 files — REJECTED, the files are CORRECT; the validator's isolation assumption is what is wrong, and editing correct records to satisfy a broken checker inverts the relationship between model and tool; (iii) narrow SKIP_VALIDATE so it skips only one layer — a real improvement but a larger change to the escape hatch, and it treats the symptom rather than the broken gate; recorded as a possible follow-on; (iv) CHOSEN — demote the broken gate, keep the working kernel-free one enforced, leave the rest of the kernel path untouched. RISK ACCEPTED: the deep type-conformance/specialization residual is no longer checked at commit time for instance files. That risk is small and was already fully realised in practice — the check has not actually run on a commit for the entire measured period, because it was bypassed every time.";
        :>> consequences = "`.githooks/pre-commit` runs `validate_instances.py` only when `KEEL_KERNEL_VALIDATE=1`; `keel check-engine` remains unconditional and is now the enforced instance gate. `.engine` commits stop requiring SKIP_VALIDATE=1, so validate + all 22 guards + check-engine + clippy actually run on them again — the practical restoration of four layers. CLAUDE.md section 5 is doc-synced to state which gate is enforced and that the kernel instance validator is opt-in. issue081 resolves. The kernel remains available and is still the deeper oracle on demand (`KEEL_KERNEL_VALIDATE=1`, or run the validators directly), and `validate_schema.py`/`validate_workflows.py` still block on schema and workflow changes. NOT ADOPTED here: making SKIP_VALIDATE layer-selective — a genuine improvement, recorded as a follow-on rather than bundled. Acceptance state is carried by `status` plus the d0132Accept event and is not restated here (decisionNoVerdictProseRule).";
    }

    verification d0132Accept : Test { :>> id = "f16a41a0-1918-4be7-b615-75e59dcc2daa"; :>> title = "Human acceptance of d0132"; :>> createdAt = "2026-08-13"; :>> createdBy = "claudeOpus5"; :>> method = VerificationMethod::confirmation; :>> procedureText = "wweatherholtz attests acceptance of d0132 (the kernel per-file instance validator leaves the BLOCKING commit path and becomes opt-in behind KEEL_KERNEL_VALIDATE=1; `keel check-engine` is the enforced instance gate). The acceptance covers the stated risk: the deep type-conformance residual is no longer checked at commit time for instance files — a risk already fully realised in practice, since the check had been bypassed on every .engine commit measured. Attested 2026-08-13 in session with the words 'accept on all counts', in direct response to an enumerated list of three outstanding items (frozen-schema sign-off, D0131/D0132 acceptance, per-sitting review). Batched acceptance is sanctioned by D0019."; }
    part d0132AcceptR1 : TestResult { :>> id = "88275a22-e9f7-4474-8033-938a9b2f0679"; :>> outcome = VerdictKind::pass; :>> judgedAgainst = "8df2822"; :>> judgedAt = "2026-08-13"; :>> judgedBy = "wweatherholtz"; }
    part d0132AcceptR2 : TestResult { :>> id = "659ee9b8-b772-44b6-870c-0441423193c3"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences acceptance-state sentence replaced at d6f9da5 - editorial, the agreed substance unchanged. Their standing words, verbatim: 'issues raised are automatically accepted. they can be customizedly changed post-fact.'"; }
}
