// D0248 (status: the `status` field below is the truth) — Six clauses cut from my own Needs, and why this is NOT the acceptance gate
// Recorded via `keel record decision` (D0105 RMWX axis; issue054). Acceptance is a separate explicit
// human gate (method=confirmation, D0106): flip status + add the d0248Accept event on sign-off.
package ReferenceDecision0248 {
    private import EngineElement::*;
    private import EngineWork::*;
    private import EngineVerification::*;
    private import EngineRelationships::*;

    // #ProspectiveChange (D0070) - this Decision governs a process/schema change; the co-committed
    // change rides the process-change guard's hard lock.
    #ProspectiveChange part d0248 : Decision {
        :>> id = "e840db05-415f-498a-9d4e-915b62a7ff72";
        :>> title = "Six clauses cut from my own Needs, and why this is NOT the acceptance gate";
        :>> createdAt = "2026-08-28";
        :>> createdBy = "claudeOpus5";
        :>> status = DecisionStatus::accepted;
        :>> context = "The fourteen Needs authored under D0246 were presented to the human for narrowing as KEEL-ND-0001, rendered from the exec-summary template in the se-templates project. The read-back followed D0157: ask what is WIDER than they meant, never whether the set is good, because the second question invites assent. Six clauses were flagged by me as reaching past the evidence, and two priorities were flagged as mine rather than theirs. The human replied, in full: 'proceed.' That is an instruction to act. It is not a statement about any of the fourteen Need texts, any of the six flagged clauses, or any of the fourteen priorities I assigned. Nothing in it indicates the statements were read.";
        :>> decision = "Two clauses, and the second matters more than the first. CLAUSE A - APPLY THE CUTS. The six flagged clauses are removed and one priority is corrected, on my own authority as their author: nTurnStartRecall - 'within a declared budget and a declared latency cap' removed, and the cap-specific failure sentence generalised to 'retrieval that cannot complete says so and pushes nothing, rather than silently degrading the turn'. The honesty property survives; the implementation's measured numbers stop being constitutional. nForeignTreeVerification - the adopted/not-adopted TEST PROCEDURE removed. The D0136 outcome property it rested on is kept in outcome form: a project that has not adopted a control is in a legitimate state and is never reported as violating it. nPassDisclosesItsSource - 'Assurance is reported by judge kind rather than as one number' removed. That is a reporting FORMAT; the outcome is disclosure. nAuthoringCostsLessThanTheAlternative - the universal comparative removed and the Need RENAMED to nAuthoringIsLowFriction, because the old name asserted the clause that was cut. The concrete half survives: engine-supplied identity and dates, generated scaffolding, tooling over remembering. nDocSurfaceCannotOutliveTheChange - 'or to remove it in favour of the computed one' removed. Correcting an invalidated claim stands; mandating deletion does not. nWorkingMaterialTravels - the OPACITY sentence removed. It was mine, inserted on the engine-versus-deliverable invariant, and the human never asked for it. nRepoHoldsSeveralProjects - priority raised from should to must, because the engine pin depends on it: one repository means one checkout means one binary, so a workspace with disagreeing declarations makes the gate incoherent. CLAUSE B - THIS IS NOT THE ACCEPTANCE. No method=confirmation TestResult is recorded against the Need set, and the Business-to-Architecture gate stays CLOSED. No SystemRequirement is derived from any of the fourteen until a human attests to the set itself.";
        :>> rationale = "WHY THE CUTS NEED NO SIGNATURE. Every one narrows text I wrote, in the direction I had already argued was correct, and each was flagged BY ME as reaching past its evidence. Narrowing my own over-reach reduces what the model claims; it cannot manufacture a commitment the human did not make. Leaving six clauses I believe are wrong standing in a must-priority Need, while waiting for a reply that may not come, is the worse failure - D0157's lesson is that a wide Need gets decomposed by a later reader into work nobody asked for. Re-adding any clause costs one Decision, which is cheap and visible. WHY 'proceed.' CANNOT BE THE ACCEPTANCE, which is the whole point of this record. A method=confirmation result asserts that a HUMAN judged a specific claim. The claim here is 'these fourteen statements say what I meant, at these priorities'. 'proceed.' asserts none of that; it is consistent with the human never having opened the document. Recording it as acceptance would produce a passing attestation whose content nobody ever affirmed - the exact defect guard confirmation-authenticity exists to catch, and the class issue072/issue073 were raised for. An AI actor cannot supply human acceptance, and inferring it from an instruction to continue is precisely the inference the rule forbids. WHY THE GATE IS NOT MERELY MY CAUTION. The business-architecture skill states the ordering as non-negotiable: needs are upstream of architecture, and a SystemRequirement may not be RECORDED until the Needs it serves exist AND are accepted. Recording architecture before needs is the named issue054 defect. Deriving requirements now on a general 'proceed' would repeat it while holding a signed-looking record that no one signed. WHAT IS NOT BLOCKED, and is where the work goes instead: the latent-need derivation process is a process definition, not architecture, and the two portability defects found in the unit manifest need a resolver story rather than an accepted Need. Both proceed. COST OF NOT DECIDING. The six clauses stay in the model as must-priority direction while the reply is pending, and every reader between now and then treats them as agreed.";
        :>> consequences = "The Need set is narrower and the fourteen count is unchanged. nAuthoringCostsLessThanTheAlternative no longer resolves as a name: it is nAuthoringIsLowFriction, and its #DerivedFrom and #Implicates edges are updated in the same act, so no edge dangles. The Need tier stays at 14 gaps and 80 percent. Nothing in this Decision authors a requirement, and the fall recorded in sprint 483 is unaffected. KEEL-ND-0001 v0.1 now describes six clauses that no longer exist in the model. It is a rendered view, not a source, so it is superseded rather than edited - a fresh render is cheap and a stale one must not be mistaken for current. THE ACCEPTANCE REMAINS OUTSTANDING and is the single item blocking Phase 2. It is discharged by a human statement about the SET - that the fourteen say what they meant, or which further ones are still too wide - and by nothing else.";
    }

    // acceptance event (D0121 review-queue sign-off; D0066/D0106 — human-judged, not fabricated)
    verification d0248Accept : Test { :>> id = "ba159d8c-7dd9-49bc-8227-cc90dcab8c3a"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0248AcceptR1 : TestResult { :>> id = "51924417-8093-465a-b3a5-613375e79a66"; :>> outcome = VerdictKind::pass; :>> judgedAgainst = "32149b5"; :>> judgedAt = "2026-08-29"; :>> judgedBy = "wweatherholtz"; }
}
