// D0223 (status: the `status` field below is the truth) — decisionAuthoringIsCore: the five guards that police how a Decision is recorded can no longer be switched off
// Recorded via `keel record decision` (D0105 RMWX axis; issue054). Acceptance is a separate explicit
// human gate (method=confirmation, D0106): flip status + add the d0223Accept event on sign-off.
package ReferenceDecision0223 {
    private import EngineElement::*;
    private import EngineWork::*;
    private import EngineVerification::*;
    private import EngineRelationships::*;

    // #ProspectiveChange (D0070) - this Decision governs a process/schema change; the co-committed
    // change rides the process-change guard's hard lock.
    #ProspectiveChange part d0223 : Decision {
        :>> id = "b9e5ad68-0d60-4983-aec4-ed8f64ccecbb";
        :>> title = "decisionAuthoringIsCore: the five guards that police how a Decision is recorded can no longer be switched off";
        :>> createdAt = "2026-08-24";
        :>> createdBy = "claudeFable5";
        :>> status = DecisionStatus::accepted;
        :>> context = "The human said they were fine with the process for 'defining and cementing processes' being undisable-able and shipped with the software, and asked whether that was what we were discussing. It was NOT: process-change - the keystone requiring a signed Decision to alter a process definition or the enforcement surface - has been a CORE never-deactivatable guard all along, and change-request is a workflow outside the activation model entirely, so both halves of their sentence were already true; what I had actually been reporting was a PACKAGING defect where a unit's files could not travel. Saying so rather than accepting the premise turned up the real gap next door. decision-authoring - the process by which a Decision is authored, which is HOW a process gets cemented in this engine - claimed five guards, and a guard is core precisely when NO unit claims it (activation::guard_state). Claiming made them switchable, so 'keel deactivate decision-authoring' switched off decisionRationale, acceptanceEvents, decisionRequirementLink, attestationSubstance AND confirmationAuthenticity - the guard that stops an AI recording a human acceptance THAT NEVER HAPPENED. That put the monitor-modifiable-by-monitored gap (issue236/D0208) on the most attestation-sensitive path in the engine, where the failure mode is a fabricated human judgment that CLAUDE.md section 4 says must never be possible.";
        :>> decision = "decision-authoring asserts NO guard. Its five guards therefore become CORE - unclaimed, hence never deactivatable - and the process definition carries a comment saying why, including the explicit instruction not to re-add an assert (which would convert them back to switchable, the issue242 capture read forwards, and which audit-adherence now gates). Because core-ness is the ABSENCE of a claim rather than a list, it is also strictly more PORTABLE: an adopting project gets all five enforced with no activation step, because nothing there claims them either. The process -> guard link is still recorded, as 'core = [...]' in process-enforcement.toml, and 'keel hardening' counts core guards as enforced.";
        :>> rationale = "Defining and cementing a Decision is not an opt-in discipline - it is how this engine records that a human agreed to something, and the one place where the failure mode is fabricated consent rather than incomplete work. D0098 permits gating HONESTY unconditionally even though it forbids gating completeness, and every one of these five is an honesty check. Making them core by removing claims, rather than by adding a special case in Rust, keeps the mechanism single: 'guard_state' already returns Core for an unclaimed guard, so this is the existing rule applied rather than a new exception. The hardening declaration was necessary because otherwise a core-enforced process reports 'guards: 0' and falls into UNDECLARED - reading as 'not enforced' when the truth is the opposite, which is the honest-surface class this session has been closing all day.";
        :>> consequences = "STATED PLAINLY, because it is the real cost: a downstream project can no longer opt out of Decision-authoring discipline even if it wants a lighter process. That is the intended trade and the human directed it. Verified: all five read CORE in 'keel activation'; 'keel deactivate decision-authoring' now REFUSES with the accurate message, including the warning not to add an assert; hardening moved decisionAuthoring from undeclared to enforced (15 -> 16, accountedPct 89); audit-adherence sees Active -> Core as a STRENGTHENING (rank 2 -> 3) and does not flag it, which is the correct direction; process audit still reports every unit travels whole; 260 + 9 + 1 tests pass across every target; validate + all 49 guards + check-engine + rules green. Resolves issue254.";
    }

    // acceptance event (D0121 review-queue sign-off; D0066/D0106 — human-judged, not fabricated)
    verification d0223Accept : Test { :>> id = "4fc7183b-5aa0-4bb2-8f0d-3aacaafe3055"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/21."; }
    part d0223AcceptR1 : TestResult { :>> id = "bfc1a0d4-7109-4a55-8d5f-858bfabe2f6f"; :>> outcome = VerdictKind::pass; :>> judgedAgainst = "016cada"; :>> judgedAt = "2026-08-24"; :>> judgedBy = "wweatherholtz"; }
}
