// D0286 (status: the `status` field below is the truth) — An empty population is 0 percent and NOTHING TO ASSURE - never a vacuous 100 percent or READY - in every ratio and verdict keel computes
// Recorded via `keel record decision` (D0105 RMWX axis; issue054). Acceptance is a separate explicit
// human gate (method=confirmation, D0106): flip status + add the d0286Accept event on sign-off.
package ReferenceDecision0286 {
    private import EngineElement::*;
    private import EngineWork::*;
    private import EngineVerification::*;
    private import EngineRelationships::*;

    part d0286 : Decision {
        :>> id = "4da13f4d-0ca5-4449-b9e6-da2ad0de6d3a";
        :>> title = "An empty population is 0 percent and NOTHING TO ASSURE - never a vacuous 100 percent or READY - in every ratio and verdict keel computes";
        :>> createdAt = "2026-09-03";
        :>> createdBy = "claudeOpus5";
        :>> status = DecisionStatus::accepted;
        :>> context = "The human (st071): projects inheriting keel get a clean sweep of 100 percent when 0/0 should be 0 percent to indicate that nothing is done yet. Reproduced on a fresh keel init scaffold: report assurance showed Verification coverage 100 percent, Critique coverage 100 percent, Acceptance integrity 100 percent and Assurance readiness READY; keel show tier-satisfaction reported pct 100 for every empty tier; keel assured returned ready true. Four sites chose full for an empty denominator - reports.rs pct (map_or(100)), verification.rs pct (None => 100), tier-satisfaction's missing-tier default (t.map_or(100, ...)), and ReadinessBlockers::ready, which is 'every blocker list empty' and is therefore vacuously true over nothing - and one unit test pinned the behaviour as 'nothing to measure = vacuously complete'. hardening.rs already did it right (an empty population has no percentage, with a stated reason), so the crate held both conventions at once.";
        :>> decision = "A ratio over an empty population is 0. Every pct helper in the crate returns 0 when the denominator is 0; the tier-satisfaction default for a missing tier is 0; the pinned test is inverted with its reason. Readiness requires a non-empty governed population: ReadinessBlockers carries the governed count, ready() is false when it is 0, and the verdict is three-valued - NOTHING TO ASSURE, READY, NOT READY - so an empty project is named for what it is rather than lumped with a failing one. keel assured emits verdict and governed beside ready. Report cards over a ratio carry a fourth tone, empty, rendered neutral grey in the console and the report template, so a fresh project reads 'nothing yet' rather than red or green. THE CONTROL: a source-scan test refuses any division in the crate whose fallback is 100 - the three sites fixed were three files with three spellings of one mistake, and the fourth would have been a fourth spelling.";
        :>> rationale = "WHY 0 AND NOT NULL: the human asked for 0 to indicate that nothing is done yet; the JSON contract for pct fields is an integer that the console renders, and a null would have broken every consumer for the sake of a distinction the tone now carries. Where a percentage is a claim about a population (hardening's coverage rows), None with a reason stays right - that lens says 'nothing dispatched was found', which is a different statement from 'nothing done'. WHY A THIRD VERDICT: READY over nothing is the clean-sweep defect; NOT READY over nothing is merely misleading in the other direction - a fresh project has not failed anything. Naming the empty case is what lets a reader distinguish a project that has done nothing from one that has done things badly. WHY A SOURCE SCAN AS THE CONTROL: the four sites shared no helper - each author reached for the convention that felt natural (vacuous truth) and each was locally defensible; only a scan over the whole crate catches the next one, and the scan found a fifth instance during this sprint (verification.rs's overflow arm) that the reading had missed. WHAT DID NOT CHANGE: this repository's own verdicts. NOT READY with 379 governed before and after; percentages over non-empty populations are identical; only the empty case moved.";
        :>> consequences = "A project that inherits keel opens on 0 percent, empty-toned cards and NOTHING TO ASSURE, and earns its green. The empty-population convention is now one convention, enforced: a new ratio that defaults to 100 fails the build. hardening's None-with-reason remains for population claims. Downstream projects receive this with the next engine vintage; their historical snapshots of 100 percent were never facts, so nothing is migrated. REMOVAL PATH (D0163): revert the four defaults and delete the scan test together; the verdict word and the empty tone can stay, since they are additive.";
    }

    // acceptance event (D0121 review-queue sign-off; D0066/D0106 — human-judged, not fabricated)
    verification d0286Accept : Test { :>> id = "b4536362-5e06-46f5-bf0d-269947824f32"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0286AcceptR1 : TestResult { :>> id = "39be4c65-6663-4bf7-94e7-c8fc71a0ff97"; :>> outcome = VerdictKind::pass; :>> judgedAgainst = "a88ae5b"; :>> judgedAt = "2026-09-03"; :>> judgedBy = "wweatherholtz"; }
}
