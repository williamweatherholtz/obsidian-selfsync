// =====================================================================
// D0056 — formal-viewpoints: critique of our view layer vs ISO 42010 / Arcadia /
// SysML v2; verdict — by the frameworks' OWN discriminator (reuse x auditability x
// audience) our case clears the bar, so formalizing viewpoints is justified (not
// gold-plating). Direction accepted; the frozen-schema execution awaits sign-off.
// Recorded 2026-06-16 by wweatherholtz (research/critique; "dig in, don't placate").
// =====================================================================
package ReferenceDecision0056 {
    private import EngineElement::*;
    private import EngineWork::*;
    private import EngineVerification::*;

    part d0056 : Decision {
        :>> id = "50617283-3940-4a51-876f-1324a5b6c7ea";
        :>> title = "D0056: formalize viewpoints (ISO 42010 / Arcadia / SysML v2) — justified by reuse x auditability x audience; execution awaits schema sign-off";
        :>> createdAt = "2026-06-16";
        :>> createdBy = "wweatherholtz";
        :>> status = DecisionStatus::accepted;
        :>> context = "Deep-dive research into the viewpoint mechanism (ISO/IEC/IEEE 42010, Arcadia/Capella+Kitalpha, SysML v2 view/viewpoint/expose/render). WHY these exist: 42010 forces every stakeholder CONCERN to be framed by a viewpoint -> checkable concern coverage (no orphan concerns) + inter-view consistency (correspondence rules); a viewpoint is a reusable LENS (class), a view its application (instance). Arcadia (Voirin/Thales) adds (a) need-vs-solution layering (OA/SA=problem, LA/PA=solution) to keep 'are we solving the right problem' separate+traceable and prevent premature solutioning, and (b) cross-cutting concern viewpoints (mass/cost/perf/safety) computed across layers. SysML v2 makes views COMPUTED (expose=query, render=present) and viewpoint-declared (frame concerns/stakeholders). The research's honest DISCRIMINATOR for when formal viewpoints earn their keep: reuse x auditability x audience-count — high => formalize; one-off single-author => ad-hoc query is cheaper and the ceremony is unchecked bureaucracy. OUR STATE: view def OutstandingView/SuspectView/TraceView + viewpoint def MaintainerVP in computed.sysml are EMPTY STUBS, disconnected from the actual views which are hardcoded report.py tabs + orient/whats-next — no declared concern, stakeholder, or source; cannot audit concern coverage.";
        :>> decision = "VERDICT (not placation): formal viewpoints are justified here. ADOPT (lightweight): make Viewpoint + View first-class DECLARED elements — a Viewpoint declares {concern, stakeholder/audience, source elements+edges it draws from, renderer binding}; a View is its computed application (#View, regenerable). Convert the existing code-views (whats-next, traceability, safety, requirements, decisions, baselines, orient) into DECLARED viewpoints; keep the Rust/Python as the RENDERER but DRIVEN BY the declaration, so adding a view = declaring a viewpoint, and the model can audit which stakeholder concerns have a view (no orphans).";
        :>> rationale = "By the frameworks' own discriminator our case CLEARS the bar — the engine is REUSABLE across downstream projects, has AUDITABLE/regulated concerns (safety/STPA, verification coverage), and serves MULTIPLE AUDIENCES (maintainer, safety, PM, downstream adopter); so formal viewpoints are justified here, unlike a one-off model. NON-ADOPTIONS (honest pushback): (1) NOT Capella/Kitalpha — heavy metamodel-extension tooling with documented adoption friction (Obeo survey); friction is our #1 risk (D0054), so viewpoints must be text-light + computed, not a framework. (2) NOT Arcadia's literal OA/SA/LA/PA layers — those model a DELIVERABLE system's architecture; our system-of-interest is the work/process (D0055), so the need-vs-solution CONCEPT transfers (Business=need, Architecture=solution, satisfy edges) but the four specific layers do not. (3) 42010 correspondence-rules/model-kinds are OPTIONAL — adopt the viewpoint-declaration core; add correspondence rules only where audit demands. GAPS (filed issue018): views are code not modeled (orphan-concern risk); no cross-cutting safety/perf/security viewpoints as declared lenses; the view def anchors are disconnected stubs. EXECUTION: formalViewpoints is a frozen-schema change (new Viewpoint/View schema + report.py/orient as declaration-driven renderers) -> needs explicit human sign-off per §2.5 (like trackedMetadata) before build; surfaced, not auto-run.";
        :>> consequences = "Direction accepted; the schema change is gated on a §2.5 sign-off (formalViewpoints backlog item carries a sign-off DoD, surfaced not auto-run per D0052). When built: views become declared, auditable, extensible-by-declaration; concern-coverage becomes a computable view itself (which concerns lack a viewpoint). Keep it lightweight to honor D0054 (friction). Reaffirms D0055 (engine is systems modeling of the work/process). Sources: ISO 42010 conceptual model; Arcadia (Voirin/ISTE, mbse-capella); Kitalpha; SysML v2 view/viewpoint/expose/render; Obeo Capella adoption survey 2022.";
    }

    verification d0056Accept : Test { :>> id = "44115fd2-3323-4593-a33c-1f7039a65c57"; :>> method = VerificationMethod::confirmation; :>> procedureText = "wweatherholtz attests acceptance of decision d0056 (D0066 acceptance-events migration, attested 2026-06-17); prior record: status=accepted + file prose."; }
    part d0056AcceptR1 : TestResult { :>> id = "62c574ac-de7e-461e-9786-495effedfda4"; :>> outcome = VerdictKind::pass; :>> judgedAgainst = "e146621"; :>> judgedAt = "2026-06-17"; :>> judgedBy = "wweatherholtz"; }
}
