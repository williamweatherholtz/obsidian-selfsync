// D0402 (status: the `status` field below is the truth) — exhibitsAreMeasuredBeforePublish: a brief's exhibits are measured in a browser before the page can exist, and a page whose text does not fit is removed, not published
// Recorded via `keel record decision` (D0105 RMWX axis; issue054). Acceptance is a separate explicit
// human gate (method=confirmation, D0106): flip status + add the d0402Accept event on sign-off.
package ReferenceDecision0402 {
    private import EngineElement::*;
    private import EngineWork::*;
    private import EngineVerification::*;
    private import EngineRelationships::*;

    part d0402 : Decision {
        :>> id = "7ff11b9e-2ea3-4ebc-b96d-aa52da8a89ee";
        :>> title = "exhibitsAreMeasuredBeforePublish: a brief's exhibits are measured in a browser before the page can exist, and a page whose text does not fit is removed, not published";
        :>> createdAt = "2026-09-09";
        :>> createdBy = "claudeOpus5";
        :>> status = DecisionStatus::accepted;
        :>> context = "issue390: two exhibit builders lost text without saying so - a stacked legend spaced its entries evenly so a long label overprinted its neighbour, and a logic exhibit's note was one SVG text element that the canvas edge cut mid-word. SVG neither wraps nor clips visibly, so a figure built from correct facts can still tell the reader something false by hiding half of itself. The builders were fixed in the shared modules; what remained open was that nothing CHECKED a rendered exhibit fits. A length-estimate check written during that fix reported five false positives on right-anchored labels, because an estimate does not know where the browser puts the glyphs. The dcExhibitsDoNotHideText DoD asked for that check's cost to be weighed against the failure it catches and the choice recorded. Measured on the standing brief at 29fb76c: with a 2px tolerance for glyph side bearings at the canvas edge, one real finding - a box title 7px past its box on the fallback typeface - on a page whose screenshot had been read and passed the same morning. NOT A FORK: the DoD delegated this choice to the resolver, and the one other shape it named was already measured worse than nothing in issue390.";
        :>> decision = "A published brief's exhibits are MEASURED, not estimated. scripts/exec_brief/fit_check.py loads the page in headless Chromium and reads every SVG text element's rendered box: a box that crosses its viewBox by more than 2px, two boxes that intersect by more than 2px each way, a text that starts inside a drawn box and ends past it, or a page that scrolls horizontally is a finding, and every finding names the figure, the kind, the pixels and the text. It measures twice, with the page's web fonts and with them blocked, because a host that cannot reach fonts.gstatic.com is a real reader and the fallback face is wider. Its four known cases - overflow, overlap, overrun, and a fitting figure with a right-anchored label - run as --probe before any page is read (D0388). The enforcement point is the build: a builder ends in assert_fits(out_path), which probes, measures, and on any finding REMOVES the page and exits non-zero, so no page exists to publish unmeasured (the D0387 shape). The contract checker stays structural and browserless.";
        :>> rationale = "The guarantee these pages sell is that a figure cannot drift from the facts the way a hand-drawn one does; that guarantee covered the numbers and stopped at the layout, and the layout defect is the worse one because a truncation looks finished. The browser is the only instrument that knows where a glyph lands, and a headless one is already installed on the host that builds every brief. The cost weighed: the check adds about twelve seconds to a build that runs once per queue change (measured: probe 9.3 s, page 3.0 s), and one Python dependency the host already has; CI does not carry a browser, so this script carries no ci-probe marker and CI does not run its probe - the build does, before every page, which is where the page is made. Adding a browser to CI would be a workflow change waiting on the human for a probe of a page that only ever exists on this host; that cost was not taken.";
        :>> consequences = "Every future builder imports assert_fits and ends in it; the decision-surfacing skill's step 5 names the measurement beside the contract check. The current brief was rebuilt under the check and republished at the same URL with its one finding fixed. dcExhibitsDoNotHideText is delivered by sprint 628. If CI ever carries a browser, the ci-probe marker is one line and a Decision.";
    }

    // acceptance event (D0121 review-queue sign-off; D0066/D0106 — human-judged, not fabricated)
    verification d0402Accept : Test { :>> id = "1eb39b41-0bf3-463a-9bc4-1126f789377f"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0402AcceptR1 : TestResult { :>> id = "2439602a-abaf-4c68-9753-5e89769ad671"; :>> outcome = VerdictKind::pass; :>> judgedAgainst = "a651fb3"; :>> judgedAt = "2026-09-09"; :>> judgedBy = "wweatherholtz"; :>> createdBy = "claudeOpus5"; }
}
