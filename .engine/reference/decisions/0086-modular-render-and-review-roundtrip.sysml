// =====================================================================
// D0086 — generalize the one-off diagram into a MODULAR `sysmlv2 render <view> --mode graph|table|
// review` interactive-artifact generator over the view layer, and add `sysmlv2 apply-review` — a
// human-review ROUND-TRIP where the human acts as an independent critic: review input enters as NEW
// LINKED critique/test items that attest the element's state, INDUCE SUSPICION on a finding, and
// induce new implementation when actionable. JSON is transport; .tracking stays truth.
// #ProspectiveChange: introduces process-defs + changes what `suspect` means (keystone, D0070).
// Accepted 2026-06-21.
// =====================================================================
package ReferenceDecision0086 {
    private import EngineElement::*;
    private import EngineWork::*;
    private import EngineVerification::*;
    private import EngineRelationships::*;

    #ProspectiveChange part d0086 : Decision {
        :>> id = "63940516-2c7d-4e8f-a086-5162738496d0";
        :>> title = "D0086: modular `sysmlv2 render <view> --mode graph|table|review` over the view layer + `apply-review` round-trip (human review = independent critique entering as new linked items that attest state, induce suspicion, and induce implementation)";
        :>> createdAt = "2026-06-21";
        :>> createdBy = "wweatherholtz";
        :>> status = DecisionStatus::accepted;
        :>> context = "After the traceability diagram (D0085) the human asked three things: (1) make MORE of the artifact toggleable; (2) 'make a process to create this kind of artifact from an arbitrary view, making it modular' — i.e. generalize the one-off diagram into a renderer over ANY declared view; and (3) recreate a reviewing tool they had built and loved — accept/reject + rationale per item, exporting critique sitewide via JSON. On HOW a disposition writes back, the human specified the engine-native shape directly: 'apply-review signifies a critique or downstream test result; user input should enter as new linked items and attest to the item state and induce suspicion and new implementation if relevant (from the critique)'. The view layer already emits JSON (TOML views -> tabular rows; the Model -> typed nodes+edges; computed subcommands -> structured JSON) and viewpoints already DECLARE views (D0056/D0057) — so an interactive artifact is just a RENDERING of a view, and the diagram is one hard-wired instance of it.";
        :>> decision = "Generalize the diagram into a MODULAR renderer and add a review round-trip. (A) `sysmlv2 render <view> --mode graph|table|review [--out FILE] [ROOT]`: graph = the Model (whole, or scoped to a view's selection) as the interactive cytoscape page (D0085's diagram becomes the `render --mode graph` whole-model preset); table = any declared TOML view's rows as a sortable/filterable/searchable table; review = that table plus per-row capture (verdict accept|finding|accept-risk + rationale + lens + severity + an 'actionable?' flag) and an in-page Export-JSON button (client-side download, no server). Every node type AND edge kind is a toggle; the dense derived edges (contains/resultof) default OFF. (B) `sysmlv2 apply-review <batch.json>`: ingests the exported batch and, PER ENTRY, writes via the sanctioned write path (UUID + append-only, write.rs) a NEW LINKED verification result attesting the reviewed element's state — the human is an INDEPENDENT critic (human != the element's AI author, D0080): a `verification <e>HumanReview : Test { method = critique (or test for a downstream result); lens; critiquedBy = human; severity (when a finding); procedureText = <rationale> }` + its `TestResult` (outcome pass = accept | fail = finding; judgedBy = the human; judgedAt; judgedAgainst = commit) + `#Verify dependency from <e>HumanReview to <e>`. On a FINDING (fail): also author an `Issue` carrying the severity, and — when the entry is flagged actionable — create a resolving action (add_task) + `#Resolves dependency from <action> to <issue>` so the fix is tracked and the Issue auto-resolves once that action is done (D0077/D0078). (C) INDUCE SUSPICION (a change to the meaning of a computed view): an element is COMPUTED suspect when it carries an unresolved failing critique (a critique TestResult outcome=fail whose finding Issue is not yet resolved) — surfaced by `sysmlv2 suspect`/`orient`; nothing is stored, suspicion falls out of the authored critique + open Issue (compute-don't-store, §2.1/D0084). (D) Engine-native wrapping: a `render` process-def (regenerate-don't-commit) generalizing diagram.sysml + a deploying render skill (D0059) + a generalized 'render' viewpoint entry; the diagram process/skill/viewpoint are subsumed as the graph preset (D0085 generalized, not retired); generated /*.html stays git-ignored; doc-sync rides the change.";
        :>> rationale = "Modularity: a viewpoint already DECLARES a view (D0056/D0057); an interactive artifact is just a rendering of one — so ONE renderer over the view layer (graph for item+edge sets, table for tabular views, review for capture) replaces N bespoke per-view tools and makes every declared view explorable. Review-as-critique is the engine-native realization of the human's directive: a human reviewing an element IS an independent critic (D0080), so the judgment must enter as a first-class, defensible, lens-tagged verification LINKED to the element (not a mutation of it, not a parallel JSON store) — which then drives the existing machinery: a finding spawns an Issue (severity-carrying), INDUCES SUSPICION (the element computes suspect until the finding is resolved — exactly 'attest state + induce suspicion'), and INDUCES IMPLEMENTATION when actionable (a tracked resolving action, 'new implementation if relevant'). The round-trip keeps text-as-truth (the exported JSON is TRANSPORT; .tracking is the only source of truth, §2.1/D0018) and is the friction win for the one human gate we have (D0049/D0054) — reviewing in a fast HTML surface and writing back via the write API beats hand-editing .sysml. ALTERNATIVES: (A) confirmation-only attestation per element — REJECTED: captures the judgment but does NOT induce suspicion or implementation, and treats a human review as a passive sign-off rather than an active critique (the human's directive explicitly wanted suspicion + implementation); (B) keep the review JSON as the deliverable (the human's old standalone tool) — REJECTED: the JSON would be a parallel store of truth that drifts (§2.1); (C) separate per-view CLI renderers (one subcommand each) — REJECTED: not modular, the exact thing the human asked to avoid; (D CHOSEN) one modular `render` + critique-shaped `apply-review` round-trip. CRITERIA: modular-over-the-view-layer x review-is-an-independent-critique x induces-suspicion-and-implementation x compute-don't-store x no-parallel-truth-store.";
        :>> consequences = "New subcommands: `render` (view.rs render_html generalizing diagram_html: graph/table/review modes; reuses Model + view::run; inlined cytoscape for graph) and `apply-review` (parses the batch JSON, writes new linked critique/test verifications + results + #Verify edges, plus Issue/action/#Resolves on actionable findings — all through the write.rs UUID/append-only path; a new write primitive for an independent verification + result + #Verify, reused by apply-review). `suspect`/`orient` EXTENDED: an element with an unresolved failing critique computes suspect (new computed clause + tests; the meaning-of-a-view change that makes this a CHANGE). New `render` process-def (.engine/processes/render.sysml, regenerate-don't-commit) + render skill (.engine/skills/render) + skills-registry entry + generalized 'render' viewpoint (the diagram becomes the graph preset; D0085 subsumed, not retired). .gitignore keeps ignoring generated /*.html. #ProspectiveChange marks the keystone co-commit (D0070). doc-sync: usage.md + CLAUDE.md view list. Pairs with D0085 (diagram, generalized), D0080 (critique mechanism), D0084/D0050 (suspicion), D0077/D0078 (issue resolution loop), D0056/D0057 (viewpoints), D0059 (deploying skill), D0049/D0054 (the human gate + friction), D0001/D0018 (compute-don't-store).";
    }

    verification d0086Accept : Test {
        :>> id = "63940516-2c7d-4e8f-a086-5162738496d1";
        :>> method = VerificationMethod::confirmation;
        :>> procedureText = "wweatherholtz attests acceptance of d0086 (modular `sysmlv2 render <view> --mode graph|table|review` over the view layer + `apply-review` round-trip where human review enters as new linked independent-critique/test items that attest state, induce suspicion on a finding, and induce implementation when actionable) by directing on 2026-06-21: 'can we make a process to create this kind of artifact from an arbitrary view? making it modular?' and 'I made a tool last week that allowed acceptance/rejected, along with rationale, then exporting critique site wide via JSON ... made for a wonderful reviewing tool', selecting 'All at once' scope + 'Round-trip to authored facts', and specifying the write-back: 'apply-review signifies a critique or downstream test results. user input should enter as new linked items and attest to the item state and induce suspicion and new implementation if relevant (from the critique)'.";
    }
    part d0086AcceptR1 : TestResult {
        :>> id = "63940516-2c7d-4e8f-a086-5162738496d2";
        :>> outcome = VerdictKind::pass;
        :>> judgedAgainst = "fdaa84c";
        :>> judgedAt = "2026-06-21";
        :>> judgedBy = "wweatherholtz";
    }
}
