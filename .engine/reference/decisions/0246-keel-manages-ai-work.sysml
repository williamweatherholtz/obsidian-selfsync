// D0246 (status: the `status` field below is the truth) — keel's subject is AI work management, and the Need set is re-derived from the code to say so
// Recorded via `keel record decision` (D0105 RMWX axis; issue054). Acceptance is a separate explicit
// human gate (method=confirmation, D0106): flip status + add the d0246Accept event on sign-off.
package ReferenceDecision0246 {
    private import EngineElement::*;
    private import EngineWork::*;
    private import EngineVerification::*;
    private import EngineRelationships::*;

    // #ProspectiveChange (D0070) - this Decision governs a process/schema change; the co-committed
    // change rides the process-change guard's hard lock.
    #ProspectiveChange part d0246 : Decision {
        :>> id = "9ef3101a-490b-4496-892e-671428cb96bc";
        :>> title = "keel's subject is AI work management, and the Need set is re-derived from the code to say so";
        :>> createdAt = "2026-08-28";
        :>> createdBy = "claudeOpus5";
        :>> status = DecisionStatus::accepted;
        :>> context = "An independent bottom-up pass derived keel's capabilities from the artifacts alone - 41,203 LOC across keel-parser and keel-cli, the 89-entry CLI help surface, 52 guards, 6 hook events, 50 /api routes in serve.rs, 25 processes, 38 skills, 16 contract files, 4 schema packages and 4 CI workflows - and then diffed that against the 64 authored Needs. Three findings, each computed rather than asserted. FIRST, the Need set is inverted relative to the code. keel rootedness reports 53 of 482 delivery stories rooted in a Need and 415 chartered by a Decision that reaches no Need - 86 percent ungrounded. keel tier-satisfaction reports Need to SystemRequirement at 100 percent and SystemRequirement to Test at 100 percent, but that perfection is an artifact of only ever authoring requirements UNDER existing Needs; the reverse direction is the honest one. Half the live Needs describe viewing surfaces (19 nViewer, 5 nConsole, 5 nServe, plus n15 to n17 of 64), while the enforcement engine that is roughly 55 percent of the code carries about eight Needs. SECOND, twelve capabilities have schema, a write path or a command, a process, and a guard or contract behind them, and no Need statement mentions any of them. A keyword scan across all 64 statements returns zero for intake and verbatim elicitation, zero for migration and version skew, zero for a foreign or downstream tree, zero for friction, zero for promise and follow-through, and one incidental hit each for indicator and recall. THIRD, 19 nViewer Needs describe a deliverable built in a sibling repository, not this one. The human's verdict on the pass, recorded verbatim as st023 and translated as us028 and us029: the point of keel really is to manage AI work, the sysml part is just a means to an end, if a very defensible one; the difference between use cases and needs can be very thin, and these are more need statements than empirically-driven use cases; so sure, create them as needs. On the latent-need question they added that a use case for typing A and another for typing B could be consolidated into the need for having a keyboard, and that such a tight concise paring down of real functional needs is important.";
        :>> decision = "Adopt three clauses. CLAUSE A - SCOPE. keel's subject is the management of AI work. SysML v2 text representation is the MEANS by which that work is made auditable, not the end; it stays because it is defensible, not because it is the point. The projectBrief problem statement, which frames keel as a fix for engineering projects accumulating requirements in scattered prose documents, describes the substrate and not the subject, and is superseded by this clause as the statement of what keel is for. Scope questions - which Needs belong to this project, which belong to the sibling viewer repository - are settled against this clause. CLAUSE B - THE TWELVE NEEDS. Author as Needs the twelve capabilities the bottom-up pass found unstated: verbatim intake before interpretation; turn-start recall of the model's own facts; survival of engine evolution and a per-project engine pin; a repository holding several projects; verification against trees keel did not author; a pass that discloses what produced it; monitored-not-gated indicators; an accepted Decision's promises tracked to delivery; authoring friction as a first-class quality; the parser as the trusted computing base of every guard; a declared control distinguishable from an armed one; and a doc surface that cannot outlive the change that invalidated it. Each carries a #DerivedFrom edge to us029, so the set is attributable to the human's instruction rather than reading as unsourced authorial judgment (D0216). CLAUSE C - THIS IS NOT A LICENCE TO BACKFILL. Authoring these twelve does not retroactively root the 415 decision-chartered stories, and no story is to be re-parented to a new Need to move the rootedness number. The twelve are authored because the capabilities exist and their direction was never stated; the ungrounded ratio stays visible and becomes the computed trigger for the latent-need derivation process, authored separately.";
        :>> rationale = "WHY NEEDS RATHER THAN A BRIEF REWRITE. A Brief is one artifact and cannot be traced to; a Need is the tier requirements satisfy and tests verify. The human named the practical stake precisely: having a need stated directly is really just a source for requirements, so a missing one costs little in the moment, but latent needs left unstated weaken the direction of the program. Direction is exactly what the tier-satisfaction number cannot see - it measures whether requirements hang off Needs, never whether the Needs describe the system. WHY NOT USE CASES. The human considered and rejected the distinction: they are more need statements than empirically-driven use cases. Their word governs the type, and forcing them into use cases to satisfy a taxonomy would record my classification as theirs. WHY THE SCOPE CLAUSE COMES FIRST. Without it, the wrong Needs stay in this project by default. With it, the 19 nViewer Needs are visibly in the wrong repository and the twelve new ones are visibly in the right one, and both follow from a stated position rather than from a preference. WHY CLAUSE C. The failure mode this pass is most likely to cause is a contributor closing the 86 percent gap by re-parenting existing stories onto the new Needs. That would improve the metric while destroying its meaning - the same class of harm as issue088, where counting deliberately descoped work as an unmet obligation pointed a contributor at wrong work. An excluded item must not become an invisible one, and a real gap must not become a satisfied one by relabelling. COST OF NOT DECIDING. Twelve capabilities keep being maintained, guarded and shipped with nothing stating why they exist, and every future pass over the Need set re-derives the same finding from scratch - which is what happened here, and what the derivation process authored alongside this Decision exists to stop.";
        :>> consequences = "The twelve Needs enter .tracking/business/, each with a #DerivedFrom edge to us029 and none with a SystemRequirement yet - so keel tier-satisfaction's Need tier will DROP from 100 percent and report twelve gaps. That fall is the finding becoming visible, not a regression, and it must not be closed by authoring requirements that do not exist. keel coverage's Need tier gains twelve uncovered entries for the same reason. keel assured stays not-ready, as it already is. The projectBrief's problem statement is superseded as the statement of keel's subject by clause A; it is not deleted, since it remains an accurate description of the substrate. The 19 nViewer Needs are now visibly mis-homed. Moving them is a cross-repository migration and follows the migration process (D0067); it is NOT part of this Decision and no Need moves here. Nothing about STPA is settled here - that verdict is its own Decision.";
    }

    // acceptance event (D0121 review-queue sign-off; D0066/D0106 — human-judged, not fabricated)
    verification d0246Accept : Test { :>> id = "6271eb6d-4796-4859-9923-d2a18fca6ff8"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0246AcceptR1 : TestResult { :>> id = "1aae0ff5-578e-45c6-873d-da9ae5f41b0d"; :>> outcome = VerdictKind::pass; :>> judgedAgainst = "5c9e1b3"; :>> judgedAt = "2026-08-29"; :>> judgedBy = "wweatherholtz"; }
}
