// D0375 (status: the `status` field below is the truth) — consentBinding: how the human's chat words bind to the Decision they accept - an independent judge, the reply's referent, the signed plan, or the read-back as it stands
// Recorded via `keel record decision` (D0105 RMWX axis; issue054). Acceptance is a separate explicit
// human gate (method=confirmation, D0106): flip status + add the d0375Accept event on sign-off.
package ReferenceDecision0375 {
    private import EngineElement::*;
    private import EngineWork::*;
    private import EngineVerification::*;
    private import EngineRelationships::*;

    // RESEARCH: Counted in this tree 2026-09-08: 19 Decisions from d0337 onward with a human acceptance (judgedAt 0-2 days after createdAt) and 18 AUTO-ACCEPTED (scripts/exec_brief/facts.py, scopeDecisions* facts; an earlier hand count said 9 and was wrong); 198 issues classified by title keyword (scratch script issue_classes.py, textual and stated as approximate); the read-back's two refusals today reproduced against keel-cli/src/view/checks.rs quoted_spans - the apostrophe-then-letter rule at the span opener. Linear's agent guidance (checked 2026-09-07, docs/reviews/self-hosted-trackers-2026-09-07.md) has the same primitive - actor=app attribution - and no notion of binding a human's words to a record at all; nothing in the tools compared does. No prior art found for an isolated second-agent consent judge in an engineering tracker; the nearest is the two-person rule in change control, which C is the mechanical form of.
    // #SafetyChange (D0070) - this Decision governs a process/schema change; the co-committed
    // change rides the process-change guard's hard lock.
    #SafetyChange part d0375 : Decision {
        :>> id = "4aa4985d-ebc3-4c7f-8891-db583473caf3";
        :>> title = "consentBinding: how the human's chat words bind to the Decision they accept - an independent judge, the reply's referent, the signed plan, or the read-back as it stands";
        :>> createdAt = "2026-09-08";
        :>> createdBy = "claudeOpus5";
        :>> status = DecisionStatus::accepted;
        :>> context = "The human, 2026-09-08, after returning the brief with all eight asks marked: 'We're getting to the core of this repos trust-but-verify undergirding and I think you're fighting it a bit. It is true that I want to sign off on a lot of pressing issues, but denying work that I clearly approved because it's not 'signed' is self+defeating. Launch an independent agent to assess if a user(me) is giving consent via some text, else be less gatekeepy. The issues we've encountered have mostly been from poor process adherence and code quality, no? Not because my consent has been to easily interpreted.' What the tree says about that. No work was denied: all six ratified changes were built, committed and running before the signature; what waited was the RECORD of acceptance, and the page presented the six as asks. Since D0337 (2026-09-05, their words: consent is scoped to the processes it was promulgated under) nineteen Decisions have waited for their word, each zero to two days (mean 1.1), and eighteen auto-accepted under standing consent - D0337 is the source of the volume, not the read-back. The read-back rule (D0201 B / D0289) refused twice today, both times on MY framing: an apostrophe in 'brief's' opened the span before the real quote, so the words 'answers: d0360' were never read - issue397, tracked 2026-09-07, resolver dcQuotedWordsAreBounded at the head of the frontier. Of 198 issues, a keyword census over titles puts 73 in code and write paths, 34 in instruments reporting a wrong number, 18 in process adherence, 11 in enforcement bypass; 26 match consent words, of which nine are an acceptance recorded or kept that was not what was given (issue256 accepted with 13,136 characters of injected tool output in its context; issue373 a fork auto-accepting under standing consent; issue371 seventeen accepted texts edited after signature; issue341, 342, 347, 298, 238, 254) and eight are a control refusing or mis-framing a real acceptance (issue287, 359, 397, 223, 234, 383, 396, 217). Their claim is right by count and not by absence: the too-broad class exists and is the reason the quote must name the record.";
        :>> decision = "OPTION A (an independent consent judge, their proposal): `keel accept --judge` hands a fresh-context agent ONLY the human's verbatim message and the pending Decision's text, and it returns bound / not bound / ambiguous with the span it relied on; bound records the acceptance quoting that span, with the judge's verdict and the model that gave it as a companion receipt beside it; ambiguous asks the human one question naming the id. COST: an AI reads the human's intent, which is the class behind issue256 and issue373 - the judge's isolation makes it harder to lead, not impossible, and its context is a fixture the recording agent assembles; every chat acceptance costs a model call; a day to build, including a test in which a bare 'proceed' must come back not bound and one in which 'we can change schema. proceed' in reply to a message naming d0363 comes back bound. OPTION B (the reply's referent): the read-back accepts words given in direct reply to a proposal that named the Decision - the note quotes the human AND the proposal's sentence that named the id, and the referent is the question they answered. Mechanical, no second agent, re-readable. COST: the agent's own sentence becomes half the receipt, which is exactly what read_back_names says it never reads; nothing in the tree can verify that the quoted proposal was the message immediately before their reply; half a day. OPTION C (the signed plan covers its named steps): a safety-change or process-change Decision whose item is NAMED in the decision text of a Decision the human accepted THEMSELVES (not under standing consent) is covered by that acceptance and is recorded accepted at record time with the plan cited - the human signed once, on the plan, and its enumerated steps do not re-ask; standing consent still does not reach the enforcement surface, because the plan it flows through must carry a human's own signature. Fix issue397 alongside so a correct quote is never refused. COST: it would have covered none of today's eight, because D0367 itself auto-accepted - it pays out from the next plan the human signs, and only for steps the plan names; a guard and an accept path, a day. OPTION D (as it stands, plus the fix): keep D0337 and the read-back, fix issue397, and change the page so a shipped change is presented as a ratification with its reversal cost rather than as a choice (issue383, done on today's page). COST: nineteen signatures in three days continues at that rate for as long as the enforcement surface changes this often.";
        :>> rationale = "WHY NOT DECIDE THIS AUTONOMOUSLY: what counts as the human's consent is the one question an AI actor may not settle for itself (response contract section 4; D0129), and every option except D changes a control on the enforcement surface, which D0337 - their own words - keeps for them. WHAT I RECOMMEND, AND WHAT WOULD CHANGE IT: OPTION C, and A only for the residue C does not reach. C removes the friction they actually felt - six ratifications of work they had asked for - whenever the ask is signed once at the plan, keeps an AI out of reading their intent, and keeps D0337's line intact because the plan carries a human signature. A does what they asked in words, and its honest cost is that a model again decides what a human meant: nine issues in this tree are that reading going too wide, and the judge's isolation narrows the failure without removing it. If they say the friction is the point - that they want to be asked less even where no plan was signed - then A, with the ambiguous branch mandatory. If they say the count of nineteen is acceptable and the only fault was today's apostrophe, then D. B is on the list because it is the cheapest shape that matches their 'proceed' case; I do not recommend it, because it makes the agent's framing evidence, and the framing is the thing the human did not write. Their word decides; none of the four is applied until it does.";
        :>> consequences = "On A: a new `accept --judge` path and its two tests; the attestation policy gains a `judgeModel` line; the response contract's section 4 is amended to say an AI may bind but never supply an acceptance. On B: read_back_names gains a second span kind and the accept note format carries both quotes. On C: a `plan-covers-step` rule in the accept path and a guard that the covering plan's acceptance is a human's own (createdBy equals judgedBy, not the standing-consent token), plus the issue397 fix. On D: the issue397 fix alone. Until one is chosen the read-back stands as it is, and the brief carries this as its one ask.";
    }

    // acceptance event (D0121 review-queue sign-off; D0066/D0106 — human-judged, not fabricated)
    verification d0375Accept : Test { :>> id = "e241275f-9ab9-4fc3-827d-6fd7661dd39a"; :>> method = VerificationMethod::confirmation; :>> procedureText = "OPTION C chosen (the signed plan covers its named steps). chat, 2026-09-08, in reply to the brief and the fork as presented in this session - their words, verbatim: “c for d375”"; }
    part d0375AcceptR1 : TestResult { :>> id = "49941bd7-ea0e-4bda-a4f0-d35ecf6f0d81"; :>> outcome = VerdictKind::pass; :>> judgedAgainst = "7a61044"; :>> judgedAt = "2026-09-08"; :>> judgedBy = "wweatherholtz"; :>> createdBy = "claudeOpus5"; }
}
