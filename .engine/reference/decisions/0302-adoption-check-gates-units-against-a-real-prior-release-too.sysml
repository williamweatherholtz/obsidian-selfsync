// D0302 (status: the `status` field below is the truth) — adoption-check --vintage VERSION gates every unit against a second fixture scaffolded, imported into and gated by that prior RELEASE's binary, reported apart from the current fixture; and every enforced guard has its constraint-def identity
// Recorded via `keel record decision` (D0105 RMWX axis; issue054). Acceptance is a separate explicit
// human gate (method=confirmation, D0106): flip status + add the d0302Accept event on sign-off.
package ReferenceDecision0302 {
    private import EngineElement::*;
    private import EngineWork::*;
    private import EngineVerification::*;
    private import EngineRelationships::*;

    // #SafetyChange (D0070) - this Decision governs a process/schema change; the co-committed
    // change rides the process-change guard's hard lock.
    #SafetyChange part d0302 : Decision {
        :>> id = "4651aae3-017c-4e48-baf3-d811c6970aca";
        :>> title = "adoption-check --vintage VERSION gates every unit against a second fixture scaffolded, imported into and gated by that prior RELEASE's binary, reported apart from the current fixture; and every enforced guard has its constraint-def identity";
        :>> createdAt = "2026-09-04";
        :>> createdBy = "claudeOpus5";
        :>> status = DecisionStatus::accepted;
        :>> context = "issue265: adoption-check gates a FOREIGN tree, but its fixture is a current keel scaffold - keel adopting keel. Two real defects were verified invisible to it: issue263 (a unit asserting a constraint it does not carry, invisible because the current rules file defines the symbol) and issue259 (a control firing on a project that never adopted it, invisible because every fixture process already carries current conventions). Both showed only on penumbra, an older VINTAGE. Building the second fixture surfaced more: a v0.3.0 import does not sync the claude surface and that binary's drift guard then failed every imported unit (an engine-vintage behaviour, not the unit's); v0.2.3 has no process import at all, so no unit can be adopted onto it; the current fixture's rules file is embedded at build time so an incremental build ships a stale copy; and TWELVE enforced guards had no constraint-def identity although guard-constraints.sysml's own rule (D0195 clause 1) says every guard has one - eight of them older than guard 49 (issue370).";
        :>> decision = "(1) keel adoption-check gains --vintage VERSION. The vintage binary is obtained from the release origin - keelw's cache at .keel/bin/<version>/, else fetched with curl from the release download URL (KEELW_BASE_URL overrides), its version proved by running it - never synthesised, and never the current binary by fall-through: an unavailable vintage fails the check with the reason (KEEL_OFFLINE refuses to fetch). The vintage fixture is scaffolded by the OLD binary, each unit exported by THIS engine is stripped from and imported into it by the OLD binary, and both directions are gated by the OLD binary - the adopter on that vintage runs their own engine, not ours. Verdicts are reported as two tables, fixture: CURRENT and fixture: VINTAGE vX, never merged, and any failure in either fails the command. (2) Both loops run sync-claude between import and gate: it is the adopter's documented next command, and gating before it judged the engine's vintage rather than the unit. (3) The twelve guards without a constraint def get theirs in guard-constraints.sysml, so a unit's assert, the control map and the K8 capability handshake have an identity to bind to. (4) The failure tail keel_with reports prefers ERROR and FAIL lines over the last four lines, which for guard all were the passes that came after the failure.";
        :>> rationale = "WHY A REAL RELEASE AND NOT A SYNTHESISED OLD TREE: a synthesised vintage carries the author's guess about what was old; the release carries what adopters actually run, and the first run against it found a behaviour (no sync on import) no guess would have included. WHY THE OLD BINARY GATES: penumbra's gate was penumbra's binary; a vintage scaffold gated by the current binary would be the current fixture with older files, and D0251's pin would refuse it anyway. WHY REPORTED APART: a pass on the current fixture cannot stand in for the older one - that is the whole finding of issue265. WHY THE PROBE IS THE RECEIPT: a unit asserting unitExtrasPresent - defined in the current rules, absent from v0.3.0's engine - lands clean on the current fixture and is refused by the v0.3.0 import with the K8 message naming the guard; with the assert removed both are clean. That is the issue263 shape, made visible.";
        :>> consequences = "dcVintageFixture is delivered; issue265 resolves; issue370 (the twelve identities) is found and resolved here. A CI job may run --vintage against the previous release once the fetch cost is accepted there; it is not wired now. Units cannot be adopted onto v0.2.3 (no importer) and the check says so per unit rather than passing over it. The stale-embed finding is a build hygiene fact recorded in the sprint, not an item: `touch keel-cli/src/main.rs` after editing anything include_dir embeds.";
    }

    // acceptance event (D0121 review-queue sign-off; D0066/D0106 — human-judged, not fabricated)
    verification d0302Accept : Test { :>> id = "3f39626c-0a05-40dd-af30-c0b0accf49d3"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0302AcceptR1 : TestResult { :>> id = "cea9ed03-f77d-4028-98e6-2a31570fae77"; :>> outcome = VerdictKind::pass; :>> judgedAgainst = "284bac7"; :>> judgedAt = "2026-09-04"; :>> judgedBy = "wweatherholtz"; :>> createdBy = "claudeOpus5"; }
}
