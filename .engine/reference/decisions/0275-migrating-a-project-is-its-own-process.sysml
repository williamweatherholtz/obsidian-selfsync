// D0275 (status: the `status` field below is the truth) — Migrating a project onto a changed engine is its own process, and the engine is structurally blind to it
// Recorded via `keel record decision` (D0105 RMWX axis; issue054). Acceptance is a separate explicit
// human gate (method=confirmation, D0106): flip status + add the d0275Accept event on sign-off.
package ReferenceDecision0275 {
    private import EngineElement::*;
    private import EngineWork::*;
    private import EngineVerification::*;
    private import EngineRelationships::*;

    // #ProspectiveChange (D0070) - this Decision governs a process/schema change; the co-committed
    // change rides the process-change guard's hard lock.
    #ProspectiveChange part d0275 : Decision {
        :>> id = "8d0326fa-4a51-4a69-8261-1a153e102453";
        :>> title = "Migrating a project onto a changed engine is its own process, and the engine is structurally blind to it";
        :>> createdAt = "2026-09-01";
        :>> createdBy = "claudeOpus5";
        :>> status = DecisionStatus::accepted;
        :>> context = "Asked for a plan to migrate keel projects, I looked for the process that covers it and there is none. D0067's migration process governs a project changing its OWN data by a transform its author writes - different actor, different artefact, different failure modes. Nothing covered the other direction: the engine moved, the project did not choose it, and the project has to land somewhere honest. THE EVIDENCE THAT THIS GAP IS EXPENSIVE, counted rather than recalled: seven defects live in this path - issue301, issue310, issue314, issue323, issue324, issue326, issue327 - and NOT ONE was found by a test. Three were found by a single downstream peer session within one day. Four still have no test at all. The cause is structural rather than negligent: check_preconditions refuses any tree holding keel-cli/Cargo.toml as a self-build (migrate.rs:664-666), so THE ENGINE CANNOT MIGRATE ITSELF. Every other keel discipline is dogfooded daily; this is the one surface the self-build cannot exercise, and it has exactly the defect density that predicts.";
        :>> decision = "A projectMigration process is declared with six steps, ordered by what the NEXT step cannot recover from. pm0Preflight - gate on the CURRENT engine, record that SHA as the restore point, make the tree clean, note existing drift. pm1Capability - check what the new engine REMOVES rather than what it adds. pm2Apply - run migrate, let it refuse, let it roll back, never hand-repair a partial run. pm3Reconcile - prove the project's own pin comment, adoption choices, project-owned contracts and customised files survived the resync, then gate. pm4ProveItRemotely - read the project's OWN CI, because a local green is one machine and one binary. pm5FeedBack - file the cost upstream, since the engine is blind here and a downstream report is the only channel that exists. It ships as a unit with its skill so it travels to the projects that actually need it.";
        :>> rationale = "WHY A PROCESS AND NOT A CHECKLIST IN A SKILL: the ordering is load-bearing and a checklist cannot express why. Migrate refuses a dirty tree, and a dirty tree cannot always be committed - under engine-version skew the pre-commit gate refuses too, so a project behind its pin holding one uncommitted file can neither migrate nor commit (issue324). Cleanliness therefore has to be ESTABLISHED before migration is attempted rather than discovered during it, and the file that causes it is usually engine-authored, so it fires exactly when the project is already unhealthy. That dependency between steps is the thing being recorded. WHY pm4 EXISTS AS ITS OWN STEP rather than being folded into reconcile: a local gate proves the migration on one machine with one binary, and the entire point of the pin is that other machines exist. It is also the step most likely to be skipped and most likely to be already broken - a scaffolded project's CI has never run (issue327) and a project importing decision-channel acquires two workflows that cannot build (issue326) - so treating a silent Actions tab as success is the specific error it prevents. WHY pm5 IS NOT COURTESY: it is the only feedback channel that exists. The engine repo cannot run this path, so a defect here is invisible upstream until a downstream project reports it, and the seven-to-zero record says that is how all of them were actually found. A migration that went FINE is worth reporting for the same reason - it is the only evidence the path works, since no test can currently produce it. WHAT I CONSIDERED AND REJECTED: extending D0067 with downstream steps. It would put two different actors and two different failure modes under one purpose statement, and D0067's own steps (author a transform, dry-run, reconcile control totals, expand/migrate/contract) do not apply when the transform is the engine's and the project never saw it.";
        :>> consequences = "Projects get a process they can follow and a skill that travels, carrying the three traps that have already fired: the dirty-tree/skew deadlock, the half-update that no refusal covers, and the CI that was never running. THE HONEST LIMIT, stated rather than left to be discovered: declaring the process does not make the path tested. F9 in federation.rs proves a FRESH SCAFFOLD migrates - pin re-stamped, project comment preserved, adoption survived, gate green - and a fresh scaffold is the easy case. It does not cover a project that customised an engine file, authored its own skill naming an engine command, holds an untracked obligation record, or runs its own CI. Those four are precisely where the seven defects came from, and closing them is separate work this Decision charters rather than performs. UNTIL THEN the process's own pm5 is doing real load: downstream reports remain the primary detector, which is an uncomfortable thing to write down and the reason to write it down.";
    }

    // acceptance event (D0121 review-queue sign-off; D0066/D0106 — human-judged, not fabricated)
    verification d0275Accept : Test { :>> id = "c937bc06-3c7e-4de5-9698-53192c72dd68"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0275AcceptR1 : TestResult { :>> id = "27694c2c-7b4c-4c81-bcb7-6295a472aec2"; :>> outcome = VerdictKind::pass; :>> judgedAgainst = "0e001a6"; :>> judgedAt = "2026-09-01"; :>> judgedBy = "wweatherholtz"; }
}
