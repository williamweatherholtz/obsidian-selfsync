// =====================================================================
// D0098 — HONEST-STATE gates, not SELF-ASSURANCE gates. Amends D0079 (computed-assurance doctrine)
// + D0081 (charter-time assurance gates). A commit gate may enforce that the recorded model is
// TRUTHFUL / well-formed / traceable (honest-state) — but it must NOT hard-gate on COMPLETENESS
// ("are we done / fully covered / fully critiqued / fully dispositioned"). Incomplete implementation
// flagged AS incomplete is honest, valuable state (a burndown); suppressing it (fake pass) or
// blocking the commit until it is gone both destroy the honest picture. `assured` (self-assurance by
// name) + completeness checks become NON-BLOCKING computed burndown views surfaced in orient.
// Accepted 2026-06-24 by wweatherholtz ("accepted").
// =====================================================================
package ReferenceDecision0098 {
    private import EngineElement::*;
    private import EngineWork::*;
    private import EngineVerification::*;
    private import EngineRelationships::*;

    part d0098 : Decision {
        :>> id = "98a8b9c0-3f80-4192-aa4b-516273849698";
        :>> title = "D0098: honest-state gates, not self-assurance gates — completeness is a non-blocking burndown, never a hard commit gate";
        :>> createdAt = "2026-06-24";
        :>> createdBy = "wweatherholtz";
        :>> status = DecisionStatus::accepted;
        :>> context = "Authoring requirements for keel serve (issue046/047) exposed a structural blocker: the enforced `guard assured` (compute_readiness coverage_gaps) flags ANY governed Need/SystemRequirement with no coverage as a readiness gap, so a brand-new requirement-FIRST Need/SR cannot be committed until it is already satisfied + verified. The gates PUNISH requirement-first authoring — almost certainly WHY serve itself was built decision-first (D0094) with no driving Need. The first proposed fixes (a WIP/#Planned flag; a gap-Issue that exempts the requirement) were rejected by the human as METRIC-GAMING: they make `assured` go green while the implementation gap remains untouched in both cases. The real distinction: a gate can enforce HONESTY (the model does not lie / is well-formed / is traceable) OR self-ASSURANCE (the work is complete). Hard-gating on completeness forces exactly two bad outcomes — fake the pass, or be blocked from recording true state. Burndown analogy (human): you do not refuse to draw the chart just because work remains; incomplete implementation flagged AS incomplete is honest and useful.";
        :>> decision = "Split commit gates into two classes. (1) HONEST-STATE / INTEGRITY gates HARD-BLOCK the commit — the recorded model must not lie, be malformed, or be untraceable: validate (well-formed), actors, acceptance-events, ceremony, sprint-coverage, charter, process-change, viewpoint-renderer, manifest-coverage, critic-independence (a critique must be by an INDEPENDENT critic — honesty), process-skill, issues (every recorded problem is accounted for in the resolution graph — no dangling node), and a NEW requirement-rootedness gate (a chartered capability with NO driving Need is a traceability lie-of-omission). (2) COMPLETENESS / SELF-ASSURANCE measures are COMPUTED, ALWAYS-VISIBLE (surfaced in orient), NON-BLOCKING burndown views/indicators — they NEVER block a commit: `assured` (composite readiness) + its sub-checks (coverage %, critique-COVERAGE, ≥Medium-finding disposition backlog, OPEN CRITICAL findings, stale/suspect) + a NEW tier-satisfaction comprehensiveness view (is each tier cleanly + comprehensively satisfied downstream — a leading indicator of insufficient implementation). PURE rule (human): NOTHING completeness-related hard-blocks (incl. open Critical findings). The D0079 HONESTY core is KEPT in full: never fabricate a pass (compute-don't-author, no fake evidence). Note the borderline calls: critique INDEPENDENCE stays hard, critique COVERAGE demotes; `issues` triage stays hard (integrity). Charter-time scoping (D0081) was load-bearing only to keep hard gates from blocking on grandfathered gaps; with no hard completeness gate it survives as a burndown framing detail, not a gate.";
        :>> rationale = "ALTERNATIVES: (i) WIP/#Planned flag exempting a requirement from assured — REJECTED (metric-gaming: assured goes green, implementation gap remains). (ii) gap-Issue that marks a requirement covered — REJECTED (same gaming). (iii) fake a passing verification — REJECTED (D0079 honesty; never fake a pass). (iv) keep hard-gating completeness — REJECTED (forces fakery or blocks honest recording; structurally prevents requirement-first development, the root of issue046/047). (v) CHOSEN — gate HONESTY, surface COMPLETENESS as a non-blocking burndown. CRITERIA: honesty-of-state (never lie) x supports-requirement-first x no-metric-gaming x completeness-always-visible (never silently ignored). The human set the line: rootedness is honesty (hard); incomplete implementation of a stated requirement is honest incompleteness (burndown); pure (nothing completeness-related blocks).";
        :>> consequences = "Implemented across two steps. THIS step (declarativeGateReclassify / Sprint 145): `assured` + `critique` (coverage) leave the enforced GUARD_NAMES (13 -> 11) and the pre-commit hook — they stay RUNNABLE as diagnostics (`keel guard assured` / `keel assured`) and become non-blocking burndown; the D0079 honesty core + the 11 honest-state guards stay hard; downstream `keel init` projects inherit automatically (their hook runs `keel guard` over GUARD_NAMES). NEXT step (requirementRootednessGuard): ADD the requirement-rootedness HARD guard (-> 12 enforced) + the tier-satisfaction comprehensiveness burndown view + surface the assurance burndown in `orient` (always-visible). UNBLOCKS serveRequirementsTrace (a governed uncovered serve Need is now honest incomplete state — red on the burndown, committable). Amends D0079 (keeps compute-don't-author + no-fake-pass; drops completeness HARD-GATING) + D0081 (charter-time scoping no longer load-bearing for gating). doc-sync: CLAUDE.md (§5 guard set 13->11 + the honest-vs-assurance doctrine), the assurance prose. No .engine/processes edit (gate logic is guards.rs), so no #ProspectiveChange keystone needed.";
    }

    verification d0098Accept : Test { :>> id = "98a8b9c0-3f80-4192-ba4b-516273849698"; :>> method = VerificationMethod::confirmation; :>> procedureText = "wweatherholtz attests acceptance of d0098 (honest-state gates, not self-assurance gates: completeness is a non-blocking burndown, never a hard commit gate; rootedness is a hard honesty gate; pure — nothing completeness-related blocks, incl. open Critical findings; issues-triage stays hard, critique-coverage demotes) via the explicit 'accepted' on 2026-06-24, following the full doctrine + the two settled forks presented for acceptance."; }
    part d0098AcceptR1 : TestResult { :>> id = "98a8b9c0-3f80-4192-ca4b-516273849698"; :>> outcome = VerdictKind::pass; :>> judgedAgainst = "6a1c60c"; :>> judgedAt = "2026-06-24"; :>> judgedBy = "wweatherholtz"; }
}
