// D0367 (status: the `status` field below is the truth) — perfLandscape: computed state is slow from repetition, not from computing - four repetitions removed in rank, three approaches declined with numbers
// Recorded via `keel record decision` (D0105 RMWX axis; issue054). Acceptance is a separate explicit
// human gate (method=confirmation, D0106): flip status + add the d0367Accept event on sign-off.
package ReferenceDecision0367 {
    private import EngineElement::*;
    private import EngineWork::*;
    private import EngineVerification::*;
    private import EngineRelationships::*;

    part d0367 : Decision {
        :>> id = "a7c9947a-addd-4ded-bd8a-adedb15f6e5e";
        :>> title = "perfLandscape: computed state is slow from repetition, not from computing - four repetitions removed in rank, three approaches declined with numbers";
        :>> createdAt = "2026-09-07";
        :>> createdBy = "claudeOpus5";
        :>> status = DecisionStatus::accepted;
        :>> context = "The human, 2026-09-07: 'Keel has become slow, which is a known tradeoff for a computed state, but ideally I'd like ways to achieve performance even though our data doesn't follow a strict schema ... e.g. a database acting as cache, some kind of indexing, some auto-refreshing intermediate layer? It can still be pure compute, maybe we should just have a file index hash that can identify changes quickly? ... Do a research spike.' The spike measured before it proposed. On this host (Windows 11, 20 cores, Defender on-access scanning with no exclusion for the repository) with KEEL_PERF=2 and a measurement-only phase wrapper around run_all and orient::compute: the whole corpus - 678 files, 11.6 MB - tokenizes and parses in 275 ms and is parsed ONCE per process; `keel validate` costs 0.46 s and `keel gate --fast` 0.86 s; `keel orient` costs 5.1 s and `keel guard` 25.5 s. The 25 s is paid at every turn boundary by the Stop hook. Attribution, guard: priority-inversion 6.3 s (it re-runs orient::compute whole); about twenty guards at 0.4-1.8 s each that re-read the corpus from disk to scan lines (39 collect_sysml and 61 read_to_string sites in guards.rs); 56 git spawns at about 79 ms each on this host, 4.4 s, which the perf line reports as 0 ms because only govern.rs times them; 40 cache-hit clones of the Model, 1.57 s; all of it serial on 20 cores. Attribution, orient: criterion_suspects 1.8 s and deliverable suspicion 0.95 s, both dominated by git spawns whose answers are facts about immutable commits. Also measured: a cold read of the 11.6 MB by Python took 51 s and a warm one 0.4 s - Defender scans every open, so the reopen, not the byte, is the unit of I/O cost here. Full tables and the patch scripts that produced them: docs/reviews/perf-spike-2026-09-07.md; the tracked defect is issue409, the perf-line omission issue410.";
        :>> decision = "The premise the question started from holds: the code is not slow, the repetition is. Parsing is 1% of the guard run. Four repetitions are removed, as backlog items in this rank which is their declaration order, all four resolving issue409. First, dcGuardsRunInParallelAndTimed - the 65 enforced guards run across a thread pool with their order preserved, and every guard and every git spawn is timed in-process so the next measurement needs no patch. Second, dcGitFactsAreContentAddressed - the facts orient asks git about a full commit id (is it a commit, the DoD text at it, the paths changed since it) are immutable and are cached machine-local under that id, so a run after the first pays only for commits it has not seen. Third, dcOneCorpusPerProcess - one process opens each file once, validated by (len, mtime) on every read, and a Model cache hit shares an Arc rather than cloning. Fourth, dcGateAnswersFromItsReceipt - a green run writes the key of the tree it judged (HEAD, the dirty set with its stats, the .keel files a guard can read, the binary's build id) and an identical key answers green from the receipt in one line, so a turn boundary on an unchanged tree costs a stat pass rather than 25 s. Two more are conditional on those measurements and sit at the tail: dcGitReadsStayInProcess moves the remaining git reads in-process on gix only if the residual spawn time exceeds 500 ms per orient; dcHookDaemonOnlyIfTheReceiptIsNotEnough builds a resident process only if the receipt leaves an idle turn above one second. NOT A FORK: this is a ranked list of work with each rank's cost measured, not alternatives for the human to choose between; the choices inside it are engineering calls with the number that decided each stated, and the one real fork (a resident daemon) is deferred behind a measurement rather than argued.";
        :>> rationale = "WHY NOT THE THINGS THE QUESTION NAMED. A database as cache or an index: the expensive computations here are not lookups but whole-corpus predicates (every guard is 'over all items, does X hold'), which a database answers by scanning the same rows; and a materialised copy of the truth is a second truth that can disagree with the text (§1, D0018), the exact failure the computed-state design exists to prevent. A file-index hash to identify changes quickly: keel already has one - fingerprint::of folds (path, len, mtime) over the model in about 40 ms, memoized per epoch - and the Model cache is keyed on it; the hash was never the missing piece, what was missing is a receipt of the last green run keyed on it, which is rank 4. An auto-refreshing intermediate layer: that is the daemon, and it is the only approach whose benefit depends on the process outliving the request; with rank 4 in place the idle turn is a stat pass, so the daemon is deferred until a measurement says it is needed. A faster parser: 275 ms is already the smallest number on the table. Incremental recomputation frameworks (salsa-style): they pay only inside a resident process and rewrite every computation as a query - the cost is large and the win is bounded by rank 4's number. WHY THE RANK. Rank 1 is one function and removes the largest term (serial execution on 20 cores; the run becomes bounded by its slowest guard, which is priority-inversion at 6.3 s); rank 2 removes what bounds rank 1 (orient's spawns, which priority-inversion pays in full); rank 3 removes the corpus reopens that rank 1 only hides behind parallelism and which a Defender host pays per open; rank 4 removes the whole run from the common case, and is last because its key must be argued sound before it is trusted - the argument is in its DoD. WHAT IS DECLINED WITH A NUMBER RATHER THAN DEFERRED: a Defender exclusion or a Dev Drive for the repository would cut every open by the scan cost (51 s cold against 0.4 s warm for the same bytes) and is the largest single lever on this host, but it is a change to the human's machine, not to keel, and stays theirs to make.";
        :>> consequences = "Four items lead the ready list and are worked in order, each in its own sprint with the before/after wall time read from a shell timer and recorded in the sprint. Rank 1 and rank 3 change guards.rs, which is under the keystone lock (D0209 clause 2), so each lands with its own #ProspectiveChange Decision, and rank 4 changes what the turn-boundary gate does on an unchanged tree, so it lands with a #SafetyChange Decision - all three stay proposed for the human under D0337. What this Decision does NOT claim: that any of the four is built; that the numbers transfer to another host (they were measured on one machine with Defender scanning every open, and a Linux CI runner will show a different mix); or that the guards are pure functions of the tree - rank 4's DoD names the check that establishes it.";
    }

    // acceptance event (D0121 review-queue sign-off; D0066/D0106 — human-judged, not fabricated)
    verification d0367Accept : Test { :>> id = "ee1ab650-177a-438b-8c0a-db11fc6726df"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0367AcceptR1 : TestResult { :>> id = "3960156f-2cf9-489f-b7d8-82606b15bbdd"; :>> outcome = VerdictKind::pass; :>> judgedAgainst = "59c4336"; :>> judgedAt = "2026-09-07"; :>> judgedBy = "wweatherholtz"; :>> createdBy = "claudeOpus5"; }
}
