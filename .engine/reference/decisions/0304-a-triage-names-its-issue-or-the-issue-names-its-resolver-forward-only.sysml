// D0304 (status: the `status` field below is the truth) — A triage is a stated link, not an edge: forward from this date the issues guard fails an Issue whose resolver's text never names it and whose own text never names the resolver; earlier resolutions are counted once as history
// Recorded via `keel record decision` (D0105 RMWX axis; issue054). Acceptance is a separate explicit
// human gate (method=confirmation, D0106): flip status + add the d0304Accept event on sign-off.
package ReferenceDecision0304 {
    private import EngineElement::*;
    private import EngineWork::*;
    private import EngineVerification::*;
    private import EngineRelationships::*;

    // #SafetyChange (D0070) - this Decision governs a process/schema change; the co-committed
    // change rides the process-change guard's hard lock.
    #SafetyChange part d0304 : Decision {
        :>> id = "eaa34ca8-125a-45d2-9e52-de95d88db32d";
        :>> title = "A triage is a stated link, not an edge: forward from this date the issues guard fails an Issue whose resolver's text never names it and whose own text never names the resolver; earlier resolutions are counted once as history";
        :>> createdAt = "2026-09-04";
        :>> createdBy = "claudeOpus5";
        :>> status = DecisionStatus::accepted;
        :>> context = "issue333 (D0278 registry, direction under): the issues guard checked that a #Resolves edge EXISTS and never that the named resolver could resolve the issue - issue323's resolver was dcCliSurfaceConsolidation, carried over from the previous record call, unable to resolve a unit-identity defect, and the guard passed it. The only distinguishing signal is prose: a resolver that will close an issue names it, or the recorder's own text at triage names the resolver ('PREVENTING CHANGE: dcX'). Measured on this tree 2026-09-04: 387 resolves edges, 144 whose resolver text does not name the issue by the first draft's one-directional check, 111 by the two-directional one; as a per-item warning over history that is noise, and re-triaging 111 issues is a sitting review the human may choose (D0204), never owed. The same day the two-directional check, run forward-only, found four of my own issues from that day - three linked by the issue's text naming its resolver, and issue370, whose text named the Decision and the test but not the item that carried the fix: a real unstated link, corrected in the issue's text.";
        :>> decision = "The issues guard, in addition to the existence check, reads every resolves edge: the resolver's title, DoD text, decision, consequences, description and actionText, and the issue's description. If neither the resolver's text names the issue (whole identifier) nor the issue's text names the resolver, and the issue was created on or after 2026-09-04, that is a VIOLATION naming both and the remedy (name the issue in the resolver's DoD, or re-triage). Misses on issues created before the cutoff are counted in one WARNING line, never enumerated and never blocking. The cutoff is a constant in the guard (ISSUE_NAMING_CUTOFF); issue352's class - an engine cutoff retroactive for a downstream project - applies to it and is dcForwardOnlyCutoffIsTheProjectsOwn's open fix, stated here rather than solved here.";
        :>> rationale = "WHY EITHER DIRECTION: the recorder's text at triage time is a judgment about the resolver as much as the resolver's DoD is; requiring the resolver side only would force edits to verified DoDs (the issue343 class) every time an issue is recorded after its fix - which is the ordinary order of events for a defect found and fixed in one sprint. WHY FORWARD-ONLY: 111 historical misses are true facts about records written under a weaker rule; blocking on them would make the gate red over history nobody can honestly rewrite, and D0129 forbids rewriting it. WHY A VIOLATION AND NOT A WARNING GOING FORWARD: a mis-triage is a frontier ordered against an issue it will not close, and the cost of naming the issue is one clause in a DoD or a description the author is already writing. WHAT IT CANNOT SEE: a resolver that names the issue and still cannot resolve it - the same limit D0192 states for quotes: a fabricated link defeats a textual check, and the protections behind it are the sitting review and the DoD result the resolver must eventually pass.";
        :>> consequences = "dcControlDefectsAreFixed (rescoped to issue333; issue332 was dcSessionActorReachesHooks's, issue331 is split to dcDecisionClausesAreAddressable behind fork d0303) is delivered; issue333 resolves; the control-defects.toml [issues] entry leaves in this commit. Every issue recorded from today either names its resolver in its text or is named by its resolver's DoD - `keel record issue --resolver X` with a description that says 'PREVENTING CHANGE: X' satisfies it as written. The 111 historical misses are one line in `keel guard issues` until someone chooses to read them.";
    }

    // acceptance event (D0121 review-queue sign-off; D0066/D0106 — human-judged, not fabricated)
    verification d0304Accept : Test { :>> id = "c04bd239-d6a2-41d5-9989-306749c03ddb"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0304AcceptR1 : TestResult { :>> id = "2eea340a-6606-47ec-871e-c0f8c002b0aa"; :>> outcome = VerdictKind::pass; :>> judgedAgainst = "3990204"; :>> judgedAt = "2026-09-04"; :>> judgedBy = "wweatherholtz"; :>> createdBy = "claudeOpus5"; }
}
