// D0261 (status: the `status` field below is the truth) — Undischargeable findings are COUNTED, not enumerated, and legacy tolerance is bounded by the record's own date
// Recorded via `keel record decision` (D0105 RMWX axis; issue054). Acceptance is a separate explicit
// human gate (method=confirmation, D0106): flip status + add the d0261Accept event on sign-off.
package ReferenceDecision0261 {
    private import EngineElement::*;
    private import EngineWork::*;
    private import EngineVerification::*;
    private import EngineRelationships::*;

    // #SafetyChange (D0070) - this Decision governs a process/schema change; the co-committed
    // change rides the process-change guard's hard lock.
    #SafetyChange part d0261 : Decision {
        :>> id = "a18450b1-3df6-4076-91a7-2fbaf35ec7d0";
        :>> title = "Undischargeable findings are COUNTED, not enumerated, and legacy tolerance is bounded by the record's own date";
        :>> createdAt = "2026-08-30";
        :>> createdBy = "claudeOpus5";
        :>> status = DecisionStatus::accepted;
        :>> context = "The human said they thought rigor had been lost and asked where the gaps are. Measured rather than assumed, and the hypothesis holds - narrowly and with a precise cause. THREE OF FOUR HARDENING DIMENSIONS WERE PERFECT: help coverage 100 percent, decision follow-through 4/4, API surface 0 unaccounted. The gap was concentrated in the WARNING CHANNEL: 96 warnings across 11 guards, of which 61 (64 percent) were structurally undischargeable - 52 `legacy actor 'user'` lines on June records, where 'fixing' a judgedBy would FALSIFY provenance, and 9 grandfathered thin attestations on a fixed allowlist. WHAT THE NOISE COST, exactly: eight real verification-trace findings against MY OWN four-day-old work sat unread behind it - passing DoDs that named SystemRequirements with no #Verify edge, so the work was verified and the REQUIREMENT was not (issue082). So did a release-recorded warning saying the v0.3.1 tag and its Release item named different commits. So did ten decision-scaffolding warnings, one of which was an OPTION THE HUMAN CHOSE ON 2026-08-23 (d0201 Option B, device HMAC on deck taps) that no tracked work has ever carried. This is the priority-inversion lesson (D0258) in a second channel: a signal nobody reads is not a control, and here the reason nobody read it was that two thirds of it could never be acted on.";
        :>> decision = "Two clauses, both in the guards. CLAUSE A - COUNTED, NOT ENUMERATED. Findings that are undischargeable by construction are reported as a COUNT with the reason, never one line each. `actors` emits one line for its 52 historic references; `attestation-substance` emits one for its 9 grandfathered records. Nothing is hidden: the number is stated, and it moves when the population moves. CLAUSE B - THE TOLERANCE IS DATE-BOUNDED, WHICH IS WHAT MAKES A COLLAPSE SAFE. A legacy actor name is tolerated only on a record dated BEFORE 2026-06-12; on or after, it is a VIOLATION. The verdict comes from the RECORD'S OWN DATE, so there is no second baseline list to drift - the objection that killed the alternative designs. Every legacy reference in the corpus predates it (newest observed 2026-06-11), so the ratchet starts at zero violations. Armed by four probes including the boundary case, because an off-by-one would leave exactly one day of silent tolerance. The attestation allowlist needs no cutoff: it is fixed, and anything outside it already violates. DISCHARGED IN THE SAME PASS, because a cleaner channel that still carries unread debt would prove nothing: the 8 missing #Verify edges are authored (SystemRequirement verify coverage 86 -> 90 percent); the v0.3.1 Release record now names the commit the tag actually points at; and the three decisions that promised unbuilt mechanisms - d0201's device HMAC, d0252's migration rollback, d0249's ungrounded-ratio trigger - now carry chartered backlog tasks.";
        :>> rationale = "WHY COLLAPSE RATHER THAN DELETE. The count is real information: 52 legacy references is a fact about the corpus and it should be visible. What added nothing was the 52nd copy of a line whose action is 'none, ever'. WHY NOT SIMPLY DEMOTE THESE GUARDS. Both still hold live rules - an unknown actor is a violation, a thin attestation outside the allowlist is a violation. Turning the guards off to quiet them would remove the enforcement along with the noise, which is the trade this decision exists to avoid. WHY THE DATE AND NOT A LIST. A hand-maintained baseline of tolerated instances is the pf07 objection exactly: a second drift-prone list to fence the first. The record carries its own date, so the rule needs nothing external and cannot rot. WHAT IS NOT FIXED, and why not silently. decision-scaffolding still warns 8 times, and 4 of those are SELF-EXECUTING decisions whose change landed in the same commit (d0211, d0247, d0248, d0257) - there is no future work to charter and never will be. The guard has no third bucket to say so, which is the same two-bucket error issue173 already corrected once elsewhere. Fixing it means either an unchecked escape hatch or a locked-out legitimate case, so it is filed (issue312) rather than patched under the cover of this decision.";
        :>> consequences = "The channel goes 96 -> 24 warnings, and the two guards that dominated it now say something a reader can act on or ignore in one line each. verification-trace and release-recorded leave the warning list entirely, discharged rather than quieted. A legacy actor name on a new record now FAILS instead of warning - a strengthening, recorded here so audit-adherence reads it as one. Three mechanisms the model had promised and nobody was building are now tracked work, one of them a direction the human chose a week ago.";
    }

    // acceptance event (D0121 review-queue sign-off; D0066/D0106 — human-judged, not fabricated)
    verification d0261Accept : Test { :>> id = "aa66c2d5-fb36-4efe-9679-132220fd1182"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0261AcceptR1 : TestResult { :>> id = "a1094660-87a8-4925-a06b-0c71bb511938"; :>> outcome = VerdictKind::pass; :>> judgedAgainst = "6146f43"; :>> judgedAt = "2026-08-30"; :>> judgedBy = "wweatherholtz"; }
}
