// D0296 (status: the `status` field below is the truth) — The keel hooks are hosted above the repository: a keel plugin carries them, the launcher pins disableAllHooks off above project scope, and a ConfigChange guard restores the settings file the moment an agent turns them off
// Recorded via `keel record decision` (D0105 RMWX axis; issue054). Acceptance is a separate explicit
// human gate (method=confirmation, D0106): flip status + add the d0296Accept event on sign-off.
package ReferenceDecision0296 {
    private import EngineElement::*;
    private import EngineWork::*;
    private import EngineVerification::*;
    private import EngineRelationships::*;

    // #SafetyChange (D0070) - this Decision governs a process/schema change; the co-committed
    // change rides the process-change guard's hard lock.
    #SafetyChange part d0296 : Decision {
        :>> id = "e1fcc11c-58d5-4ccc-832a-084339c39430";
        :>> title = "The keel hooks are hosted above the repository: a keel plugin carries them, the launcher pins disableAllHooks off above project scope, and a ConfigChange guard restores the settings file the moment an agent turns them off";
        :>> createdAt = "2026-09-03";
        :>> createdBy = "claudeOpus5";
        :>> status = DecisionStatus::accepted;
        :>> context = "st090 (2026-09-03): 'would keel work better as an extension? forced pre post hooks?', pulled forward by st091 ('we do. go'). Today every keel hook lives in the repository's .claude/settings.json (claude_surface.rs:131-138): the agent it gates can edit the file, Claude Code reloads hooks live, and the drift guard compares only the keel-OWNED entries - so the cheapest bypass, 'disableAllHooks': true beside intact hook entries, reads as no drift (issue365). The landscape spike (D0282) had named exactly this class in Kiro - blocking hooks the controlled party can edit - and keel had it too. What holds regardless is the third leg: CI re-derives validate and every guard on the tree, so a silenced hook delays detection to push time; it does not hide dishonest state. The question is therefore how much of the in-loop tier can be made a control rather than a convention, and at what cost per rung. SIX LIVE RUNS on 2026-09-03 in a scratch project with a minimal plugin loaded by --plugin-dir (PostToolUse appending to a log, ConfigChange as the probe), nested headless sessions (claude -p, Claude Code 2.1.260): RUN 1 baseline - plugin PostToolUse fires (2 log lines for 2 tool calls). RUN 2 - agent writes disableAllHooks into project settings mid-session; ConfigChange fires one second AFTER the write; the following tool call's PostToolUse never fires. RUN 3 - seven steps, ConfigChange hook denying only when its stdin contains the key: no deny issued, because the payload carries session_id, cwd, hook_event_name, source (project_settings) and file_path ONLY - no config content; steps 4-7 fired no PostToolUse. RUN 4 - ConfigChange with an unconditional exit 2: the two tool calls after the write DID fire their PostToolUse - the deny keeps the plugin hooks alive for the rest of the session. RUN 5 - the key already on disk at launch: no plugin hook fires at all, and SessionStart cannot block. RUN 6 - the same on-disk key, launched with --settings {'disableAllHooks': false}: both PostToolUse fire - the launch scope beats the project scope for that key, as the documented precedence (managed > --settings > local > project > user) predicts. DOCUMENTED, not run: hook lists MERGE across scopes and a project cannot remove a user-, plugin- or managed-scope hook; disableAllHooks is read from any scope; managed hooks run unless the key is set in managed settings too; allowManagedHooksOnly is managed-scope only; a blocked ConfigChange does NOT revert the file on disk; plugins install per user (here under ~/.claude/plugins/cache/<marketplace>/<plugin>/<version>/), enabledPlugins and extraKnownMarketplaces are settable from any scope including the project's; managed settings live at C:/Program Files/ClaudeCode/managed-settings.json (system path, admin-only).";
        :>> decision = "Host the hook set above the repository, in three layers that each cover what the one below cannot, and keep the repository's settings.json as the DECLARATION only. (1) A keel PLUGIN (.claude-plugin/plugin.json + hooks/hooks.json, generated by the same generator as claude_surface.rs so there is one source of the hook set and two renderings) carries the enforcement copy; the repository publishes it as a marketplace so a project's own settings can name it in extraKnownMarketplaces/enabledPlugins. (2) The launcher - the console's claude -p spawn in launcher.rs, and a `keel claude` wrapper for interactive sessions - passes --plugin-dir to the shipped plugin and --settings with 'disableAllHooks': false, so a key already on disk at launch is overridden above project scope (RUN 6). (3) A `keel hook config-change` handler in the plugin denies (exit 2) any project- or local-scope settings change that sets disableAllHooks or alters a keel-owned hook entry, and because a deny does not revert the file, it RESTORES the keel-owned subset itself - the same regeneration `keel sync-claude` performs - so the file cannot survive to the next launch (RUN 4 + RUN 5). The payload carries only file_path, so the handler reads the file, never stdin. (4) The drift guard and pre-write refuse disableAllHooks in repo-scope settings (issue365), so the key can never be COMMITTED; and `keel status` reports which hosts are live and whether the project settings carry the key - an out-of-hook check, because a dead hook cannot report itself. Managed settings with allowManagedHooksOnly is documented for enterprise deployers as the only host the agent's shell cannot reach; it is not keel's default because a project cannot declare it and it couples every project on a machine to one engine version.";
        :>> rationale = "WHY NOT STAY: issue365 is a one-line bypass of the whole in-loop tier that the guard built to notice hook tampering reports as clean; the landscape spike's own critique of Kiro applied to keel. WHY NOT MANAGED-ONLY: it is the only truly forced rung, but it is admin-deployed per machine, undeclarable by a project, and version-couples every project on the host - the D0054 friction cost is the whole adoption story. WHY THREE LAYERS AND NOT ONE: the runs show each layer's hole. A plugin alone dies to an on-disk key at launch (RUN 5). A ConfigChange deny alone protects the live session but leaves the file for the next launch (documented non-revert, RUN 5). A launch override alone protects only sessions keel launched. Together: the key cannot take effect in-session (deny), cannot persist (restore), cannot survive a keel launch (override), and cannot be committed (guard). WHY THE PLUGIN IS GENERATED FROM THE SAME SOURCE: two hand-maintained copies of the hook set is the dual-truth D0105 forbids; the repository's settings.json stays as declaration so `keel init` still stands up a gated project on a machine with no plugin, and the drift guard keeps declaration and enforcement copy equal. WHY THIS IS NOT A FORK: the evidence eliminates two of the three alternatives on facts a reader can re-run (the six runs are reproducible from the recorded prompts), and the remaining shape is a layering, not a choice between exclusive options. WHAT THE THIRD LEG STILL GUARANTEES: none of this changes what CI detects; it changes WHEN a violation is caught - at the edit instead of at the push - and whether the in-loop advisories (post-edit, stop, pre-write) are a control the agent maintains or one it cannot silence without a recorded refusal. HONEST LIMIT: every layer below managed settings lives on a filesystem the agent's shell can reach (~/.claude/plugins, the launch settings file); what they cannot be reached by is a repository commit, and what catches a shell-level edit is the fire-ledger reconciliation (dcExternalFactGate) and CI - the same detective backstop as today.";
        :>> consequences = "Chartered, in priority order, all EXECUTE: dcDriftGuardRefusesDisableAllHooks (issue365, already on the backlog); dcKeelPluginHostsTheHooks (plugin + marketplace generated from claude_surface's generator, sync-claude --check covers both renderings); dcHookConfigChangeRestoresTheFile (`keel hook config-change`: read file_path, deny, regenerate the keel-owned subset, one fire-ledger line); dcLaunchPinsHooksOn (launcher.rs spawn and `keel claude` pass --plugin-dir and --settings disableAllHooks:false); dcStatusReportsHookHosts (`keel status` names the live hosts and flags the key). The control structure (D0284) gains the plugin and the launch override as sources once they exist - computed, not authored. CLAUDE.md §5 gains the hosting sentence when the plugin ships, not before. Managed settings are documented for enterprise deployers as an option, never required. Supersedes nothing: D0130/D0209 stand; this moves where their controls live.";
    }

    // acceptance event (D0121 review-queue sign-off; D0066/D0106 — human-judged, not fabricated)
    verification d0296Accept : Test { :>> id = "532cadc8-eae2-4353-84f1-01162fe2dfce"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0296AcceptR1 : TestResult { :>> id = "d6b57c3b-0993-4eca-a5ad-d3333569702c"; :>> outcome = VerdictKind::pass; :>> judgedAgainst = "7d174a6"; :>> judgedAt = "2026-09-03"; :>> judgedBy = "wweatherholtz"; }
}
