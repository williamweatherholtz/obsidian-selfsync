// =====================================================================
// D0105 — adopt declarative, model-driven controls: collapse the
// bespoke per-defect Rust guards into a small generic evaluator over DECLARED rules. ~8 of 14 guards
// are one assertion in disguise ("a downstream instance must carry its declared upstream edge to an
// existing element"); the other ~5 are per-element integrity predicates. Replace both with declared
// `EdgeRule`/`ElementRule` elements (SysML, fork #1) evaluated generically by `keel check`, plus a
// CLOSED RMWX verb axis for writes. Code stops growing per-defect (rules -> infinity, code -> flat).
// Design artifact: docs/proposals/2026-06-30-declarative-controls-issue054.md. status=proposed:
// this CAPTURES the direction the human endorsed in analysis; ACCEPTANCE awaits the Change-Request +
// schema/core human sign-off (a `Rule` type is a frozen-core addition). Drives issue054 + issue055.
// =====================================================================
package ReferenceDecision0105 {
    private import EngineElement::*;
    private import EngineWork::*;
    private import EngineVerification::*;
    private import EngineRelationships::*;

    part d0105 : Decision {
        :>> id = "05a1b0c1-4105-42a3-ab5c-516273849705";
        :>> title = "D0105: declarative, model-driven controls — collapse bespoke guards into declared rules";
        :>> createdAt = "2026-06-30";
        :>> createdBy = "claudeOpus";
        :>> status = DecisionStatus::accepted;
        :>> context = "The engine enforces invariants with bespoke hand-compiled Rust guards, one per defect class. The set grew 12->13->14 (D0102/D0103) and issue054 proposed a 15th; D0047 ('every correction becomes a permanent guard') institutionalizes this reactive growth. Three smells: (1) GUARD SPRAWL — the control surface grows linearly with discovered defects. (2) CLI-VERB PROLIFERATION — add-task/append-result/apply-review/proposed-add-decision: one verb per authored type, coupling the CLI to the schema. (3) DUPLICATED TRUTH — business.sysml already DECLARES the workflow order (first needs then useCases); a hand-written ordering guard re-encodes that truth in Rust, the anti-pattern Sec 2.1 forbids. ANALYSIS FINDING (proven): sorting the 14 guards by what they ACTUALLY assert, ~8 of 14 reduce to ONE assertion — 'a downstream instance must carry its declared upstream edge to an existing element' (ceremony/sprint-coverage/requirement-rootedness/issues/process-skill/charter/process-change/decision-requirement-link). The other ~5 (actors/decision-rationale/critic-independence/manifest-coverage/viewpoint-renderer) are per-element integrity predicates. Separately, the Business/Architecture workflows are INERT (no deploying skill, contra D0059; the process-skill guard scans only .engine/processes/, not .engine/workflows/), which is the real root of issue054 F1; and `keel serve` has no Business/Needs view. Full design: docs/proposals/2026-06-30-declarative-controls-issue054.md. SPIKE CORRECTION (2026-07-01, sprint172): the '~8 of 14 collapse' headline UNDERSTATES scope — expressing the 3 hardest guards (ceremony/charter/sprint-coverage) showed the predicates stay small but complexity migrates into a bounded ~4-predicate SCOPE sub-language (the load-bearing complexity + inner-platform danger zone), a THIRD OrderingRule kind, and a declared exemption mechanism (proposal sec 10). Classifying acceptance-events (D0066) as an EdgeRule makes the collapse ~9 of 14.";
        :>> decision = "Adopt DECLARATIVE, MODEL-DRIVEN controls evaluated generically — not coded. (a) THREE declared rule kinds, first-class SysML elements with UUID identity carrying a `justifiedBy` edge to their justifying Decision: `EdgeRule` (subject + required edge + object + cardinality + scope + severity) subsumes the ~9 conformance guards (incl. acceptance-events: accepted Decision -> acceptance-event, cardinality>=1); `ElementRule` (subject + a predicate from a CLOSED vocabulary — nonBlank/minLength/matchesPattern/inRegistry/distinct/referentExists/resolvesToCommand/countCompare) subsumes the ~5 structural guards; `OrderingRule` (succession-conformance — reads the declared workflow first..then and checks instance gate-state in order) subsumes ceremony's gate-ordering. (b) A bounded SCOPE sub-language (governedSince(decision) / newlyAdded(git-temporal, forward-only) / where-status(computed) / numeric-cutoff) — per the sprint172 spike, SCOPE is the load-bearing complexity, so (c) a META-RULE caps scope-predicate growth (a new scope predicate requires a justifying rule), and (d) a declared EXEMPTION mechanism (grandfather sets with recorded basis) covers the pervasive grandfathering. (c) A single `keel check` evaluates whatever the model declares, replacing the forever-growing `guard <name>`. (d) A CLOSED RMWX verb axis (read/record/modify/execute), each generic over the model, replaces the per-type write verbs; triage becomes (verb x targetType)->process. FORK #1 RESOLVED: rules live as SysML elements (single source of truth, native provenance, critique-able/suspect-able/coverage-counted), and the TOML contracts (critique-policy.toml, reverify.toml) are RECONCILED into the model (governance->Rule; pure execution params referenced BY a Rule), not extended. The friction objection is killed by the generic `record` verb.";
        :>> rationale = "ALTERNATIVES: (i) status quo — keep adding one Rust guard + one CLI verb per defect — REJECTED (proven 8x duplication; sprawl; downstream projects inherit this repo's defect history with no opt-out). (ii) 'one process to rule them all' (enforce only workflow conformance) — REJECTED as INSUFFICIENT (covers ordering/edge-conformance but NOT per-element integrity; those don't vanish — they become ElementRules). (iii) declare rules in TOML (extend the existing contracts) — REJECTED (second store -> drift; no typed provenance edge; opaque to critique/suspicion/coverage; no identity). (iv) CHOSEN — SysML-declared EdgeRule/ElementRule + generic evaluator + closed verb axis: strictly more faithful to the engine's own invariants (Sec 2.1 text-is-truth; Sec 2.6 reference-don't-embed; D0088 requirements-as-evaluable-constraints), and justified BECAUSE keel is a reusable multi-project engine (downstream declares its own rules, enforcement free). CRITERIA: single-source-of-truth x flat-code-growth x downstream-flexibility x faithful-to-invariants x honest-state-preserved.";
        :>> consequences = "schema/core gains `Rule`/`EdgeRule`/`ElementRule`/`OrderingRule` + the predicate vocabulary + the scope sub-language + the exemption mechanism + the scope-cap meta-rule — ALL as ONE FROZEN-CORE sign-off before any code (avoid repeated freeze cycles; this is why status=proposed). MIGRATION via D0067 (expand/migrate/contract) with a PARITY GATE: build the evaluator alongside the guards, express each as a rule, prove `keel check` output == the guards' output on the current repo, THEN retire the Rust predicates (precedent: the retired python/rust parity check). ROLLBACK CRITERION: if parity cannot be achieved for a guard (e.g. charter's git-temporal scope), that guard STAYS a Rust predicate (partial migration) and the 'code->flat' claim is re-scoped; abandon the direction only if a majority of the conformance guards fail parity. The 'flat code' claim MUST be RE-VALIDATED against the corrected surface (3 kinds + scope sublang + exemptions) before the full migration. TOML MIGRATION (concrete): critique-policy.toml's required-lenses-per-type -> policy `ElementRule`s; reverify.toml's commands=[...] -> a reverify `Rule` referencing the command list as a parameter; `keel critique-policy`/`keel reverify` read the Rule; the .toml files are deleted in the contract step after parity. UPON ACCEPTANCE (not before): reframes D0047 (corrections -> declared rules, not new code); extends D0088 (constraint layer -> ElementRules); subsumes issue054's resolver (ordering -> EdgeRule; add-decision -> `record`). The D0068 charter-wording amendment is tracked separately (issue055). Honest-state vs completeness (D0098) preserved; edge algebra stays CLOSED. INDEPENDENT CRITIQUE (claudeSonnet46, sprint173): FAILED this decision as stale-vs-spike; this revision addresses findings C1-C6/C10/C13; residual C11 (AI-authored decision reframing accepted decisions) + C12 (two-thread coordination protocol) need HUMAN disposition (issue056). doc-sync: CLAUDE.md Sec 3 (triage axes) + Sec 5 (guard enumeration -> `keel check`). Tracked work: declarativeControlsEvaluator, guardsToRulesMigration, businessArchSkillAndWorkflowGuard, serveBusinessNeedsView (EngineBacklog).";
    }

    verification d0105Accept : Test { :>> id = "05a1b0c1-4105-42a3-bb5c-516273849705"; :>> method = VerificationMethod::confirmation; :>> procedureText = "wweatherholtz attests acceptance of D0105 (declarative, model-driven controls — replace ~9-of-14 bespoke guards with a generic keel check over declared EdgeRule/ElementRule/OrderingRule + a closed RMWX verb axis; SysML rules, TOML reconciled; migration via D0067 parity gate) via the explicit 'yes for d0105' on 2026-07-02, after review of the reworked decision + the independent Sonnet critique (which initially FAILED it as stale, then was addressed by the sprint173 rework). This acceptance DISPOSITIONS residual critique finding C11 (an AI-drafted decision reframing accepted decisions is procedurally acceptable given this explicit human sign-off)."; }
    part d0105AcceptR1 : TestResult { :>> id = "05a1b0c1-4105-42a3-cb5c-516273849705"; :>> outcome = VerdictKind::pass; :>> judgedAgainst = "38c1ed4"; :>> judgedAt = "2026-07-02"; :>> judgedBy = "wweatherholtz"; }
}
