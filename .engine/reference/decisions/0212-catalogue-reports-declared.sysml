// D0212 (status: the `status` field below is the truth) — catalogueReportsDeclared: every declared process is listable, showable and exportable - carrying enforcement is not a precondition of travelling
// Recorded via `keel record decision` (D0105 RMWX axis; issue054). Acceptance is a separate explicit
// human gate (method=confirmation, D0106): flip status + add the d0212Accept event on sign-off.
package ReferenceDecision0212 {
    private import EngineElement::*;
    private import EngineWork::*;
    private import EngineVerification::*;
    private import EngineRelationships::*;

    // #ProspectiveChange (D0070) - this Decision governs a process/schema change; the co-committed
    // change rides the process-change guard's hard lock.
    #ProspectiveChange part d0212 : Decision {
        :>> id = "95c9e0e5-0c83-4efa-8456-99b6ff06d352";
        :>> title = "catalogueReportsDeclared: every declared process is listable, showable and exportable - carrying enforcement is not a precondition of travelling";
        :>> createdAt = "2026-08-24";
        :>> createdBy = "claudeFable5";
        :>> status = DecisionStatus::accepted;
        :>> context = "The human asked whether processes are transferable between projects. Measured: 23 process definitions, 11 reachable through keel process. and both exited 2 with 'no process intake' while .engine/processes/intake.sysml sat on disk, and search returned 0 matches - so 12 processes including intake, definition-of-done, definition-of-ready, adversarial-panel-review and migration were DENIED by the catalogue. Cause: process_cmd::rows() iterated activation::unit_names(), and a unit forms only when a process asserts a guard. The nine-lens panel of 2026-08-24 converged on this as the single highest-value fix and as the un-swept half of issue149, whose remedy taught and / to report the whole set and never reached this catalogue - a D0047 correct-at-the-root failure. It also violates srPortModularProcessUnit, an accepted MUST that a unit carry its definition, deploying skill and rules/guards so it can be moved between projects whole; and three critiques dated 2026-08-21 passed that requirement with zero findings, two citing a live run of the very command, while tier-satisfaction reported 103/103 - a false green inside the verification substrate.";
        :>> decision = "The process catalogue reports every DECLARED process. rows() iterates activation::declared_processes() (the already-existing, already-tested helper) rather than unit_names(), so list, search, show and export all reach all 23. A THIRD state is reported rather than two: a guard-bearing process reads active or INACTIVE, and a guard-less one reads with the reason printed - because reporting a guard-less process as INACTIVE would assert this project had switched it off, which is a false claim about the control inventory. is_process_active semantics are UNCHANGED and a zero-guard process stays non-switchable, so keel deactivate keeps its accurate refusal rather than reporting success and changing nothing. The list header now states its population and the split instead of a bare total. The activation-manifest guard's scanned count reads the declared population for the same reason. NOT CHANGED: activation still governs guards, the unit set stays observably narrower than the declared set, and the regression test asserting that relationship still holds.";
        :>> rationale = "The panel rejected the alternative (merge the two catalogues into one computation, gated by a diff) because it would have BROKEN the existing declared_processes_is_every_file_not_only_the_guard_bearing_units test, regressed issue149's recorded conclusion that the defect was the surface and not the mechanism, and added a detector to an engine that already detects more than it triages. This fix is subtractive: it removes a surface's ability to disagree rather than adding a control to notice that it did. One call site into a tested helper, and it closes the portability finding, the discoverability finding and the two-catalogue confusion at once.";
        :>> consequences = "keel process list|search|show|export reach all 23 declared processes; a guard-less process is transferable as a unit. A new regression test (catalogue_reports_every_declared_process_not_only_guard_bearing_units) pins the population and pins that a guard-less row never reads INACTIVE. The vacuous assertion in activation.rs's issue149 test is re-pointed from knowledge-graph-memory - which has since gained an assert constraint, so the assertion passed without exercising the guard-less case - to intake, with a companion assertion that intake really asserts none, so the next capture cannot silently re-hollow it. Resolves issue241. Doc-sync: guards.md's activation-manifest row and CLAUDE.md's portability line ride this commit.";
    }

    // acceptance event (D0121 review-queue sign-off; D0066/D0106 — human-judged, not fabricated)
    verification d0212Accept : Test { :>> id = "3b0ce936-eb55-4640-80f7-e3da3116f428"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/8."; }
    part d0212AcceptR1 : TestResult { :>> id = "cb84a780-c8c9-4b4a-a84e-f0ab6373ead1"; :>> outcome = VerdictKind::pass; :>> judgedAgainst = "bca4265"; :>> judgedAt = "2026-08-24"; :>> judgedBy = "wweatherholtz"; }
}
