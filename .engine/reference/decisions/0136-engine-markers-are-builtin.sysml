// D0136 — The engine's own marker algebra is BUILTIN to the binary; project markers may be declared in
// any project file. Fixes a D0133 regression that blocked a downstream project entirely.
// Marked #ProspectiveChange (D0070): work authored under D0133's stricter reading stays valid.
package ReferenceDecision0136 {
    private import EngineElement::*;
    private import EngineWork::*;
    private import EngineVerification::*;
    private import EngineRelationships::*;

    #ProspectiveChange part d0136 : Decision {
        :>> id = "4d81f0a6-2c37-4e95-b8da-16c05e79b342";
        :>> title = "D0136: the engine's marker algebra is builtin to the binary; project markers declare anywhere in the project";
        :>> createdAt = "2026-08-14";
        :>> createdBy = "claudeOpus5";
        :>> status = DecisionStatus::accepted;
        :>> context = "issue089, REPORTED FROM THE FIELD: another project using keel found D0133 blocking their work, and asked whether that was intended. It was not. Reproduced by simulating their state in this repo — an existing project's on-disk `.engine/schema/` predating D0133 with an upgraded v0.2.0 binary: 566 violations, `keel guard` exit 1, EVERY COMMIT BLOCKED, including on the engine's own shipped files (.engine/rules/rules.sysml). MECHANISM: D0133's `marker-vocabulary` is a HARD guard living in the BINARY, but its passing condition was `metadata def` lines in the PROJECT's schema files. `include_dir!` embeds `.engine` at BUILD time, so a v0.2.0 binary carries the nine declarations D0133 added — while upgrading the binary never touches an existing project's on-disk schema. In THIS repo the guard and the declarations landed in one commit, so the split was invisible; downstream the two version independently and the guard fails closed. TWO AGGRAVATING FACTS: (a) it failed on `#Verify`, `#DerivedFrom`, `#CharteredBy` — the engine's OWN edge algebra, consumed by the binary's OWN guards — so a project was being asked to re-declare the engine's contract back to it; (b) the only apparent remedy was editing `schema/core`, which is FROZEN (§2.5) and needs that project's own human sign-off, so the guard forced every downstream project into a frozen-schema change purely to keep committing. NOTHING about this was an acceptance gap: there was no judgment for a human to supply, only a defect to fix.";
        :>> decision = "(A) The engine's marker algebra becomes a BUILTIN set known to the binary (`ENGINE_MARKERS`): DependsOn, Supersede, OrderingOnly, CharteredBy, Resolves, Verify, DerivedFrom, Measures, Informs, JustifiedBy, Dispositions, Covers, ProspectiveChange, SafetyChange, Capability, ProcessDefect, View. These are always valid with NO project declaration, because they are the engine's CONTRACT — its own guards and views consume them, so the binary owns them. (B) PROJECT-declared markers are scanned from ANY of the project's own `.engine` or `.tracking` files, not only `.engine/schema` — so a downstream project declares its own vocabulary in its own files and never needs to touch frozen `schema/core`. (C) The guard STAYS HARD. With (A) and (B) the only remaining failures are genuine typos or genuinely undeclared project markers, which is exactly the class D0133 existed to catch, and the check is still exact set-membership rather than a heuristic. (D) The violation message no longer directs the reader to edit frozen schema; it distinguishes 'fix the typo' from 'declare your own marker in your own file'. (E) Shipped immediately as a PATCH release, because a downstream team is blocked — which is the first real use of the release discipline established one sprint earlier.";
        :>> rationale = "The engine's algebra is the engine's contract, and a contract must not be a project's obligation to restate. Making the binary own it removes the version-skew failure at the root rather than papering over it with a migration note or a warning level. Keeping the guard HARD matters: D0133's whole value is that a misspelled `#Verify` would silently report a DELIVERED requirement as unverified, and demoting the guard to a warning to escape this regression would have traded a real protection for a bug that has a clean fix. Verified rather than argued: in the reproduced downstream state the violation count goes 566 -> 0 while `#DerivdFrom` still hard-fails with exit 1, so the unblock costs nothing in protection. ALTERNATIVES: (i) demote to warning-only — REJECTED, discards the protection to dodge a fixable defect; (ii) make `keel init`/an upgrade path rewrite the project's schema — REJECTED, the engine must not silently rewrite a project's authored files, and it would not help a project that authored its own `.engine` fresh per D0093; (iii) require projects to declare the engine's markers and document the migration — REJECTED, that is the imposition described above and it fails closed on the engine's own files; (iv) CHOSEN — the binary owns its own vocabulary. GENERAL LESSON, worth more than the fix: a control shipped in the binary must not depend on content the binary cannot guarantee is present or current. This is the same coupling class as issue076 (a gate depending on a runtime that may be absent), arriving through DATA instead of through a runtime — and it was not caught here because in this repo the code and the data always move together.";
        :>> consequences = "`ENGINE_MARKERS` added to keel-cli/src/guards.rs; the project-declaration scan widened from `.engine/schema` + `.engine/workflows` to all of `.engine` + `.tracking`; the violation message rewritten. issue089 resolves. Downstream projects on any schema vintage are unblocked with no action required from them, and a project needing its own marker declares it in its own file with no frozen-schema sign-off. The typo protection is unchanged. Ships as v0.2.1. A unit test asserts every engine marker resolves against an EMPTY project declaration set and that a misspelling still does not, so the builtin set cannot silently regress. Acceptance state is carried by `status` plus the d0136Accept event.";
    }

    verification d0136Accept : Test { :>> id = "8e5c0b23-71fa-4d48-9c06-2af31b98e5d7"; :>> title = "Human acceptance of d0136"; :>> createdAt = "2026-08-14"; :>> createdBy = "claudeOpus5"; :>> method = VerificationMethod::confirmation; :>> procedureText = "wweatherholtz reported the field regression and directed its resolution, 2026-08-14: 'other project using keel say d0133 is now blocking them from doing their work. is this intended? if so, why? if it's just backfilling acceptance, do so now. work to-date is accepted. if it's a legitimate sign off for something, or something else, convince me.' The answer given was that it is NOT intended and NOT an acceptance gap — a hard guard in the binary depended on project-side schema content, so there was no judgment for a human to supply, only a defect to fix. 'work to-date is accepted' covers the sitting's work; this Decision records the remedy adopted on that direction, and the human was told plainly that no sign-off would have unblocked the downstream project."; }
    part d0136AcceptR1 : TestResult { :>> id = "6b09d7e4-5a81-4c32-bf17-90e2c4a63f58"; :>> outcome = VerdictKind::pass; :>> judgedAgainst = "ef08353"; :>> judgedAt = "2026-08-14"; :>> judgedBy = "wweatherholtz"; }
}
