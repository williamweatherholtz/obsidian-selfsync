// =====================================================================
// D0093 — engine-as-product spin-up UX: make the engine ADOPTABLE on a new project via a DUAL-SURFACE,
// AI-driven / human-supervised model. CLI/JSON = authority + automation substrate (the AI agent's
// surface); HTML = the human's oversight lens (orient/review/decide) — one .tracking truth, HTML never
// a second store (renders #Views + wraps the write API). Cold start: `sysmlv2 init` (binary-embedded
// engine tree). First value: a guided, project-based `introduction` process+skill. Human home:
// `sysmlv2 orient --html`. This is the engine declaring itself DONE-AS-A-PRODUCT.
// Accepted 2026-06-22 by wweatherholtz (review dialogue: "Accept as drafted").
// =====================================================================
package ReferenceDecision0093 {
    private import EngineElement::*;
    private import EngineWork::*;
    private import EngineVerification::*;
    private import EngineRelationships::*;

    // D0070: introduces the dual-surface doctrine + new processes (prospective; built via milestones).
    #ProspectiveChange part d0093 : Decision {
        :>> id = "93a4b5c6-1d6e-4f70-a829-516273849593";
        :>> title = "D0093: engine-as-product spin-up UX (dual-surface AI/human; init + introduction + orient-dashboard)";
        :>> createdAt = "2026-06-22";
        :>> createdBy = "wweatherholtz";
        :>> status = DecisionStatus::accepted;
        :>> context = "The engine is functionally complete (schema, processes, skills, decisions, the Rust toolchain, 13 guards, the computed views, the D0092 disposition lifecycle) but has NO productization path: adopting it on a new project means hand-copying files + reading the decision log — the 6-12 month learning-curve / revert-to-spreadsheets adoption cliff that onboarding + MBSE research and the engine's own D0054 name as the #1 failure mode. Two structural facts make this acute: (a) the repo CONFLATES the reusable ENGINE (.engine + binary + CLAUDE.md) with THIS build's INSTANCE (.tracking); (b) the UX is CLI/JSON-first — ideal for the AI AGENT but high-friction for the HUMAN's recurring loops (orient/review/decide), though the existing HTML views (diagram/render/report, D0085-87) already prove the lens pattern. The human asked to design the 'finishing' / spin-up UX, grounded in research.";
        :>> decision = "Adopt a DUAL-SURFACE, AI-driven / human-supervised spin-up architecture. (1) SURFACES (one truth, two lenses): CLI/JSON is the AUTHORITY + automation substrate (the AI agent's primary surface); HTML is the human's ergonomic OVERSIGHT lens (orient/review/decide). HTML NEVER stores truth — it renders computed #Views and wraps the write API (progressive disclosure: minimal human surface, full CLI/model on request). This DUAL-SURFACE invariant joins the section-2 invariants. (2) COLD START: `sysmlv2 init [DIR]` scaffolds a new project from a BINARY-EMBEDDED engine tree (self-contained, like the vendored cytoscape) + CLAUDE.md + a STARTER/empty .tracking + a printed getting-started. (3) ENGINE/INSTANCE BOUNDARY: schema + processes + skills + binary + CLAUDE.md = reusable engine (scaffolded); .tracking (needs/requirements/work/issues/critiques + the new project's OWN decisions) = per-project instance (starter only, never ours). The engine's architecture decisions ship as READ-ONLY engine REFERENCE (design rationale) — a new project authors its own decisions fresh. (4) FIRST VALUE: an `introduction` process + deploying skill (D0059) runs a guided, PROJECT-BASED first session (capture the first business need -> first refine->sprint -> show orient), not a doc dump. (5) HUMAN HOME: `sysmlv2 orient --html` — the recurring dashboard (status + ready frontier + open findings + assurance), drilling down to the CLI/JSON authority.";
        :>> rationale = "Grounded in onboarding research (time-to-first-value in hours not days; project-based learning beats doc dumps, combating analysis-paralysis), MBSE adoption research (learning curve + revert-to-spreadsheets = #1 killer; pilotability / stepwise rollout — 'the best tool is the one adopted successfully'), progressive disclosure (NN/g), and the engine's own D0054 (beat-the-spreadsheet) + section-2.1 (compute-don't-store views) + D0059 (process needs a skill) + D0086/D0087 (the existing HTML view/review/report pattern this EXTENDS, not reinvents). ALTERNATIVES: (A CHOSEN) dual-surface spin-up (init + introduction + orient-html), CLI-authority / HTML-oversight. (B) CLI-only + better docs — REJECTED: leaves the human's high-frequency loops in raw JSON, doesn't lower the adoption cliff. (C) full GUI / human-first authoring — REJECTED for now: a second authoring surface risks bypassing the AI's ENFORCED discipline + a much larger build; HTML stays oversight + write-API-wrapped (revisitable). (D) template repo instead of init — REJECTED: drifts from the binary version. CRITERIA: time-to-first-value x beat-the-spreadsheet x one-truth(no second store) x AI-authority-preserved x self-contained x stepwise-adoptable.";
        :>> consequences = "Milestones (backlog, chartered by D0093): engineInit (`sysmlv2 init [DIR]` + binary-embedded engine tree + getting-started; this milestone RESOLVES the engine/instance boundary CONCRETELY — incl. how the engine's reference decisions ship WITHOUT polluting the new project's instance views (decisions/coverage/critique), e.g. a separate reference location or an exclusion marker) -> introductionProcess (.engine/processes/introduction.sysml + deploying skill) -> orientDashboard (`sysmlv2 orient --html`). Later/optional: a unified console; human-first HTML authoring (revisit option C). Each milestone is a normal sprint. doc-sync (per milestone): CLAUDE.md (a spin-up/adoption section + the dual-surface invariant in section 2), usage.md (init / introduction / orient --html), the viewpoint registry (orient gains an html renderer; an introduction viewpoint). This decision marks the engine's intent to be DONE-AS-A-PRODUCT: spinnable-up on a new project, onboarding its first human+AI pair. ROLLOUT: [2026-06-23] introductionProcess landed — .engine/processes/introduction.sysml (5-step guided onboarding) + the introduction deploying skill (skills-registry) + a usage.md onboarding pointer; this commit co-records the new process-def per the D0070 keystone. engineInit + orientDashboard remain. [2026-06-23] engineInit landed (5a8d9fb — `sysmlv2 init` binary-embedded cold start + engine/instance boundary: decisions->reference, manifest reset; verified live guard-green). [2026-06-23] orientDashboard landed — `sysmlv2 orient --html` human dashboard (computed #View, report-card template) + the dual-surface invariant added to CLAUDE.md section 2 + orient viewpoint renderer updated. D0093 spin-up arc COMPLETE: the engine is spin-up-able (init -> introduction -> orient dashboard).";
    }

    verification d0093Accept : Test { :>> id = "93a4b5c6-1d6e-4f70-b829-516273849593"; :>> method = VerificationMethod::confirmation; :>> procedureText = "wweatherholtz attests acceptance of d0093 (engine-as-product spin-up UX: dual-surface AI-driven/human-supervised — CLI authority + HTML oversight lens, one truth; `sysmlv2 init` binary-embedded cold start; engine/instance boundary with architecture decisions as read-only reference; an introduction process+skill for guided project-based first value; `sysmlv2 orient --html` human dashboard) by selecting 'Accept as drafted' in the D0093 review dialogue on 2026-06-22."; }
    part d0093AcceptR1 : TestResult { :>> id = "93a4b5c6-1d6e-4f70-c829-516273849593"; :>> outcome = VerdictKind::pass; :>> judgedAgainst = "e9c5e43"; :>> judgedAt = "2026-06-22"; :>> judgedBy = "wweatherholtz"; }
    part d0093AcceptR2 : TestResult { :>> id = "8f2d97a9-7588-4a59-b61c-e7fd5c0fa971"; :>> outcome = VerdictKind::pass; :>> judgedAgainst = "eb0adcf"; :>> judgedAt = "2026-09-04"; :>> judgedBy = "wweatherholtz"; :>> createdBy = "claudeOpus5"; :>> notes = "REBOUND (D0308): AUTO-RE-BOUND under standing consent (D0207/D0308): consequences gained a ROLLOUT note at 90b29b8 - editorial, the agreed substance unchanged. Their standing words, verbatim: 'issues raised are automatically accepted. they can be customizedly changed post-fact.'"; }
}
