// D0368 (status: the `status` field below is the truth) — guardsParallel: the enforced guards run across a thread pool in declared order, and every guard and every git run is timed in-process
// Recorded via `keel record decision` (D0105 RMWX axis; issue054). Acceptance is a separate explicit
// human gate (method=confirmation, D0106): flip status + add the d0368Accept event on sign-off.
package ReferenceDecision0368 {
    private import EngineElement::*;
    private import EngineWork::*;
    private import EngineVerification::*;
    private import EngineRelationships::*;

    // #ProspectiveChange (D0070) - this Decision governs a process/schema change; the co-committed
    // change rides the process-change guard's hard lock.
    #ProspectiveChange part d0368 : Decision {
        :>> id = "9abcc964-c62e-410c-9751-93ec57967444";
        :>> title = "guardsParallel: the enforced guards run across a thread pool in declared order, and every guard and every git run is timed in-process";
        :>> createdAt = "2026-09-07";
        :>> createdBy = "claudeOpus5";
        :>> status = DecisionStatus::accepted;
        :>> context = "D0367 measured `keel guard` at 25.5 s on this host with the corpus parsing in 275 ms: the guards ran one after another on a 20-core machine, and the perf line reported `git x56 in 100ms` over 4.4 s of spawns because only two helpers timed their runs (issue410) - so the largest term in issue409 was serial execution and the second-largest was invisible. Rank 1 of D0367 is this change. It touches guards.rs, which is under the keystone lock (D0209 clause 2), so it carries the #ProspectiveChange marker and waits for the human under D0337 while the code is already in the tree behind it. Measured with the same binary shape before and after, a shell timer around `keel guard` on this tree, three runs each: before 30.2, 27.2, 26.6 s; after 14.1, 11.2, 11.7 s; stdout byte-identical apart from the elapsed figure. The run is now bounded by priority-inversion, which re-runs orient::compute whole and is slower under contention (12.8 s in the pool against 6.8 s alone) - the term rank 2 removes.";
        :>> decision = "`guards::run_all` runs the enforced guards across a fixed pool of OS threads (std::thread::scope, one worker per available core, no new dependency) and returns their reports in GUARD_NAMES order exactly as the serial loop did, with the activation filter still running first and serially; each guard runs inside a `perf::phase('guard:<name>')` so KEEL_PERF=2 attributes the run per guard without a measurement patch; and `gitx::git()` returns a wrapper whose `output`, `status` and `spawn` add their wall time to GIT_NANOS on every run, with orient's two batch waits timed at the wait, so `git xN in Nms` is the time git took. NOT A FORK: this is the mechanism D0367 ranked first with its number, and its correctness rests on a stated property - no guard writes a file or sets process state, so the answer per guard is a function of the tree and the pool changes no verdict, which the order and determinism tests pin.";
        :>> rationale = "Parallelism is the one change that removes the largest term with one function and no dependency: the guards were already independent computations over one shared, cached model, and a pool the size of the host does one parse and shares it. The order is preserved by slot, never by finishing time, because every consumer prints or compares the reports positionally and a thread's finishing order is not a fact about the tree. The timing moves into the constructor's wrapper so that no site can build a git command that runs untimed - the same argument that put the COUNT there (dcInstrumentAllGitSites): a coverage-8-percent timer got believed once, and a wrapper at the one constructor is the only shape under which the next site is timed by construction. The clock runs whether or not KEEL_PERF is set because one Instant read is nothing beside a process spawn, and an always-on clock is what a test can pin without racing the lazy env read. One consequence surfaced by the pool and fixed in the same change: a cold burst of twenty callers computed twelve fingerprints (36 tree walks, 6.3 s of thread time) where the serial loop paid one, so fingerprint::of now serialises its compute and looks again under the lock - 3 walks, 139 ms.";
        :>> consequences = "`keel guard`, `keel hook stop`, `keel gate` and the workspace gate answer in roughly the time of their slowest guard instead of the sum. The per-guard phases and the true git time are now permanent instrumentation: the next perf question is answered by KEEL_PERF=2 and no patch. The static test forbidding a raw Command::new('git') outside gitx.rs still holds, and a site needing a builder method the wrapper lacks adds it there rather than reaching the inner Command. What this does NOT do: shorten priority-inversion, which now bounds the run (dcGitFactsAreContentAddressed, rank 2); remove the per-guard corpus reopens (dcOneCorpusPerProcess, rank 3); or skip the run on an unchanged tree (dcGateAnswersFromItsReceipt, rank 4). Sprint 598 records the numbers.";
    }

    // acceptance event (D0121 review-queue sign-off; D0066/D0106 — human-judged, not fabricated)
    verification d0368Accept : Test { :>> id = "9a8b6a9b-d0e6-4807-8158-5623bfdda1be"; :>> method = VerificationMethod::confirmation; :>> procedureText = "their words, 2026-09-08, the copy-for-Claude text of the published brief with their selections marked: '[x] Ratify: the checks run side by side / [ ] Reverse it, run them one after another / [ ] Discuss (answers: d0368)'"; }
    part d0368AcceptR1 : TestResult { :>> id = "ed61fc04-9168-4323-a3f1-926e91056916"; :>> outcome = VerdictKind::pass; :>> judgedAgainst = "a08f2a1"; :>> judgedAt = "2026-09-08"; :>> judgedBy = "wweatherholtz"; :>> createdBy = "claudeOpus5"; }
}
