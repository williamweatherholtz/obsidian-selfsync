// D0172 — PROPOSED. Sprint reviews run three critique passes; a recurring retro finding becomes a
// tracked item; the retro-backlog guard gets tightened so its PASS means what it says.
// #ProspectiveChange (D0070).
package ReferenceDecision0172 {
    private import EngineElement::*;
    private import EngineWork::*;
    private import EngineVerification::*;
    private import EngineRelationships::*;

    #ProspectiveChange part d0172 : Decision {
        :>> id = "4e08c2a7-6b51-4d39-9f24-83ba50ce1d76";
        :>> title = "D0172: the review is an adversarial act and the retro produces tracked work — three critique passes per review, items for recurring findings";
        :>> createdAt = "2026-08-20";
        :>> createdBy = "claudeOpus5";
        :>> status = DecisionStatus::accepted;
        :>> context = "THEIR QUESTION, verbatim: 'are we identifying these recurring issues in sprint retros? we should be. and have sprint reviews with the 3 critique pass and add those items two. new process'. THE HONEST ANSWER WAS NO, WITH EVIDENCE. Retros this session recorded AVOIDABLE-ISSUE lines faithfully - and one failure class, shell-mangled authoring, appears in FIVE retros with zero backlog items, zero controls, and a sixth occurrence the sprint after the fifth. The control that should have forced it, the retro-backlog guard, is satisfied by ANY tracked item co-staged in the commit; every hardening commit staged issues.sysml for its own findings, so the guard passed vacuously throughout (issue189). A retro that only writes lessons is manual vigilance with better formatting, and D0047 already says manual vigilance is not a control. MEANWHILE THE HARDENING SERIES DEMONSTRATED WHAT REVIEWS COULD BE: nine critique passes found sixteen real defects, five of them in code written during the series - but that rigor lived in an ad-hoc series, not in the ceremony that runs every sprint.";
        :>> decision = "PROPOSED: the `review-critique` process, deployed by BOTH ceremony skills (sprint-review and sprint-retro), with four steps. (1) THREE PASSES PER REVIEW - claims checked against computed views and emitted artifacts rather than the code meant to produce them; boundaries probed on a COPY when the probe can write; and the sprint's OWN DIFF searched for defects it introduced, because five of sixteen hardening findings were in series-written code. A pass that finds nothing states what it checked; a skipped pass states why. (2) A REVIEW FINDING BECOMES A TRACKED ITEM BEFORE THE GATE CLOSES - never prose in the gate text, which is D0046's founding rule applied to the ceremony that was exempting itself. (3) THE RETRO ASKS WHETHER AN AVOIDABLE-ISSUE HAS APPEARED BEFORE, and on the second occurrence it becomes a tracked item with a preventing change or carries a recorded reason none is possible. (4) THE GUARD GETS TIGHTENED (dcRetroFindingsAreItems' sibling, dcRetroGuardTiesFinding) so the co-staged item must be tied to THE FINDING rather than to the commit - and until that lands, step 4 says plainly that it is discipline, not enforcement.";
        :>> rationale = "WHY 'SECOND OCCURRENCE' RATHER THAN 'EVERY FINDING': a first occurrence may genuinely be noise, and forcing an item per retro line would produce the warning fatigue issue160 warns about - items nobody reads, satisfying a rule nobody believes. The second occurrence is the moment the finding is proven recurring, which is exactly D0047's trigger. WHY THE THREE PASSES ARE NAMED IN THE PROCESS rather than left to judgment: the hardening series showed my reading is systematically less reliable than a cheap mechanical check (three sprints running, a text control found more instances than I had fixed), and it showed I violate rules I have read unless the rule sits in the path of the work. Naming the passes puts them in the path. WHY BOTH CEREMONY SKILLS DEPLOY IT: the review runs passes 1-3 and the retro runs step 3's recurrence check - splitting the process would recreate the gap where each ceremony assumes the other covers it.";
        :>> consequences = "IF ACCEPTED: every sprint review carries three named passes with findings-or-checked-clean statements; recurring retro findings become work; the guard tightening is tracked as dcRetroGuardTiesFinding. THE COST IS REAL AND STATED: a review gate grows from a paragraph to three, and a genuine second-occurrence finding costs an item even when small - that is the point, and it is also why first occurrences are exempt. THE FIRST TEST OF THE PROCESS IS ITS OWN SPRINT: sprint 372's review gate runs the three passes on this very change, and its retro records the shell-authoring failure class as the tracked item it should have been five retros ago. REMOVAL PATH, per D0163: delete the process file and the two registry purpose references; the ceremony skills revert to their prior text; dcRetroGuardTiesFinding is superseded by a Decision recording the reversal. Nothing else reads it. IF REJECTED: retros keep producing prose, and the sixth occurrence of the heredoc failure becomes the seventh.";
    }

    // acceptance event (D0121 review-queue sign-off; D0066/D0106 — human-judged, not fabricated)
    verification d0172Accept : Test { :>> id = "f8b685c4-293f-4cda-a358-c074d51d5946"; :>> method = VerificationMethod::confirmation; :>> procedureText = "Their words, verbatim: 'accept all. proceed'. Said in response to the queue of six proposed Decisions presented for signature - D0167, D0168, D0169, D0170, D0171, D0172 - so 'all' is that queue and this acceptance covers d0172 as one of the six. For D0170 the acceptance includes the Decision's stated lean, retire."; }
    part d0172AcceptR1 : TestResult { :>> id = "e8063e2c-d846-4187-9dac-d4f5c9ea46da"; :>> outcome = VerdictKind::pass; :>> judgedAgainst = "3abc583"; :>> judgedAt = "2026-08-20"; :>> judgedBy = "wweatherholtz"; }
}
