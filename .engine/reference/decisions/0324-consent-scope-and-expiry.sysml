// D0324 (status: the `status` field below is the truth) — consentScopeAndExpiry: whether standing consent (D0207) binds to the revision of the rule it was granted under, and whether it expires
// Recorded via `keel record decision` (D0105 RMWX axis; issue054). Acceptance is a separate explicit
// human gate (method=confirmation, D0106): flip status + add the d0324Accept event on sign-off.
package ReferenceDecision0324 {
    private import EngineElement::*;
    private import EngineWork::*;
    private import EngineVerification::*;
    private import EngineRelationships::*;

    // RESEARCH: Measured 2026-09-05 in this tree: 111 auto-acceptances under D0207 (grep AUTO-ACCEPTED over .engine/decisions); each names d0207 and quotes the standing words but records neither the commit of the D0207 file nor the guard count (63 today, 49 when D0207 was granted on 2026-08-23) at the moment of acceptance - so nothing in the record says which rule a consent was given under. The knowledge record behind the question: the landscape spike D0282 found every in-path product treating a standing, revision-unbound, non-expiring grant as the artifact to distrust - Entra Agent ID time-bounds grants and re-opens approval on extension; CapLease shows single-use tokens still replay under agent retry unless durable state records the confirmation event and remaining budget - and the untrusted commenter on the override thread (GH#29) asked exactly this. Prior art in this tree: D0207 (the grant, its own text: issues raised are automatically accepted, they can be customizedly changed post-fact), D0290 (override by a superseding Decision), D0289 (override by the quoted word), D0308 (an acceptance binds to the text it signed - the revision-binding shape, applied to Decisions not to consent), D0322 (a fork in substance is held - narrows what consent reaches), stpa-self run 1 UCA-R3 (consent applied too long, ccRecordConsentScoped bound to issue342).
    part d0324 : Decision {
        :>> id = "4753047f-894d-4b05-9c75-210c1c0b34fc";
        :>> title = "consentScopeAndExpiry: whether standing consent (D0207) binds to the revision of the rule it was granted under, and whether it expires";
        :>> createdAt = "2026-09-05";
        :>> createdBy = "claudeOpus5";
        :>> status = DecisionStatus::accepted;
        :>> context = "D0207 grants standing consent: a non-fork Decision is accepted at record time in the human's name. The grant names no revision and no end. Since it was given, the rule set it operates under has changed - 14 guards added, record-time acceptance moved into the binary (D0291), the fork detector widened (D0322) - and 111 Decisions have been accepted under it. The override thread is the escape valve the human chose (D0207 clause 2, D0290). The landscape spike found that every comparable product distrusts exactly this artifact: a standing, revision-unbound, non-expiring grant. issue342 names the gap; stpa-self run 1 bound CC-R3 to it. This is a FORK: it decides how much of the human's own future the human is pre-committing, which only they can weigh.";
        :>> decision = "OPTION A (keep as is, and say why): the grant stays revision-unbound and non-expiring; the override thread and the quoted word remain the escape valves; this Decision records that the human chose it knowingly and the auto-acceptance note cites this Decision. COST: nothing to build; the record still cannot say which rule a consent was given under, so a later weakening of the rule set silently widens what earlier consent covers - the D0282 finding stands unanswered, stated rather than fixed. OPTION B (stamp the revision, informational): every auto-acceptance records the D0207 file's commit and the guard count at the moment of acceptance in its note; `keel show attestation` splits auto-acceptances by the revision they were given under; nothing lapses, nothing is refused. COST: a note format change and a census column - a day; the reader can see pre-revision consents but nothing acts on them. OPTION C (bind consent to the revision): a change to the D0207 file, or a weakening of the guard set (audit-adherence's own signal), LAPSES standing consent - `keel record decision` records proposed and says why - until the human re-grants it with their quoted word; the re-grant is a Decision with a #Supersede edge to the lapsed one, so the chain of consents is readable. COST: B's stamping plus the lapse check in the record path, a re-grant command, and the interruptions - every deliberate change to the consent rule or the guard set pauses autonomy until the human speaks once; guards.rs changed on 13 of the 14 days since the grant. OPTION D (an expiry the human sets): D0207 gains a duration in attestation-policy.toml (say 14 days); auto-acceptance refuses after it until the human renews with a quoted word; a renewal is a Decision. COST: a policy field, a date check, a renewal command; the human is asked on a calendar rather than on a change, which D0204 (nothing owed to the human on a schedule) argues against.";
        :>> rationale = "WHY NOT DECIDE THIS AUTONOMOUSLY: it is the human's own pre-commitment, and every option except A costs them interruptions in a pattern they must choose. WHAT I RECOMMEND, AND WHAT WOULD CHANGE IT: OPTION B now, with C's lapse rule scoped to the D0207 file alone - not to every guard-set change - as the second Decision if the human wants a control rather than a record. The D0282 finding is about a grant nobody can date; B dates it at near-zero cost and makes the census show what each consent covered. C on the guard set would have paused autonomy on 13 of the last 14 days, which is the hammering the human said they do not want (st065), while C on the D0207 file alone pauses only when the consent's own words change, which is when a human should be asked. D asks on a calendar, which this project's governance never does to the human (D0204). It stops recommending B if the human says the record is not enough and they want autonomy to pause on a rule change (then C, file-scoped), or if they want the grant to end without their act (then D).";
        :>> consequences = "Until accepted: nothing changes; dcConsentIsScopedAndExpires's DoD is this proposal and passes when judgment-request-quality accepts it and the fork is surfaced. On B: the auto-acceptance note gains the D0207 commit and guard count; attestation gains a column; CC-R3 (ccRecordConsentScoped) binds to the stamp. On C: a second Decision for the lapse and re-grant. On A or D: as stated. issue342 is resolved by this item's delivery either way.";
    }

    // acceptance event (D0121 review-queue sign-off; D0066/D0106 — human-judged, not fabricated)
    verification d0324Accept : Test { :>> id = "aa26381e-5321-4c17-92d5-0249195bc556"; :>> method = VerificationMethod::confirmation; :>> procedureText = "their words, verbatim: 'd0324 - standing consent is scoped only to the existing processes under which it was promulgated' - not one of the four lettered options; recorded as the human's own answer and delivered as D0337"; }
    part d0324AcceptR1 : TestResult { :>> id = "7e894f7b-c2be-4528-bb8c-84f4e82ffe1a"; :>> outcome = VerdictKind::pass; :>> judgedAgainst = "9a726d2"; :>> judgedAt = "2026-09-05"; :>> judgedBy = "wweatherholtz"; :>> createdBy = "claudeOpus5"; }
}
