// D0163 — PROPOSED. A Decision that adds a capability must say how it comes back out. Written because
// the human asked how a feature gets unplugged if they dislike it after implementation, and the engine
// had no answer for ANY feature — only for a process that happens to assert a guard.
// #ProspectiveChange (D0070): adds a required clause to the decision-authoring process and a
// warning-level control. Derives no requirement yet.
package ReferenceDecision0163 {
    private import EngineElement::*;
    private import EngineWork::*;
    private import EngineVerification::*;
    private import EngineRelationships::*;

    #ProspectiveChange part d0163 : Decision {
        :>> id = "f4c07e29-5b83-4d16-9a70-38e15c9b6a74";
        :>> title = "D0163: a Decision that adds a capability must state its REMOVAL path";
        :>> createdAt = "2026-08-19";
        :>> createdBy = "claudeOpus5";
        :>> status = DecisionStatus::accepted;
        :>> context = "THE HUMAN ASKED THREE QUESTIONS ABOUT THE KNOWLEDGE GRAPH - is creating it a process, can it be updated, can it be UNPLUGGED if they dislike it after implementation - and the third had no answer. UPDATING was already well covered: a process change is marked `#ProspectiveChange` or `#SafetyChange`, which makes its Decision a version boundary the engine computes against, so `keel governing-version <item>` reports which version governed any recorded work and `keel reprocess-candidates` computes what to redo. UNPLUGGING was not. `keel deactivate` exists (D0138) but switches GUARDS, so it only reaches a process that asserts a constraint - 6 of this repository's 18 processes - and it reaches no FEATURE at all: a command and a directory have no switch, no owner, and nothing in the model saying how they come out. I CHECKED WHETHER THIS WAS SPECIFIC TO D0161 AND IT IS NOT. Nothing in `.engine/decisions/` states a removal path for anything it added. 162 Decisions have each answered 'what if we do this' and 'what if we do not', and none has answered 'what if we do this and then want it gone' - which is the question a user actually asks after adoption, and the one that decides whether they trust adopting anything. The engine is careful about how capability ARRIVES (Change Request, acceptance, doc-sync, a guard) and silent about how it LEAVES.";
        :>> decision = "PROPOSED, TWO PARTS. PART 1 - A REQUIRED CLAUSE. The `decision-authoring` process gains a step: a Decision that adds a user-visible capability - a command, a directory, an item type, a hook, a guard - must state in its `consequences` HOW THE CAPABILITY IS REMOVED, at whichever of three levels applies. DATA: the capability is inert without authored input, so deleting the input removes the effect and nothing else must happen (the cheapest kind, and a reason to prefer designs shaped this way). DECLARED: the capability is bound to a process that asserts a constraint, so `keel deactivate <process>` turns it off and `keel activation` reports it INACTIVE. CODE: removal is an ordinary §3a CHANGE with doc-sync, which must be SAID rather than left implicit, because 'you can always delete the code' is true of everything and therefore informative about nothing. A Decision may also state that removal is NOT supported, with the reason - an honest answer that the reader can weigh, unlike silence. PART 2 - A WARNING-LEVEL CONTROL, `removal-path`, following D0102's promote-once-low-noise pattern: a Decision marked `#ProspectiveChange` or `#SafetyChange` whose `consequences` field carries no removal statement is REPORTED and never blocks. Warning-level and keyword-scanned, exactly like the retro gate's existing scan-evidence check, because whether prose adequately describes a rollback is judgment-bound and a hard gate on a heuristic would be gamed by adding the word 'remove'. Its purpose is to make the omission VISIBLE at authoring time, not to certify the answer. FORWARD-ONLY: existing Decisions are not retro-failed (issue068), so the check applies from its introduction commit.";
        :>> rationale = "WHY THIS IS NOT CEREMONY. A tool that is easy to adopt and impossible to abandon is a tool people refuse to adopt, and the refusal happens quietly, before any conversation. This repository already knows the failure in its harder form: D0132 records a kernel validator that could only be turned off ALL-OR-NOTHING, so it was turned off - and took every other validation layer with it. That is what an unremovable control costs, and it cost more than the control was worth. Stating the exit at authoring time is the cheap version of the same lesson. WHY WARNING AND NOT HARD, against my own sprint-344 reasoning for making `impossible-evidence-date` hard: that guard checks whether a recorded fact is POSSIBLE, which is arithmetic and cannot be judged. This one checks whether prose is ADEQUATE, which is judgment, and a hard gate on judgment gets satisfied rather than met. D0102's pattern exists for exactly this distinction. WHY THE THREE LEVELS RATHER THAN ONE RULE: they are not equally good and the ranking is the useful part. A capability that is inert without authored input needs no mechanism at all, which makes 'can this be shaped so its input is authored?' a design question worth asking BEFORE building - and in D0161's case asking it produced a better design than the one before it. WHAT THIS DECISION OWES ITSELF: it adds a control, so it must state its own removal path, and it does - see consequences. A policy that exempted itself would be the clearest possible evidence it was ceremony.";
        :>> consequences = "IF ACCEPTED: one step added to the decision-authoring process, one warning-level guard (37 guards, 27 hard, 10 warning), a doc-sync obligation on `.engine/docs/guards.md` and CLAUDE.md's guard count in the same commit, and every future capability-adding Decision carries an exit. THE COST IS ONE PARAGRAPH PER DECISION, and the benefit is that the question is asked while the design is still soft - which is when it can change the design, as it did for D0161. REMOVAL PATH FOR THIS DECISION ITSELF, at the DECLARED and CODE levels: the guard belongs to the `decision-authoring` process unit, which already asserts constraints, so `keel deactivate decision-authoring` turns it off and `keel activation` reports it INACTIVE - no code change and no rebuild. To remove it entirely, drop it from GUARD_NAMES and delete the process step, an ordinary §3a CHANGE with doc-sync; nothing else depends on it, it stores no state, and no recorded fact becomes unreadable if it disappears. IF REJECTED: the recorded position is that capability removal stays undocumented per feature and answered case by case - which is survivable for a single-user tool and not for the downstream adoption D0157 contemplates, so a rejection should say which of those two futures it is choosing.";
    }

    // acceptance event (D0121 review-queue sign-off; D0066/D0106 — human-judged, not fabricated)
    verification d0163Accept : Test { :>> id = "f621e159-2072-4dbe-921f-dab4985bf1b9"; :>> method = VerificationMethod::confirmation; :>> procedureText = "ACCEPT - submitted in the obligations deck review of 2026-08-20 (verdict recorded with no per-item note)"; }
    part d0163AcceptR1 : TestResult { :>> id = "6b956c77-0c96-4763-af8b-675a971d075d"; :>> outcome = VerdictKind::pass; :>> judgedAgainst = "b7e000d"; :>> judgedAt = "2026-08-20"; :>> judgedBy = "wweatherholtz"; }
}
