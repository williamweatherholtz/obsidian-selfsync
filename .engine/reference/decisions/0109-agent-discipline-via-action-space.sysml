// =====================================================================
// D0109 — pursue AI-agent discipline through ACTION-SPACE constraints
// (typed tools / process-launcher / validated I/O), realized as keel's interaction boundary, NOT through
// a general AI frontend, `claude -p`, or a "more rigorous skill" alone. Output of the sprint194 research
// spike (docs/proposals/2026-07-06-ai-discipline-levers.md). Drafted for the human's decision.
// =====================================================================
package ReferenceDecision0109 {
    private import EngineElement::*;
    private import EngineWork::*;
    private import EngineVerification::*;
    private import EngineRelationships::*;

    part d0109 : Decision {
        :>> id = "09a1b0c1-4109-42a3-ab5c-516273849709";
        :>> title = "D0109 (PROPOSED): agent discipline via action-space constraints (keel's boundary), not a general frontend / claude -p / skill-alone";
        :>> createdAt = "2026-07-06";
        :>> createdBy = "claudeOpus";
        :>> status = DecisionStatus::accepted;
        :>> context = "The human wants less freeform AI interpretation + more structured carrying-out — tired of agents that stray, ignore processes, don't document, 'do what they said they wouldn't' (a REAL, evidenced failure: D0106 was violated after adoption; issue058 dual-truth; a premature 'close as covered'). Candidate fixes floated: a frontend app that launches tasks + validates format; `claude -p` to cut prompt overhead; a more rigorous input-interpretation skill. Research (sprint194) assessed which actually buys discipline. Key finding (the human's own strong-typing-vs-stringly-typing analogy): a SKILL is a linter (soft, ignorable — engine-triage + D0106's Parsed: block were still violated); TYPED TOOLS / a process-launcher / schema-validated I/O are the compiler (invalid actions unrepresentable). `claude -p` does NOT reduce injected system-prompt overhead (same agent/prompt; scriptable + subscription-billed); only a custom Agent-SDK harness owns the prompt, and enterprise auth generally can't be delegated to third-party 'lite' harnesses.";
        :>> decision = "Pursue discipline through ACTION-SPACE levers (hard -> soft): (1) a process-launcher — invoke DEFINED processes/skills, not freeform prompts; show the parse/route + approve-before-execute (this STRUCTURALLY closes D0106's conversational residual that a commit gate cannot — issue059); (2) generation-time schema-validated I/O + repair loop (reject malformed AI output at the boundary, auto-retry, before commit); (3) short single-purpose context decomposition (agents drift with long/diffuse context); (4) the input-interpretation skill (engine-triage) as the SOFT backstop, not the primary control. Realize these as the MATURATION of `keel serve` (keel's existing interaction boundary, D0093 dual-surface) over the already-declared model — NOT a new general AI IDE, NOT `claude -p` overhead-cutting, NOT 'a more rigorous skill' as the main fix.";
        :>> rationale = "ALTERNATIVES: (i) a general freeform AI frontend — REJECTED (competes with Claude Code/Cursor; scope; and a UI over a still-freeform agent is lipstick — discipline is in the model, not the UI). (ii) `claude -p` for less overhead — REJECTED (wrong lever: same system prompt; the SDK is the only prompt-owning path, with enterprise-auth friction). (iii) a more rigorous input skill alone — REJECTED as sufficient (softest lever; engine-triage already exists + D0106 already emits Parsed: and was still violated). (iv) CHOSEN — action-space constraints at keel's boundary: matches the strong-typing insight (make invalid actions unrepresentable), reuses keel's model + `keel serve` surface (one source of truth, subscription billing), and uniquely closes the issue059 conversational residual. Friction (D0054) is acceptable here — single-user tool by the human's statement. CRITERIA: hard-not-soft-control x reuses-existing-model x closes-issue059-residual x avoids-scope-blowup x honest-about-claude-p.";
        :>> consequences = "UPON ACCEPTANCE: scope the work as `keel serve` increments (process-launcher + approve-before-execute; generation-time schema-validation + repair loop; small-context task decomposition), tracked via the Business/Architecture workflows (needs-before-architecture, business-architecture skill — would also close issue061). NOT a separate project unless it outgrows serve. The input-interpretation skill stays the soft backstop. OPEN FORKS for the human: build order (launcher first vs validator first); harness (extend serve vs a separate SDK app). Supersedes nothing; informs the frontend idea. Acceptance verdict/provenance are the discrete d0109Accept TestResult (not prose, D0058/issue058). Full research: docs/proposals/2026-07-06-ai-discipline-levers.md.";
    }

    verification d0109Accept : Test { :>> id = "09a1b0c1-4109-42a3-bb5c-516273849709"; :>> method = VerificationMethod::confirmation; :>> procedureText = "wweatherholtz attests acceptance of D0109 (pursue agent discipline via action-space constraints at keel's boundary — process-launcher + validated I/O + short context — not a general frontend / claude -p / skill-alone) via the explicit 'yes for d0109' on 2026-07-06, after the sprint194 research spike. The build-order + harness forks remain the human's to decide before implementation."; }
    part d0109AcceptR1 : TestResult { :>> id = "09a1b0c1-4109-42a3-cb5c-516273849709"; :>> outcome = VerdictKind::pass; :>> judgedAgainst = "37931c2"; :>> judgedAt = "2026-07-06"; :>> judgedBy = "wweatherholtz"; }
}
