// D0235 (status: the `status` field below is the truth) — renameIsAChange: my own fix to the keystone lock opened a git-mv bypass in every repository, and an adversarial panel found it within the hour
// Recorded via `keel record decision` (D0105 RMWX axis; issue054). Acceptance is a separate explicit
// human gate (method=confirmation, D0106): flip status + add the d0235Accept event on sign-off.
package ReferenceDecision0235 {
    private import EngineElement::*;
    private import EngineWork::*;
    private import EngineVerification::*;
    private import EngineRelationships::*;

    // #SafetyChange (D0070) - this Decision governs a process/schema change; the co-committed
    // change rides the process-change guard's hard lock.
    #SafetyChange part d0235 : Decision {
        :>> id = "dd9934e8-9155-4a76-80e8-89c68004027f";
        :>> title = "renameIsAChange: my own fix to the keystone lock opened a git-mv bypass in every repository, and an adversarial panel found it within the hour";
        :>> createdAt = "2026-08-26";
        :>> createdBy = "claudeFable5";
        :>> status = DecisionStatus::accepted;
        :>> context = "An adversarial panel was convened on D0234. PEDANT-3 found that yesterday's fix to issue272 - narrowing the keystone lock from `--diff-filter=ACMR` to `MD` so a freshly scaffolded project could make its first commit - DROPPED R, renames, which ACMR had included. Reproduced on a plain SINGLE-PROJECT repo, so this was live in every repository including this one and penumbra, not confined to the new workspace path I had just built: `sed s/blocking/warning/ .engine/rules/rules.sysml > rules2.sysml; rm rules.sysml; git add -A` presents git with `R096`, the MD filter matches nothing, and `keel guard process-change` reports PASS - 0 scanned. Every blocking rule in a project downgraded to a warning by a `git mv`, with no signed Decision. The same panelist found a second blindness in the same function: git C-QUOTES a path containing a non-ASCII byte in this output while `rev-parse --show-prefix` does not, so a project named `proj` with a circumflex was invisible to the workspace gate AND to its own guards, and a full rules downgrade there passed too. I had told the human there was no live exposure. That was wrong.";
        :>> decision = "The keystone lock reads `MDR` - modified, deleted, AND renamed - never a bare `A`, which remains the issue272 fix. The staged-path reader is rewritten to take BOTH sides of a rename, because `--name-only` prints only a rename's destination: the source matters (a locked file left its path) and so does the destination (a locked file arrived carrying modified content). It now calls git with `-c core.quotePath=false` and `-z`, parsing NUL-separated `--name-status -M` records, so the bytes it compares against `--show-prefix` are the same bytes git used.";
        :>> rationale = "The narrowing was correct in its intent and wrong in its reach. What the lock must ask is whether a control was WEAKENED or REMOVED without a signature; an addition is a control arriving, which is why A stays exempt, but a rename is the most direct possible weakening - it is a modification wearing a new path, and git reports it as neither M nor D. Reading `--name-only` was the deeper error: a filter over a projection that hides one half of the very operation being policed. `--name-status` with both paths makes the question answerable. The C-quoting fix belongs in the same change because it is the same mistake in the same function - comparing two git outputs that quote differently - and leaving it would mean a second control gap in code I was already editing.";
        :>> consequences = "A legitimate rename of a locked file now requires a signed Decision, which is more friction than yesterday and is the correct amount: moving a process definition IS a process change. The `core.quotePath=false` plus `-z` parsing changes the staged-path reader for every guard that uses it, not only the keystone, so any guard that was silently skipping non-ASCII paths now sees them - a behaviour change in the direction of seeing more. VERIFIED both ways rather than asserted: the rename downgrade now FAILS with both paths named (2 scanned, 1 violation) where it passed before; a fresh `keel init` plus `git add -A` plus commit still SUCCEEDS through the scaffolded hook, so the issue272 fix survives. STATED PLAINLY: this defect existed because I weakened a control and did not test the weakening against the class of change it was meant to keep catching. The panel that found it also found that `audit-adherence`, which I named as the compensating control for the A exemption, is blind in a multi-project repo - so the compensation I cited did not exist there either. That is recorded separately as its own issue rather than repaired here. Resolves issue273.";
    }

    // acceptance event (D0121 review-queue sign-off; D0066/D0106 — human-judged, not fabricated)
    verification d0235Accept : Test { :>> id = "eb0416ec-16ec-4f05-b9a2-d8ae76ec37ca"; :>> method = VerificationMethod::confirmation; :>> procedureText = "agreed with panel's decisions [recorded by the human in the keel console, stated by them on 2026-08-26 when asked which surface they used - their words above are unaltered; this bracket is the CHANNEL citation delegatedAcceptanceSubstanceRule requires, and the console now appends it automatically (issue287)]"; }
    part d0235AcceptR1 : TestResult { :>> id = "0bcf922e-48b4-47c9-a006-919dad1a16e2"; :>> outcome = VerdictKind::pass; :>> judgedAgainst = "ddba1cd"; :>> judgedAt = "2026-08-26"; :>> judgedBy = "wweatherholtz"; }
    // MERGE 2026-08-27 (keel sync keep-both rule): the same acceptance also fired through the GitHub
    // standing-consent channel (D0207) before the console record above was pushed. Same verdict, same
    // judge, same day, different channel - both facts kept; the standing-consent pair renamed so names
    // do not collide. The console record above is the individually-reviewed acceptance.
    verification d0235AcceptStanding : Test { :>> id = "fe95dae1-c332-40e7-a55e-83bb8bcd0f16"; :>> method = VerificationMethod::confirmation; :>> procedureText = "AUTO-ACCEPTED under standing consent (D0207). Their standing words, verbatim: 'issues raised are automatically accepted. they can be customizedly changed post-fact.' Not individually reviewed; override anytime by replying 'reject <why>' on https://github.com/williamweatherholtz/sysmlv2-ai-toolkit/issues/29."; }
    part d0235AcceptStandingR1 : TestResult { :>> id = "25851b03-1ea5-45e6-8615-479971cd31d5"; :>> outcome = VerdictKind::pass; :>> judgedAgainst = "ddba1cd"; :>> judgedAt = "2026-08-26"; :>> judgedBy = "wweatherholtz"; }
}
