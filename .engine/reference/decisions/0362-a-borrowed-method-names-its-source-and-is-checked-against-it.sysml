// D0362 (status: the `status` field below is the truth) — borrowedMethodsCiteTheirSource: a process that borrows an external method names its source of record and is periodically checked against it
// Recorded via `keel record decision` (D0105 RMWX axis; issue054). Acceptance is a separate explicit
// human gate (method=confirmation, D0106): flip status + add the d0362Accept event on sign-off.
package ReferenceDecision0362 {
    private import EngineElement::*;
    private import EngineWork::*;
    private import EngineVerification::*;
    private import EngineRelationships::*;

    // #ProspectiveChange (D0070) - this Decision governs a process/schema change; the co-committed
    // change rides the process-change guard's hard lock.
    #ProspectiveChange part d0362 : Decision {
        :>> id = "c846a416-5d72-4e34-969c-dd9ce690377b";
        :>> title = "borrowedMethodsCiteTheirSource: a process that borrows an external method names its source of record and is periodically checked against it";
        :>> createdAt = "2026-09-07";
        :>> createdBy = "claudeOpus5";
        :>> status = DecisionStatus::accepted;
        :>> context = "Several processes here are local summaries of somebody else's method: STPA from the Leveson-Thomas handbook, the propriety lenses from mutation testing and control validation, the executive brief from Minto and Zelazny, the retrieval benchmark's statistics from McNemar. A summary is what an agent actually follows, and nothing has ever checked a summary against the thing it summarises. On 2026-09-07 the owner asked whether the STPA work should have included controlled processes and the rest. Reading the handbook - fetched, and read at pages 22 to 26 - showed that page 25 states a control structure 'contains at least five types of elements: Controllers, Control Actions, Feedback, Other inputs to and outputs from components (neither control nor feedback), Controlled processes'. Our SOP named four. The consequence was not one careless run: an agent following a reference that names four types produces four types every time, and this project's model accordingly had zero of the fourth class, no schema type able to express it, zero sensors, zero actuators and no representation of a control algorithm - while the missing fourth class is precisely where 'the measurement was taken against the wrong thing' belongs. The defect had been in the reference since it was written, invisible because every run of the process conformed to it perfectly.";
        :>> decision = "A process that borrows an external method records its SOURCE OF RECORD - the document, its authors, its edition or date - and the date its local summary was last checked against that source; a summary older than the declared interval is reported as UNVERIFIED against its source rather than assumed faithful. NOT A FORK: the alternative is to keep summarising without a back-reference, which is the state that hid a missing element type for as long as the reference existed, and there is no third option - either the summary is checked against its source or it is trusted because it reads well.";
        :>> rationale = "The failure mode is specific and it is not carelessness: a local summary is INTERNALLY consistent, every run conforms to it, and no gate can notice an omission because the omission is in the standard being enforced. That makes it invisible to every control this project has - guards check the model against the rules, and the rules were wrong. The only thing that finds it is comparison with the source, which costs twenty minutes and is exactly what nobody schedules. Recording the source turns 'somebody should check' into a date that ages, which is the same mechanism `stpa-currency` already uses for an analysis that has fallen behind its control structure - a currency claim, not a correctness claim, because whether a summary is FAITHFUL is a judgment and only whether it was RECENTLY COMPARED can be computed.";
        :>> consequences = "Each borrowing process gains two authored facts and an aging date, and the reference set becomes auditable: a reader can see which summaries have been compared with their sources and when. The interval is per process rather than global, because a stable standard and a moving one deserve different cadences. The cost is real and small: a comparison is a read of the source against the summary, and the STPA one took twenty minutes and produced a missing element type, a wrong step-2 gate, and three findings the project had never been able to see. WHAT THIS DOES NOT DO: it does not make a summary faithful, and it cannot - a comparison performed badly reports the same green as one performed well, which is why the recorded fact is the DATE of the comparison and the person who made it, never a verdict that the summary is correct.";
    }

    // acceptance event (D0121 review-queue sign-off; D0066/D0106 — human-judged, not fabricated)
    verification d0362Accept : Test { :>> id = "01b1adba-cbcd-44d5-9961-f61480775c16"; :>> method = VerificationMethod::confirmation; :>> procedureText = "their words, 2026-09-08, the copy-for-Claude text of the published brief with their selections marked: '[x] Accept the rule / [ ] Not worth the ceremony / [ ] Discuss (answers: d0362)'"; }
    part d0362AcceptR1 : TestResult { :>> id = "fa62331e-e692-4123-a9eb-70b777de89c6"; :>> outcome = VerdictKind::pass; :>> judgedAgainst = "a08f2a1"; :>> judgedAt = "2026-09-08"; :>> judgedBy = "wweatherholtz"; :>> createdBy = "claudeOpus5"; }
}
