// D0135 — Operationalise the Deploy workflow (a release PROCESS + skill, a recorded Release), and trim
// CLAUDE.md to the behaviour-changing core with the catalogues moved to reference docs.
// Marked #ProspectiveChange (D0070): work done under the prior docs/release arrangement stays valid.
package ReferenceDecision0135 {
    private import EngineElement::*;
    private import EngineWork::*;
    private import EngineVerification::*;
    private import EngineRelationships::*;

    #ProspectiveChange part d0135 : Decision {
        :>> id = "e6b19d70-4a52-4c8f-91b3-05fd7e2a6c84";
        :>> title = "D0135: operationalise the Deploy workflow; trim CLAUDE.md to the behaviour-changing core";
        :>> createdAt = "2026-08-14";
        :>> createdBy = "claudeOpus5";
        :>> status = DecisionStatus::accepted;
        :>> context = "The human asked to take the process creation-and-sharing idea to a new project and, if ready, to 'do proper release with updated documentation, focusing on concision and really trimming down what we're doing here to the core critical elements AI should be using this project for'. TWO findings. (1) READINESS: process creation-and-sharing is NOT ready — nProcessPortability has three SystemRequirements and no delivered work; there is no `keel process list/import/export/activate` and no activation manifest. What works today is `keel init`, which spins up the WHOLE engine all-or-nothing. That was reported plainly rather than papered over, because a release implying otherwise would mislead the very project it was made for. (2) RELEASE DISCIPLINE was the honest gap D0128 named: the Deploy workflow was DEFINED but never run — one GitHub release six weeks stale at v0.1.0, no recorded `Release` item, and version discipline left to memory, while the engine governs Deploy for others. The release WORKFLOW already existed and was complete (per-platform builds attached on a `v*` tag); what was missing was the process, the cadence, the record, and the first real run. (3) DOCS: CLAUDE.md had grown to 522 lines / 45KB and is injected as context every single turn. Its §5 alone was a 120-line guard catalogue, and §3 still RESTATED the response contract that D0130 had moved to the output style — the dual truth tracked as issue086.";
        :>> decision = "(A) RELEASE PROCESS: add `.engine/processes/deploy.sysml` — reconcile version, gate the exact tree to be tagged, tag so CI publishes per-platform binaries, record the `Release` — with a deploying `release` skill (D0059). Cadence is PER-MILESTONE, never per-sprint. 'Reconcile' is defined explicitly as each version surface being deliberate, NOT equal: the crate version tracks the shipped binary while `KEEL_API_VERSION` is a separate contract a downstream viewer pins and bumps only on a breaking `/api/*` read shape. (B) CUT v0.2.0 as the first real run, and record it as a `Release` item; release CONTENTS stay a computed view over git ancestry, never hand-listed. (C) DOCS TRIMMED: CLAUDE.md 522 -> ~184 lines (45KB -> 12KB, a 73% byte reduction), reorganised to the behaviour-changing core — invariants, orient, the routing table, working rules, the validation commands, environment. The 120-line guard catalogue MOVES to `.engine/docs/guards.md` (moved, not deleted). The restated response contract is REMOVED outright, which resolves issue086 by making the output style the single home in fact and not merely in principle. Also corrected: a pre-existing broken doc reference (`keel-syntax-notes.md`, actually `sysmlv2-syntax-notes.md`).";
        :>> rationale = "CLAUDE.md is paid for on EVERY turn, which makes its length a recurring tax on every future session rather than a one-off tidiness question — and a 45KB file competes with the actual task for attention, which is the same attention-dilution argument that moved the response contract into the system prompt (D0130). Trimming by MOVING rather than deleting keeps the catalogue available to anyone who needs it while removing it from the per-turn cost; the guard table is also more usable as a table than as dense prose. On the release: a defined-but-never-run workflow is exactly the dogfooding failure this engine exists to expose, and it now blocks a real dependency — srDcEngineVersionParity (D0129) needs published, pinnable versions for a distributed team to pin TO, and srRelPublishedArtifact needs a downloadable binary so a contributor gets a matching gate without a Rust toolchain. ALTERNATIVE REJECTED on readiness: cut the release and describe process-sharing as available-ish. Refused — the human's stated purpose for the release was to use it on a new project for exactly that feature, so overstating it would cause the specific harm the release was meant to avoid. The honest answer (the engine is usable today; à-la-carte process selection is not built) is more useful than a reassuring one.";
        :>> consequences = "Adds `.engine/processes/deploy.sysml` + the `release` skill; bumps the crate to 0.2.0; records the v0.2.0 `Release` item in `.tracking/baselines.sysml`. CLAUDE.md drops to ~184 lines with `.engine/docs/guards.md` as the catalogue; issue086 RESOLVES because the restated contract is gone rather than merely deprecated. keelReleaseProcess and issue070 resolve. NOT delivered and explicitly still open: nProcessPortability's three SystemRequirements (srPortModularProcessUnit, srPortActivationManifest, srPortCatalogExchange) — process creation-and-sharing remains unbuilt, and `keel init` remains all-or-nothing. A downstream project can adopt keel whole today; it cannot yet take one process à la carte. Acceptance state is carried by `status` plus the d0135Accept event.";
    }

    verification d0135Accept : Test { :>> id = "7c04e2b8-9153-4d6a-ae27-3b8f01d5947e"; :>> title = "Human acceptance of d0135"; :>> createdAt = "2026-08-14"; :>> createdBy = "claudeOpus5"; :>> method = VerificationMethod::confirmation; :>> procedureText = "wweatherholtz directed this work on 2026-08-14: 'let's reach a good stopping point - i want to implement this process creation & sharing idea on a new project. it ready to use? if so, do proper release with updated documentation, focusing on concision and really trimming down what we're doing here to the core critical elements AI should be using this project for.' The direction authorises the release and the doc trim; the readiness question was answered NEGATIVELY for process creation-and-sharing (unbuilt) and that answer is recorded in this Decision's context rather than glossed, so the acceptance covers a release that does NOT include the feature the human asked about."; }
    part d0135AcceptR1 : TestResult { :>> id = "1f9a63c5-7de0-4821-b64f-a05c2e738d19"; :>> outcome = VerdictKind::pass; :>> judgedAgainst = "425145d"; :>> judgedAt = "2026-08-14"; :>> judgedBy = "wweatherholtz"; }
}
