// D0413 (status: the `status` field below is the truth) — guardWarningsStateTwoClasses: the guard runner states its warning population as two classes - actionable warnings a reader is asked to read, and counted-history lines that are not - and orient carries the actionable ones in its burndown
// Recorded via `keel record decision` (D0105 RMWX axis; issue054). Acceptance is a separate explicit
// human gate (method=confirmation, D0106): flip status + add the d0413Accept event on sign-off.
package ReferenceDecision0413 {
    private import EngineElement::*;
    private import EngineWork::*;
    private import EngineVerification::*;
    private import EngineRelationships::*;

    // #ProspectiveChange (D0070) - this Decision governs a process/schema change; the co-committed
    // change rides the process-change guard's hard lock.
    #ProspectiveChange part d0413 : Decision {
        :>> id = "f2417cf5-48cf-4132-9c56-7cb7a2f776f7";
        :>> title = "guardWarningsStateTwoClasses: the guard runner states its warning population as two classes - actionable warnings a reader is asked to read, and counted-history lines that are not - and orient carries the actionable ones in its burndown";
        :>> createdAt = "2026-09-09";
        :>> createdBy = "claudeOpus5";
        :>> status = DecisionStatus::accepted;
        :>> context = "issue404, tracked as dcGuardWarningsAreActionable. Under D0214 clause 1 the verdict line read 'ALL PASS - 131 warning(s) across 12 guard(s), NOT violations and NOT blocking, but UNREAD until someone reads them'. The count rose six times during one session, from 38 to 131, as work landed. Several of those lines are undischargeable by design - 52 legacy actor references in immutable history, resolutions before the naming cutoff, grandfathered thin attestations and compound Decisions, a sprint closed before its ceremony existed - and counting rather than enumerating them was sound; it was also the mechanism, because a set holding permanent noise cannot be read as a set worth reading, so the actionable warnings inherited the noise's fate. Nothing in the report distinguished the two classes; a reader had to know which lines were history.";
        :>> decision = "NOT A FORK: the DoD names one property and forbids the alternative (promotion to violations, D0088). A guard that reports immutable history constructs the line with guards::history_line, which carries the HISTORY prefix; GuardReport::actionable and GuardReport::history partition the warnings on that mark; the printer labels a history line HISTORY instead of WARN; each guard's summary counts its actionable warnings and appends its counted-history lines as a separate number; the runner's verdict line states the actionable count with the guards carrying them first, and the counted-history count with its guards second, never summed; and keel orient's burndown carries guard_warnings - the actionable count, the counted-history count and per guard the count, its first line and the command that lists the rest - read from the guard receipt for this tree and null with a how line when no green receipt covers the tree. Classification is the guard's declaration, never a reading of the prose. This reverses D0214's clause 1 wording alone; D0214's clause 2 (a superseded Release stops warning) stands.";
        :>> rationale = "The number a reader is asked to act on must be the number they can act on. History counted beside it inflates the population until the summary trains blindness to the warnings that name a fixable condition, which is the exact failure D0214 set out to end. Marking at construction rather than classifying at print keeps one home for the fact: the guard that knows a line is history says so where it writes the line, and every reader - printer, runner, orient - reads the same mark. Orient carries the actionable set because that is where work is chosen (D0052), so a warning an edit can discharge appears beside the other work rather than in a runner summary read at commit time.";
        :>> consequences = "keel-cli/src/guards.rs gains HISTORY_PREFIX, history_line, is_history, GuardReport::actionable and GuardReport::history, warning_population and a labelled printer; five counted-history sites (actors, ceremony, issues, attestation-substance, decision-scaffolding) construct their lines with history_line; main.rs's runner summary is warning_population; view/mod.rs's burndown gains guard_warnings from the receipt; three unit tests carry the probe pair and the live actor guard; .engine/docs/guards.md states the two classes. Guard source and the runner are the enforcement surface (D0209 clause 2), so this Decision is the co-committed change record and, as a process change, stays proposed for the human (D0337). STATED LIMIT: a guard that reports history without history_line is counted actionable until it is marked; the mark is opt-in per site and no check enumerates the unmarked sites.";
    }
    #SupersedeClause dependency from d0413 to d0214;

    // acceptance event (D0121 review-queue sign-off; D0066/D0106 — human-judged, not fabricated)
    verification d0413Accept : Test { :>> id = "f8023094-96c1-4624-b2ad-61f90df718fa"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0413 (D0201 B); recorded as given (D0423)."; }
    part d0413AcceptR1 : TestResult { :>> id = "fe5c94fd-73aa-4e69-8747-d967f5989ff5"; :>> outcome = VerdictKind::pass; :>> judgedAgainst = "3e6c518"; :>> judgedAt = "2026-09-11"; :>> judgedBy = "wweatherholtz"; :>> createdBy = "claudeOpus5"; }
}
