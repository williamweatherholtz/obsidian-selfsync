// D0440 (status: the `status` field below is the truth) — keystoneGuardsReadTheWorkingTreeOutsideAHook: the guards that read the staged index read the working tree instead when no commit hook is running, so a verifier and the commit see one verdict
// Recorded via `keel record decision` (D0105 RMWX axis; issue054). Acceptance is a separate explicit
// human gate (method=confirmation, D0106): flip status + add the d0440Accept event on sign-off.
package ReferenceDecision0440 {
    private import EngineElement::*;
    private import EngineWork::*;
    private import EngineVerification::*;
    private import EngineRelationships::*;

    // #ProspectiveChange (D0070) - this Decision governs a process/schema change; the co-committed
    // change rides the process-change guard's hard lock.
    #ProspectiveChange part d0440 : Decision {
        :>> id = "fb57fb23-ae90-4317-8bcf-4502101c5579";
        :>> title = "keystoneGuardsReadTheWorkingTreeOutsideAHook: the guards that read the staged index read the working tree instead when no commit hook is running, so a verifier and the commit see one verdict";
        :>> createdAt = "2026-09-10";
        :>> createdBy = "claudeOpus5";
        :>> status = DecisionStatus::accepted;
        :>> context = "Seven guards answer from the staged index: process-change, doc-sync, decision-amends-process, retro-backlog, ownership, the marked-Decision probe the workspace gate uses, and the added-item scan retro-backlog relies on. All of them read git diff --cached, because the commit is what the keystone lock governs (D0070, D0209 clause 2). On 2026-09-10 the D0425 verifier ran keel guard --no-receipt over a tree whose sprint edits were not yet staged and reported ALL PASS; the pre-commit hook then refused the same edits on process-change once git add had run (issue464, High). The verifier had read an empty index and called it a clean tree. Every guard run outside a hook - the turn-boundary stop hook, a verifier, a human at the terminal - has the same blind spot: a locked-file edit is invisible until the moment it is staged. A pre-commit hook receives GIT_INDEX_FILE from git in both the plain and the -a commit shape (probed 2026-09-10 in a scratch repository), and no keel process outside a git hook receives it.";
        :>> decision = "NOT A FORK: this makes one read answer the same question in both places. When keel runs inside a git hook - GIT_INDEX_FILE is set by git, or KEEL_HOOK is set by a caller that is the commit gate - the seven guards read the staged index exactly as today. When neither is set they read the working tree: git diff HEAD --name-status -M with the same filters, plus every untracked file under the project as an addition, and a file's text is read from disk rather than from the index blob. Each affected guard's summary line names which read it made - (read: index) or (read: working tree) - so a receipt states what population it judged. A staged-only read outside a hook is no longer offered.";
        :>> rationale = "The lock exists so that a control cannot change without a signed Decision; whether the edit has been staged is a fact about the author's shell, not about the control. A verifier that reads the index judges a tree the author has not shown it, and the D0425 split depends on the verifier's verdict being the commit's verdict - otherwise the primary learns the refusal from the hook after the recorder has already written the sprint. Reading the working tree outside the hook makes a locked-file edit a violation the moment it exists, which is when a reader can still act on it cheaply. Inside the hook the index remains the right population because a partially staged file is committed as its index blob, not as its disk text. The untracked set must count as additions or the authorising Decision - almost always a new file - would be invisible, and every properly signed change would read as unsigned. What would change it: a hook shape git runs without GIT_INDEX_FILE, in which case KEEL_HOOK is the caller's declaration and the scaffolded hook would set it.";
        :>> consequences = "guards.rs gains one read-mode function that every former staged_changes and staged_files caller and the added-item scan go through, and one blob reader that reads the index inside a hook and disk outside it. The GuardReport summary line carries the read mode for the guards that consult it; status.rs does not count that line as a warning. Process-change (D0337): guard source is the enforcement surface (D0209 clause 2), so this Decision waits for the human's word and the commit carries it marked. issue464 resolves through dcGuardReadsTheWorkingTreeOutsideTheHook. The D0388 pair: a fixture repository with an unstaged .engine/processes edit and no Decision fails process-change before staging (known-positive - today it passes), the same tree with an unstaged marked Decision beside it passes (known-negative), and the existing process-change tests run with GIT_INDEX_FILE set prove the staged read unchanged. What accepting binds: a guard run outside a hook judges the tree on disk. What it forecloses: a green guard over edits nobody has staged.";
    }

    // acceptance event (D0121 review-queue sign-off; D0066/D0106 — human-judged, not fabricated)
    verification d0440Accept : Test { :>> id = "54baa576-3595-48d2-83b4-52cb6b28507f"; :>> method = VerificationMethod::confirmation; :>> procedureText = "Selected on the decision brief copy-out (fifteenth publish), pasted into chat 2026-09-11: the set of 33 HELD process-change ratifications accepted with one word, this record being one member (D0406 named it in the table). No note added. - their words, verbatim: “Accept the set: each of the 33 rules named in the table is recorded accepted on its own, quoting these words (recommended)” WARN: read-back - the quoted words do not name d0440 (D0201 B); recorded as given (D0423)."; }
    part d0440AcceptR1 : TestResult { :>> id = "a1500b63-8198-40f5-8a90-58b038f763ca"; :>> outcome = VerdictKind::pass; :>> judgedAgainst = "3e6c518"; :>> judgedAt = "2026-09-11"; :>> judgedBy = "wweatherholtz"; :>> createdBy = "claudeOpus5"; }
}
