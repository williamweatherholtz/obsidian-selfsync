// =====================================================================
// ProjectAcceptance — the requirement-verification traceability layer (CR d0011, 2026-07-05).
// Before this, tier-satisfaction showed SR-verified-by-Test at 0/15: the 125 automated tests
// were entirely divorced from the requirements model, so nothing enforced that a requirement
// had a behavioral test — which is how the multi-device config divergence/removal defects
// (0.10.4) shipped untested. This package authors the `#Verify` edges (Test -> SystemRequirement)
// that were missing: existing SRs are verified by their existing delivery DoD Tests; the four
// new config-sync SRs get explicit Given/When/Then ACCEPTANCE scenarios (the two that would have
// caught the escape are called out), backed by the reconcile suite green at the 0.10.4 fix commit.
// =====================================================================
package ProjectAcceptance {
    private import EngineElement::*;
    private import EngineVerification::*;
    private import ProjectRequirements::*;
    private import ProjectDelivery::*;
    private import ProjectUseCases::*;
    // 2026-09-11 panel (SE2): six #Verify edges removed — their DoDs did not exercise the SR they were said to verify
    // (residualLowFindings→sr3, mountHardeningR3→sr6, postR2FunctionAudit→sr9, mountHardeningR4→sr14, mountHardeningR1→sr17,
    // mountHardeningR6→sr23); each SR keeps at least one legitimate edge.
    private import ProjectStpaAuthorities::*;   // same-device / release-channel authorities STPA sr44..sr51 (stpa-authorities.sysml)
    private import ProjectStpaNesting::*;       // nesting STPA SafetyRequirements sr29..sr43 (stpa-nesting.sysml)
    private import ProjectStpaAnalysis::*;      // STPA SafetyRequirements sr1..sr25 (stpa-ucas.sysml)

    // ---- new config-sync acceptance scenarios (BDD) ----
    verification acConfigSelective : Test {
        :>> id = "c0f1a5cc-3001-4a10-9b20-a1b2c3d40021"; :>> method = VerificationMethod::test;
        :>> location = "client/test/configsync.test.ts";
        :>> procedureText = "GIVEN config sync with a per-category selection WHEN shouldSync classifies a path THEN notes always sync, each .obsidian category syncs only when opted in, unrecognized .obsidian files never sync, and SelfSync's own/legacy plugin folder never syncs — the 32-combo matrix + the e2e per-dial + own-folder tests are green.";
    }
    verification acConfigAdditiveSafe : Test {
        :>> id = "c0f1a5cc-3002-4a10-9b20-a1b2c3d40022"; :>> method = VerificationMethod::test;
        :>> location = "client/test/reconcile.test.ts";
        :>> procedureText = "GIVEN device A has a plugin and device B never installed it WHEN both sync THEN B receives it (defer to data) and it is never removed from A; AND a filtered/never-held path records no base and can never manufacture a deletion; AND a genuine removal from a device that HELD the file propagates (auto-remove, D0013) while a removed file is never auto-pulled-back. Reconcile tests 'accepts=false skipped entirely', 'no phantom delete', 'additive pull', and 'removal -> PROPAGATES' (both directions) are green.";
    }
    verification acConfigAdjudication : Test {
        :>> id = "c0f1a5cc-3003-4a10-9b20-a1b2c3d40023"; :>> method = VerificationMethod::test;
        :>> location = "client/test/reconcile.test.ts";
        :>> procedureText = "SCENARIO (would have caught the crash): GIVEN two devices with different community-plugins.json WHEN they sync THEN neither list is overwritten, NO note-style conflict copy is created, and the SAME-FILE difference is queued for user adjudication. Reconcile tests 'divergence -> adjudicate, no crash/no garbage copy' and the resolveConfigConflict local/remote cases are green. (Removals propagate, not adjudicate — see acConfigAdditiveSafe.)";
    }
    verification acConfigLiveDetect : Test {
        :>> id = "c0f1a5cc-3006-4a10-9b20-a1b2c3d40026"; :>> method = VerificationMethod::inspect;
        :>> location = "client/src/main.ts";
        :>> procedureText = "Inspected: the plugin registers vault.on('raw', ...) (feature-detected) and, for in-scope .obsidian/ paths, debounces the event burst (600ms), suppresses the echo of its own writes/removes (markConfigSelfWrite, 4s window), and reconciles the changed paths via reconcilePath — so a config change syncs promptly (event-driven) on desktop. onRemoteChanged's periodic full reconcile remains the mobile fallback + safety net (Obsidian mobile does not fire 'raw' reliably for hidden files). On-device latency confirmed under L4.";
    }
    verification acSyncRobust : Test {
        :>> id = "c0f1a5cc-3004-4a10-9b20-a1b2c3d40024"; :>> method = VerificationMethod::test;
        :>> location = "client/test/reconcile.test.ts";
        :>> procedureText = "GIVEN one file throws during reconcile WHEN reconcileAll runs THEN that file's error is reported and skipped and every other file still syncs — the 'per-file isolation' reconcile test is green.";
    }
    // ── Batch 1: continuous-sync reliability ──
    verification acServerApi : Test {
        :>> id = "c0f1a5cc-3211-4a10-9b20-a1b2c3d40211"; :>> method = VerificationMethod::test;
        :>> location = "client/test/e2e.spec.ts";
        :>> procedureText = "e2e (real server) exercises the health ping, login, create + list vault, and changes/commit/get across two clients; server cargo tests cover put/delete-chunk + argon2id auth — green.";
    }
    verification acInstantPush : Test {
        :>> id = "c0f1a5cc-3212-4a10-9b20-a1b2c3d40212"; :>> method = VerificationMethod::inspect;
        :>> location = "server/src/ws.rs";
        :>> procedureText = "Inspected: the server broadcasts a change notification on commit over the WebSocket channel and the client subscribes and reconciles on notify, so a remote change reflects near-real-time rather than only on the next poll.";
    }
    verification acIncrementalSync : Test {
        :>> id = "c0f1a5cc-3213-4a10-9b20-a1b2c3d40213"; :>> method = VerificationMethod::test;
        :>> location = "client/test/e2e.spec.ts";
        :>> procedureText = "e2e sequential edits each propagate in order via the version-cursor incremental path (changes(since=version)); an idle poll with no server advance does the cheap check only — green.";
    }
    verification acSelfHealingReconnect : Test {
        :>> id = "c0f1a5cc-3214-4a10-9b20-a1b2c3d40214"; :>> method = VerificationMethod::inspect;
        :>> location = "client/src/main.ts";
        :>> procedureText = "Inspected: reconnect() is single-flight (connecting guard), backs off on failure, restarts polling + WS on success, and ceases after unload; a failed poll hands off to scheduleReconnect.";
    }
    // ── Batch 2: data-safety + durability ──
    verification acDegradedServerGuard : Test {
        :>> id = "c0f1a5cc-3215-4a10-9b20-a1b2c3d40215"; :>> method = VerificationMethod::test;
        :>> location = "client/test/reconcile.test.ts";
        :>> procedureText = "Reconcile tests: C2 refuses bulk delete-local when the server manifest is empty but base is non-empty (batch + event paths), and still honors a legit delete-local when the server has other files; e2e 'deleting the LAST file leaves the peer's copy intact' — green.";
    }
    verification acDurableIndex : Test {
        :>> id = "c0f1a5cc-3216-4a10-9b20-a1b2c3d40216"; :>> method = VerificationMethod::test;
        :>> location = "server/src/vault.rs";
        :>> procedureText = "Server tests: commits/deletes append absolute journal records; replay reconstructs on reopen; a torn trailing record is discarded; a malformed complete record errors; chunk-refs recompute from files; compaction snapshots + truncates — green.";
    }
    // ── Batch 3: large-file performance ──
    verification acStreamedTransfer : Test {
        :>> id = "c0f1a5cc-3217-4a10-9b20-a1b2c3d40217"; :>> method = VerificationMethod::test;
        :>> location = "client/test/reconcile.test.ts";
        :>> procedureText = "Reconcile + e2e: a >=8MiB download streams to disk (base hash-only) and bypasses the buffered size gate; without an appendWrite io it's skipped; a too-large file fires onSkip once; e2e large binary (~4MB) syncs byte-identical + dedups a copy; mapPool bounds parallel transfer — green.";
    }
    verification acResumableInitialSync : Test {
        :>> id = "c0f1a5cc-3218-4a10-9b20-a1b2c3d40218"; :>> method = VerificationMethod::test;
        :>> location = "client/test/reconcile.test.ts";
        :>> procedureText = "Reconcile test 'is idempotent — a second reconcile re-downloads nothing': after a first pass pulls the files, a second reconcile performs zero writes (all in-sync via base + chunk cache), so an interrupted sync resumes rather than restarts. Full-scale on-device resume under load stays an L4 check.";
    }
    // ── Batch 4: vault management + onboarding ──
    verification acVaultSwitch : Test {
        :>> id = "c0f1a5cc-3219-4a10-9b20-a1b2c3d40219"; :>> method = VerificationMethod::test;
        :>> location = "client/test/reconcile.test.ts";
        :>> procedureText = "switchTo tests: download (target wins, drops local-only, resets stale base), upload (local wins, drops target-only), merge (union, conflict-copies divergence, nothing lost), and download-into-empty (auto). Config exclusion holds (io.list is filtered) — green.";
    }
    verification acSetupLink : Test {
        :>> id = "c0f1a5cc-3220-4a10-9b20-a1b2c3d40220"; :>> method = VerificationMethod::test;
        :>> location = "client/test/connstr.test.ts";
        :>> procedureText = "connstr tests: encode/parse round-trips server+user (+optional vault), preserves scheme/port, canonicalizes default ports, and the encoded link contains NO password/secret; invalid links are rejected — green.";
    }
    verification acDeviceIdentity : Test {
        :>> id = "c0f1a5cc-3221-4a10-9b20-a1b2c3d40221"; :>> method = VerificationMethod::test;
        :>> location = "client/test/devicename.test.ts";
        :>> procedureText = "devicename.test.ts covers the extracted parsing: usableModel gates the UA-Client-Hints model (accepts 'Pixel 9', rejects ''/undefined/'K'); a real Android UA yields the model; a frozen 'K', a model-less Android UA, and desktop UAs yield null; platformDisplayName strips architecture tokens so 'Linux aarch64' can never surface (the actual Android bug). The async UA-CH resolution (getHighEntropyValues), its cache, and the Platform.* fallback ordering in autoDeviceName + the iOS iPhone/iPad ceiling are inspected (D0015).";
    }
    // ── Batch 5: config completeness + sharing/admin split ──
    verification acConfigReload : Test {
        :>> id = "c0f1a5cc-3222-4a10-9b20-a1b2c3d40222"; :>> method = VerificationMethod::inspect;
        :>> location = "client/src/main.ts";
        :>> procedureText = "Inspected: a config write queues the path via onConfigWritten and flushConfigReload asks Obsidian to reload the affected surface (plugins/appearance/hotkeys/snippets) so a pulled change applies without a manual restart (best-effort). On-device confirmed at L3/L4.";
    }
    verification acConfigAdjudicationUI : Test {
        :>> id = "c0f1a5cc-3223-4a10-9b20-a1b2c3d40223"; :>> method = VerificationMethod::test;
        :>> location = "client/test/configgroup.test.ts";
        :>> procedureText = "groupConfigConflicts collapses a plugin's files into one 'Plugin: <id>' entry, keeps distinct plugins separate, and labels non-plugin files by purpose ('Enabled community plugins', 'Hotkeys', 'Theme: X') — unit-tested. Inspected: the badge counts GROUPS, ConfigConflictModal resolves a whole group in one click (Use this device / Use synced), and the count self-clears — resolveConfigGroup + onConfigResolved prune entries + settingsRefresh re-renders, and the periodic reconcile prunes any stale entry.";
    }
    verification acReadOnlyGating : Test {
        :>> id = "c0f1a5cc-3224-4a10-9b20-a1b2c3d40224"; :>> method = VerificationMethod::test;
        :>> location = "client/test/reconcile.test.ts";
        :>> procedureText = "Read-only reconcile tests: no upload of a local-only file, still pulls the owner's files, no delete-remote, and on divergence the owner's version is canonical while the local edit is kept as a LOCAL-only copy (nothing pushed); sharing-e2e confirms read-only pulls but never pushes — green.";
    }
    verification acRegistrationPolicy : Test {
        :>> id = "c0f1a5cc-3225-4a10-9b20-a1b2c3d40225"; :>> method = VerificationMethod::test;
        :>> location = "server/src/registration.rs";
        :>> procedureText = "Server tests: closed registration rejects open sign-up; open allows it; a single-use invite token (hashed) is accepted exactly once and rejected on reuse — green.";
    }
    verification acAdminSurface : Test {
        :>> id = "c0f1a5cc-3226-4a10-9b20-a1b2c3d40226"; :>> method = VerificationMethod::test;
        :>> location = "server/src/admin.rs";
        :>> procedureText = "Server admin tests: /api/admin/* requires an admin role, manages accounts + shares, and responses never include password hashes or session tokens — green.";
    }
    // ── Human on-device attestations (wweatherholtz, 2026-07-05, against 0.10.7) ──
    verification acInstantPushConfirm : Test {
        :>> id = "c0f1a5cc-3301-4a10-9b20-a1b2c3d40301"; :>> method = VerificationMethod::confirmation;
        :>> procedureText = "wweatherholtz attests: a change made on one device appears on the other near-instantly (WebSocket push), not only on a poll — observed on his own devices running 0.10.7.";
    }
    verification acSelfHealingReconnectConfirm : Test {
        :>> id = "c0f1a5cc-3302-4a10-9b20-a1b2c3d40302"; :>> method = VerificationMethod::confirmation;
        :>> procedureText = "wweatherholtz attests: after a dropped connection / server blip the plugin reconnects on its own with no user action — observed on 0.10.7.";
    }
    verification acConfigAdjudicationUIConfirm : Test {
        :>> id = "c0f1a5cc-3303-4a10-9b20-a1b2c3d40303"; :>> method = VerificationMethod::confirmation;
        :>> procedureText = "wweatherholtz attests: hit a genuine config divergence and resolved it through the 'Config differences' modal, picking a side — observed on 0.10.7.";
    }
    // ── Data-safety: tombstone-authoritative deletion (the 0.10.25 field-escape regression) ──
    verification acTombstoneAuthoritativeDelete : Test {
        :>> id = "c0f1a5cc-3401-4a10-9b20-a1b2c3d40341"; :>> method = VerificationMethod::test;
        :>> location = "client/test/reconcile.test.ts";
        :>> procedureText = "SCENARIO (would have caught the field data-loss): GIVEN a populated local vault with a saved base WHEN it reconciles against a WRONG / FRESH / RESTORED server that lacks those files but has issued NO deletion tombstones THEN every local file is RESTORED (pushed back), none deleted; AND a SECOND reconcile against that now-non-empty server still deletes nothing (durable, not a one-shot guard); AND a file the server GENUINELY tombstoned IS removed locally; AND a partial-shrink server (many files missing, no tombstones) restores rather than mass-deletes. The fake server models tombstones (deletions[] with versions), and the 'DATA-LOSS REGRESSION: two reconciles against a wrong/empty server never delete local files' + 'RESTORES...no tombstone' + 'delete-local PROPAGATES a real server tombstone' + 'DI-1 partial-shrink' reconcile tests are green.";
    }
    verification acFreeMerge : Test {
        :>> id = "c0f1a5cc-3005-4a10-9b20-a1b2c3d40025"; :>> method = VerificationMethod::inspect;
        :>> procedureText = "Inspected: neither the plugin nor the server contains a licence/payment/sponsorship gate on any sync, conflict, or merge capability — all reconciliation is available to every user.";
    }
    // ── Grantee-side sharing: redeem a share LINK (incl. must-change onboarding) + leave/decline ──
    verification acRedeemAndLeaveShare : Test {
        :>> id = "c0f1a5cc-3402-4a10-9b20-a1b2c3d40342"; :>> method = VerificationMethod::test;
        :>> location = "client/test/sharing-e2e.spec.ts";
        :>> procedureText = "e2e (real server) 'must-change account -> change password -> redeem a share LINK -> sync the shared vault': an admin-created (must-change) recipient logs in (must_change signalled; /api/vaults 403), changes password (200), the owner mints a readWrite share LINK, the recipient REDEEMS it (grant bound; appears in listShared), syncs the owner-qualified vault and reads the note; a SECOND redeem of the same link is rejected (single-use); then the grantee LEAVES (DELETE /api/shared) -> the owner-qualified route is 200 before and 403 after, and the vault is gone from listShared. Green (2 tests) against the debug server binary. Client parse/decision units (sharelink.test redeemTargetError + percent-encoded link) + the guided-redeem wizard must-change flow (modals-ui.dom) are also green.";
    }

    part acConfigSelectiveR1 : TestResult { :>> id = "c0f1a5cc-4001-4a10-9b20-a1b2c3d40031"; :>> outcome = VerdictKind::pass; :>> judgedAgainst = "db1b008"; :>> judgedAt = "2026-07-05"; :>> judgedBy = "ai"; }
    part acConfigAdditiveSafeR1 : TestResult { :>> id = "c0f1a5cc-4002-4a10-9b20-a1b2c3d40032"; :>> outcome = VerdictKind::pass; :>> judgedAgainst = "af8b722"; :>> judgedAt = "2026-07-05"; :>> judgedBy = "ai"; }
    part acConfigAdjudicationR1 : TestResult { :>> id = "c0f1a5cc-4003-4a10-9b20-a1b2c3d40033"; :>> outcome = VerdictKind::pass; :>> judgedAgainst = "af8b722"; :>> judgedAt = "2026-07-05"; :>> judgedBy = "ai"; }
    part acSyncRobustR1 : TestResult { :>> id = "c0f1a5cc-4004-4a10-9b20-a1b2c3d40034"; :>> outcome = VerdictKind::pass; :>> judgedAgainst = "db1b008"; :>> judgedAt = "2026-07-05"; :>> judgedBy = "ai"; }
    part acFreeMergeR1 : TestResult { :>> id = "c0f1a5cc-4005-4a10-9b20-a1b2c3d40035"; :>> outcome = VerdictKind::pass; :>> judgedAgainst = "db1b008"; :>> judgedAt = "2026-07-05"; :>> judgedBy = "ai"; }
    part acTombstoneAuthoritativeDeleteR1 : TestResult { :>> id = "c0f1a5cc-4401-4a10-9b20-a1b2c3d40341"; :>> outcome = VerdictKind::pass; :>> judgedAgainst = "a9f2ee7"; :>> judgedAt = "2026-07-06"; :>> judgedBy = "ai"; }
    part acRedeemAndLeaveShareR1 : TestResult { :>> id = "c0f1a5cc-4402-4a10-9b20-a1b2c3d40342"; :>> outcome = VerdictKind::pass; :>> judgedAgainst = "d46a9ac"; :>> judgedAt = "2026-07-12"; :>> judgedBy = "ai"; }
    part acConfigLiveDetectR1 : TestResult { :>> id = "c0f1a5cc-4006-4a10-9b20-a1b2c3d40036"; :>> outcome = VerdictKind::pass; :>> judgedAgainst = "d6c0325"; :>> judgedAt = "2026-07-05"; :>> judgedBy = "ai"; }
    part acServerApiR1 : TestResult { :>> id = "c0f1a5cc-4211-4a10-9b20-a1b2c3d40311"; :>> outcome = VerdictKind::pass; :>> judgedAgainst = "5364968"; :>> judgedAt = "2026-07-05"; :>> judgedBy = "ai"; }
    part acInstantPushR1 : TestResult { :>> id = "c0f1a5cc-4212-4a10-9b20-a1b2c3d40312"; :>> outcome = VerdictKind::pass; :>> judgedAgainst = "5364968"; :>> judgedAt = "2026-07-05"; :>> judgedBy = "ai"; }
    part acIncrementalSyncR1 : TestResult { :>> id = "c0f1a5cc-4213-4a10-9b20-a1b2c3d40313"; :>> outcome = VerdictKind::pass; :>> judgedAgainst = "5364968"; :>> judgedAt = "2026-07-05"; :>> judgedBy = "ai"; }
    part acSelfHealingReconnectR1 : TestResult { :>> id = "c0f1a5cc-4214-4a10-9b20-a1b2c3d40314"; :>> outcome = VerdictKind::pass; :>> judgedAgainst = "5364968"; :>> judgedAt = "2026-07-05"; :>> judgedBy = "ai"; }
    part acDegradedServerGuardR1 : TestResult { :>> id = "c0f1a5cc-4215-4a10-9b20-a1b2c3d40315"; :>> outcome = VerdictKind::pass; :>> judgedAgainst = "5364968"; :>> judgedAt = "2026-07-05"; :>> judgedBy = "ai"; }
    part acDurableIndexR1 : TestResult { :>> id = "c0f1a5cc-4216-4a10-9b20-a1b2c3d40316"; :>> outcome = VerdictKind::pass; :>> judgedAgainst = "5364968"; :>> judgedAt = "2026-07-05"; :>> judgedBy = "ai"; }
    part acStreamedTransferR1 : TestResult { :>> id = "c0f1a5cc-4217-4a10-9b20-a1b2c3d40317"; :>> outcome = VerdictKind::pass; :>> judgedAgainst = "5364968"; :>> judgedAt = "2026-07-05"; :>> judgedBy = "ai"; }
    part acResumableInitialSyncR1 : TestResult { :>> id = "c0f1a5cc-4218-4a10-9b20-a1b2c3d40318"; :>> outcome = VerdictKind::pass; :>> judgedAgainst = "912722b"; :>> judgedAt = "2026-07-05"; :>> judgedBy = "ai"; }
    part acVaultSwitchR1 : TestResult { :>> id = "c0f1a5cc-4219-4a10-9b20-a1b2c3d40319"; :>> outcome = VerdictKind::pass; :>> judgedAgainst = "5364968"; :>> judgedAt = "2026-07-05"; :>> judgedBy = "ai"; }
    part acSetupLinkR1 : TestResult { :>> id = "c0f1a5cc-4220-4a10-9b20-a1b2c3d40320"; :>> outcome = VerdictKind::pass; :>> judgedAgainst = "5364968"; :>> judgedAt = "2026-07-05"; :>> judgedBy = "ai"; }
    part acDeviceIdentityR1 : TestResult { :>> id = "c0f1a5cc-4221-4a10-9b20-a1b2c3d40321"; :>> outcome = VerdictKind::pass; :>> judgedAgainst = "a504d0c"; :>> judgedAt = "2026-07-05"; :>> judgedBy = "ai"; }
    part acConfigReloadR1 : TestResult { :>> id = "c0f1a5cc-4222-4a10-9b20-a1b2c3d40322"; :>> outcome = VerdictKind::pass; :>> judgedAgainst = "5364968"; :>> judgedAt = "2026-07-05"; :>> judgedBy = "ai"; }
    part acConfigAdjudicationUIR1 : TestResult { :>> id = "c0f1a5cc-4223-4a10-9b20-a1b2c3d40323"; :>> outcome = VerdictKind::pass; :>> judgedAgainst = "d7fb9f5"; :>> judgedAt = "2026-07-05"; :>> judgedBy = "ai"; }
    part acReadOnlyGatingR1 : TestResult { :>> id = "c0f1a5cc-4224-4a10-9b20-a1b2c3d40324"; :>> outcome = VerdictKind::pass; :>> judgedAgainst = "5364968"; :>> judgedAt = "2026-07-05"; :>> judgedBy = "ai"; }
    part acRegistrationPolicyR1 : TestResult { :>> id = "c0f1a5cc-4225-4a10-9b20-a1b2c3d40325"; :>> outcome = VerdictKind::pass; :>> judgedAgainst = "5364968"; :>> judgedAt = "2026-07-05"; :>> judgedBy = "ai"; }
    part acAdminSurfaceR1 : TestResult { :>> id = "c0f1a5cc-4226-4a10-9b20-a1b2c3d40326"; :>> outcome = VerdictKind::pass; :>> judgedAgainst = "5364968"; :>> judgedAt = "2026-07-05"; :>> judgedBy = "ai"; }
    // human on-device attestations
    part acInstantPushConfirmR1 : TestResult { :>> id = "c0f1a5cc-4301-4a10-9b20-a1b2c3d40331"; :>> outcome = VerdictKind::pass; :>> judgedAgainst = "912722b"; :>> judgedAt = "2026-07-05"; :>> judgedBy = "wweatherholtz"; }
    part acSelfHealingReconnectConfirmR1 : TestResult { :>> id = "c0f1a5cc-4302-4a10-9b20-a1b2c3d40332"; :>> outcome = VerdictKind::pass; :>> judgedAgainst = "912722b"; :>> judgedAt = "2026-07-05"; :>> judgedBy = "wweatherholtz"; }
    part acConfigAdjudicationUIConfirmR1 : TestResult { :>> id = "c0f1a5cc-4303-4a10-9b20-a1b2c3d40333"; :>> outcome = VerdictKind::pass; :>> judgedAgainst = "912722b"; :>> judgedAt = "2026-07-05"; :>> judgedBy = "wweatherholtz"; }

    // ---- embedded-timestamp / conflict-noise acceptance scenarios (BDD, 2026-07-29) ----
    verification acEmbeddedTimestamp : Test {
        :>> id = "d7c13001-0000-4a10-9b20-a1b2c3d40031"; :>> method = VerificationMethod::test;
        :>> location = "client/test/frontmatter.test.ts";
        :>> procedureText = "GIVEN a note with NO managed timestamp fields WHEN SelfSync first seeds it THEN `created` is initialized from the file's existing creation time and `updated` from its modification time (TFile.stat / OS metadata), NOT the current time (falling back to now only if stat is unavailable), injecting a frontmatter block when missing; AND GIVEN a managed note WHEN SelfSync detects a genuine content change THEN it stamps `updated` (ISO-8601 with offset); AND stamping the managed field does not change the normalized hash (no re-sync loop). Verified by frontmatter.test.ts (seed-from-OS-metadata, stamp-on-genuine-change, inject-when-absent, offset format) + reconcile.test.ts (no loop).";
    }
    verification acNormalizedIdentity : Test {
        :>> id = "d7c13002-0000-4a10-9b20-a1b2c3d40032"; :>> method = VerificationMethod::test;
        :>> location = "client/test/frontmatter.test.ts";
        :>> procedureText = "GIVEN two note versions identical except the managed timestamp keys WHEN their normalized hashes are computed THEN the hashes are equal (managed keys masked, key order + EOL normalized); AND non-markdown / unparseable-YAML files fall back to the raw hash. Verified by the frontmatter.test.ts normalized-hash table.";
    }
    verification acTimestampConflictResolve : Test {
        :>> id = "d7c13003-0000-4a10-9b20-a1b2c3d40033"; :>> method = VerificationMethod::test;
        :>> location = "client/test/reconcile.test.ts";
        :>> procedureText = "GIVEN two devices whose note differs only in managed timestamp fields WHEN reconcile runs THEN no conflict copy is created and the earliest `created` + older `updated` are kept; AND a local file whose only change is a spurious timestamp bump is reverted and not pushed; AND a genuine content conflict still merges/conflicts as before (no regression). Verified by reconcile.test.ts timestamp-only + copy-bump + no-regression cases.";
    }
    verification acDriveFsTimes : Test {
        :>> id = "d7c13004-0000-4a10-9b20-a1b2c3d40034"; :>> method = VerificationMethod::test;
        :>> location = "client/test/fstimes.test.ts";
        :>> procedureText = "GIVEN a managed note written on pull or local stamp WHEN the FS-time driver runs THEN mtime is set from `updated` on desktop, creation time is set from `created` on Windows/macOS, Linux skips creation time, and a missing/failing native addon degrades to mtime-only without throwing; POSIX ctime is never set. Verified by fstimes.test.ts with mocked utimes / DataWriteOptions per platform.";
    }
    verification acExcludedFolders : Test {
        :>> id = "d7c13005-0000-4a10-9b20-a1b2c3d40035"; :>> method = VerificationMethod::test;
        :>> location = "client/test/excludedFolders.test.ts";
        :>> procedureText = "GIVEN a folder on the excluded list WHEN SelfSync processes a note under it THEN no managed timestamp field is read, written, or FS-time-driven for that note and content sync is unchanged; AND the settings UI can add (with folder autocomplete) and remove entries. Verified by excludedFolders.test.ts (isExcluded/matchFolders + set ops), settings-ui.dom.test.ts (add/remove wiring), and a *.pwspec.ts e2e asserting an excluded folder's file never reaches the server.";
    }

    // ---- embedded-timestamp #Verify edges (Test -> SystemRequirement) ----
    #Verify dependency from acEmbeddedTimestamp to srEmbeddedTimestamp;
    #Verify dependency from acNormalizedIdentity to srNormalizedIdentity;
    #Verify dependency from acTimestampConflictResolve to srTimestampConflictResolve;

    // ---- D0042 wire-compatibility #Verify edges (Test -> SystemRequirement) ----
    // The two D0042 sprint DoDs (delivery.sysml) passed and NAME these four SRs in their procedure text,
    // but until 2026-09-07 no typed edge reached the requirements, so tier-satisfaction counted the
    // protocol-compat SRs as unverified while the work that verifies them was green (verification-trace
    // warning, issue082 class). Typed here; the DoDs' recorded verdicts are unchanged.
    #Verify dependency from wireSignatureServerDoD to srWireSignature;
    #Verify dependency from wireSignatureServerDoD to srContractDriftGate;
    #Verify dependency from wireCompatClientDoD to srCompatVerdict;
    #Verify dependency from wireCompatClientDoD to srCompatFailClosed;
    #Verify dependency from acDriveFsTimes to srDriveFsTimes;
    #Verify dependency from acExcludedFolders to srExcludedFolders;

    // ---- #Verify edges: Test -> SystemRequirement (the previously-missing traceability) ----
    // new config SRs
    #Verify dependency from acConfigSelective to srConfigSelective;
    #Verify dependency from acConfigAdditiveSafe to srConfigAdditiveSafe;
    #Verify dependency from acConfigAdjudication to srConfigAdjudication;
    #Verify dependency from acSyncRobust to srSyncRobust;
    #Verify dependency from acConfigLiveDetect to srConfigLiveDetect;
    #Verify dependency from acFreeMerge to srFreeMerge;
    // Batch 1 — continuous-sync reliability
    #Verify dependency from acServerApi to srServerApi;
    #Verify dependency from acInstantPush to srInstantPush;
    #Verify dependency from acIncrementalSync to srIncrementalSync;
    #Verify dependency from acSelfHealingReconnect to srSelfHealingReconnect;
    // Batch 2 — data-safety + durability
    #Verify dependency from acDegradedServerGuard to srDegradedServerGuard;
    #Verify dependency from acDurableIndex to srDurableIndex;
    // Batch 3 — large-file performance
    #Verify dependency from acStreamedTransfer to srStreamedTransfer;
    #Verify dependency from acResumableInitialSync to srResumableInitialSync;
    // Batch 4 — vault management + onboarding
    #Verify dependency from acVaultSwitch to srVaultSwitch;
    #Verify dependency from acSetupLink to srSetupLink;
    #Verify dependency from acDeviceIdentity to srDeviceIdentity;
    // Batch 5 — config completeness + sharing/admin split
    #Verify dependency from acConfigReload to srConfigReload;
    #Verify dependency from acConfigAdjudicationUI to srConfigAdjudicationUI;
    #Verify dependency from acReadOnlyGating to srReadOnlyGating;
    #Verify dependency from acRegistrationPolicy to srRegistrationPolicy;
    #Verify dependency from acAdminSurface to srAdminSurface;
    // human on-device attestations (wweatherholtz)
    #Verify dependency from acInstantPushConfirm to srInstantPush;
    #Verify dependency from acSelfHealingReconnectConfirm to srSelfHealingReconnect;
    #Verify dependency from acConfigAdjudicationUIConfirm to srConfigAdjudicationUI;
    #Verify dependency from l4MobileOndeviceDoD to srMobile;
    // existing SRs verified by their existing delivery DoD Tests
    #Verify dependency from goal1ConfigUxDoD to srClearConfig;
    #Verify dependency from goal1ConfigUxDoD to srGuidedWizard;
    #Verify dependency from goal1ConfigUxDoD to srSettingsOneHome;
    #Verify dependency from rel06FixSetDoD to srSingleIndicator;
    #Verify dependency from m1ProtocolDoD to srSimpleBackend;
    #Verify dependency from m2ChunkingBinaryDoD to srSingleBinary;
    #Verify dependency from m2ChunkingBinaryDoD to srContentDedup;
    #Verify dependency from b11ParallelChunkDoD to srConcurrentPerf;
    #Verify dependency from m3ConflictMergeDoD to srConflictMerge;
    #Verify dependency from m3ConflictMergeDoD to srThreeWayMerge;
    #Verify dependency from m3ConflictMergeDoD to srNeverClobber;
    #Verify dependency from m5MobileDoD to srMobile;
    #Verify dependency from b7AuthHardeningDoD to srSecurity;
    #Verify dependency from vaultSharingP1DoD to srVaultSharing;
    // tombstone-authoritative deletion strengthens the never-clobber + degraded-server guards
    #Verify dependency from acTombstoneAuthoritativeDelete to srNeverClobber;
    #Verify dependency from acTombstoneAuthoritativeDelete to srDegradedServerGuard;
    // validation (D0006): the escape-reproducing scenarios validate their use cases too
    #Verify dependency from acConfigAdjudication to ucResolveConfigDifference;
    #Verify dependency from acConfigAdditiveSafe to ucRemoveOrKeepPlugin;
    #Verify dependency from acConfigAdditiveSafe to ucSyncSetupAcrossDevices;
    #Verify dependency from acTombstoneAuthoritativeDelete to ucNeverLoseLocalData;
    #Verify dependency from acTombstoneAuthoritativeDelete to ucSwitchVault;
    // sharing: the redeem-a-link + leave e2e verifies the SR, the grantee use case, AND the owner-side
    // link-create path of ucShareVault (the e2e mints the link the recipient redeems).
    #Verify dependency from acRedeemAndLeaveShare to srVaultSharing;
    #Verify dependency from acRedeemAndLeaveShare to ucRedeemSharedVault;
    #Verify dependency from acRedeemAndLeaveShare to ucShareVault;
    // reality-reconciliation (2026-07-12): validate the updated/new use cases via the delivery DoDs
    // that already cover the shipped behaviour.
    #Verify dependency from deployComposeHardeningDoD to ucDeployServer;      // prebuilt image + Compose + TLS posture
    #Verify dependency from cmmcMfaDoD to ucAdministerServer;                 // admin TOTP MFA
    #Verify dependency from vaultNameAndSizeLimitsDoD to ucContinuousNoteSync; // configurable per-file size cap

    // ---- typed disposition (D0092) for issueScanSkipMtimePreservedBlindspot ----
    // The (size,mtime) scan-skip has one accepted hole: an out-of-band writer that preserves BOTH size
    // and mtime is not noticed until something bumps mtime. This Test STATES the acceptRisk; its
    // TestResult is the OWNER's attestation and is appended only on their explicit word (CLAUDE.md §3c
    // — never inferred). Until then the finding is, truthfully, undispositioned AND still listed open.
    verification scanSkipResidualAccept : Test {
        :>> id = "aec501a9-b89f-484b-84be-a085c6c1119f";
        :>> method = VerificationMethod::confirmation;
        :>> disposition = DispositionKind::acceptRisk;
        :>> procedureText = "ACCEPT-RISK: the (size,mtime) scan-skip residual is knowingly kept. Basis: it turns each whole-vault pass from O(vault bytes) into O(changed files) - a measured battery/CPU drain on large and mobile vaults - and the destructive branch is structurally excluded and now PINNED by reconcile tests (a scan-hit is gated on the remote being present, delete-local exists only when it is absent, so a stale-stat local edit can never be deleted; the hole is exactly the stat gate, caught the moment mtime moves). Consequence when it hits: a same-size-and-same-mtime out-of-band change is LATE, not lost - picked up by the next real edit or a full re-hash. The owner attests acceptance of this residual on these terms.";
    }
    // RAN: Owner's words: 'accept all recommendations. proceed' (console, 2026-11-11, Statement st021). The AI's prompt named the claim: accept the scan-skip residual, a same-size same-mtime out-of-band change syncs late, not lost, and keeps the O(changed files) scan. The owner accepts that residual on the terms of scanSkipResidualAccept. The #Dispositions edge to issueScanSkipMtimePreservedBlindspot is authored in the same commit.
    part scanSkipResidualAcceptR1 : TestResult { :>> id = "5bbf37f5-c878-466c-9780-caf12cc9de27"; :>> outcome = VerdictKind::pass; :>> judgedAgainst = "475ef54"; :>> judgedAt = "2026-11-11"; :>> judgedBy = "wweatherholtz"; }
    // The #Dispositions edge to issueScanSkipMtimePreservedBlindspot is deliberately NOT authored yet.
    // keel 0.3.1's open-issues lens treats a finding with a #Dispositions edge as closed EVEN WHEN the
    // disposition Test has no TestResult - i.e. an unattested acceptRisk hid this issue from the open
    // list (verified: removing the edge made it reappear; issueUnattestedDispositionClosesFinding).
    // Re-checked 2026-11-11 on keel 0.4.1 (keelDispositionLensReport clause 2): with the edge authored
    // and no TestResult, the open count dropped from 11 to 10 and the issue vanished, so upstream #62 is
    // still unfixed. The edge below is authored in the same commit as the owner's attestation
    // (scanSkipResidualAcceptR1, Statement st021), so the closure it implies is now true.
    #Dispositions dependency from scanSkipResidualAccept to issueScanSkipMtimePreservedBlindspot;

    // ---- STPA SafetyRequirement #Verify edges (Test -> SafetyRequirement), authored 2026-09-07 ----
    // stpaSafetyAnalysis's DoD requires each mitigating Safety Requirement to carry a verify-linked Test.
    // Until now no SR had one: the 25 SRs were REALIZED (#RealizedBy -> controller) but not verified in the
    // model. Each edge below was settled by reading the Test's recorded procedure against the SR's statement,
    // and only Tests with a recorded PASS are linked - a Test that verifies the behaviour but has no result
    // is listed as a gap, not linked. Same discipline as the acceptance edges above.
    // sr1: restore on mere absence, delete only on a tombstone: the acceptance scenario that would have caught the field data loss, the confirmedAbsent re-probe, and the switch-upload probe guard
    #Verify dependency from acTombstoneAuthoritativeDelete to sr1;
    #Verify dependency from falseAbsenceDeleteFixDoD to sr1;
    #Verify dependency from switchUploadProbeGuardDoD to sr1;
    // sr2: the streamed-pull racing-edit guard (names SR-2) and the write->read race fix that committed a merge, not the racing save
    #Verify dependency from streamedPullRacingEditGuardDoD to sr2;
    #Verify dependency from critiqueRPlus1ClientFixesDoD to sr2;
    // sr3: streamFileToDisk verifies the whole-file hash before the atomic rename; a hash mismatch on a mount pull is a per-file skip, never adopted
    #Verify dependency from mountHardeningR7DoD to sr3;
    // sr4: shouldSync classification: notes always, each .obsidian category only when opted in, unrecognised files never (32-combo matrix + e2e)
    #Verify dependency from acConfigSelective to sr4;
    // sr5: CSS trust gate (names SR-5), the hot-load restart trust barrier, and its fresh-privacy re-check
    #Verify dependency from cssTrustGateDoD to sr5;
    #Verify dependency from hotLoadSyncedPluginsDoD to sr5;
    #Verify dependency from hotLoadPrivacyGateFreshCheckDoD to sr5;
    // sr6: the own/legacy plugin folder never syncs (acceptance matrix), the self-plugin credential-folder guard on push/pull, and mounts under .obsidian rejected
    #Verify dependency from acConfigSelective to sr6;
    #Verify dependency from pushPullPreviewDoD to sr6;
    #Verify dependency from pluginPushPullDoD to sr6;
    // sr7: the concurrent-commit CAS race test (exactly one 200 / one 409) and the delete-side CAS mirror
    #Verify dependency from testHardeningServerDoD to sr7;
    #Verify dependency from deleteRemoteCasGuardDoD to sr7;
    // sr8: commit_rejects_correct_size_but_wrong_hash and the strict size gate, fail-first
    #Verify dependency from mutationTestingVaultDoD to sr8;
    // sr9: journal records durable before replay reconstructs on reopen (torn record discarded); shard-dir fsync after rename
    #Verify dependency from acDurableIndex to sr9;
    // sr10: safe_rel_path rejects empty/absolute/non-canonical paths (fail-first) - the request-path half; the Unicode case-collision fold is round5CriticFixes (unstamped)
    #Verify dependency from mutationTestingVaultDoD to sr10;
    // sr12: must_change gate + revoke-mid-session; exact (owner,vault,grantee) match predicates; read-only grants never push or delete
    #Verify dependency from testHardeningServerDoD to sr12;
    #Verify dependency from mutationTestingSharesPassDoD to sr12;
    #Verify dependency from acReadOnlyGating to sr12;
    // sr13: revoke-mid-session on the server; revoke/purge durable-write assertions
    #Verify dependency from testHardeningServerDoD to sr13;
    #Verify dependency from mutationTestingSharesPassDoD to sr13;
    // sr14: degraded 503 on a not-empty manifest; a not-ready mount source holds the mount offline; the clear operator message when the server is not ready
    #Verify dependency from testHardeningServerDoD to sr14;
    #Verify dependency from schemaRollbackClearErrorDoD to sr14;
    #Verify dependency from rollback503CleanMessageDoD to sr14;
    // sr15: the D0042 wire-contract signature: server derives + publishes, client fails closed on mismatch
    #Verify dependency from wireCompatClientDoD to sr15;
    #Verify dependency from wireSignatureServerDoD to sr15;
    // sr17: poll-path 401 re-logs-in once; 401-login -> blocked{authRejected}; mount transports rotate the token on relogin
    #Verify dependency from reconcilePathReloginOnceDoD to sr17;
    #Verify dependency from connectionFsmTypedFailureDoD to sr17;
    // sr18: the WebSocket token travels in the Sec-WebSocket-Protocol auth. entry, never the URL query (hardening suite)
    #Verify dependency from testHardeningServerDoD to sr18;
    // sr20: statusDisplay is a pure projection of Phase; no optimistic flip before real transfer
    #Verify dependency from statusDisplayPureProjectionDoD to sr20;
    #Verify dependency from connectPhaseNoOptimisticFlipDoD to sr20;
    // sr21: vault switch reports a decrementing pending count; the exam pass reports checked X/N
    #Verify dependency from switchReportsProgressDoD to sr21;
    #Verify dependency from reconcileExamProgressDoD to sr21;
    // sr22: a whole-connection error aborts the pass (offline + backoff once) instead of completing into a false synced
    #Verify dependency from switchAbortOnOutageDoD to sr22;
    #Verify dependency from connectPhaseNoOptimisticFlipDoD to sr22;
    // sr23: resume cancels the suspended backoff timer and re-attempts; mounts refresh on resume; reconnect() single-flight + backoff
    #Verify dependency from resumeReattemptsConnectionDoD to sr23;
    #Verify dependency from acSelfHealingReconnect to sr23;
    // sr24: delete_checked(path, expected_version) mirrors commit's CAS; 409 on a stale delete
    #Verify dependency from deleteRemoteCasGuardDoD to sr24;
    // sr25: the connect sub-phases are shown as the Connecting detail and logged with elapsed time
    #Verify dependency from connectPhaseVisibilityDoD to sr25;
    // sr11: reindex refuses/routes rather than silently dropping - reindex_recovers_from_store_and_force_drops_truly_lost,
    //       reindex_routes_a_bitrotted_recovered_file_to_lost_not_corruption (autoReindexDoD, stamped in the 2026-09-07 backfill)
    #Verify dependency from autoReindexDoD to sr11;
    // sr16: admin_reindex_and_prune_history_http_ok + the admin any-vault reindex/delete surface (stamped in the backfill)
    #Verify dependency from uiFunctionalAuditDoD to sr16;
    #Verify dependency from adminPortalEnhancementsDoD to sr16;
    // sr19: SEC#4 runtime orphan-chunk sweep bounds uncommitted bytes (runtime_orphan_sweep_runs_on_upload_but_spares_inflight_chunks)
    #Verify dependency from round1DeferredHardeningDoD to sr19;
    // (sr11/sr16/sr19 were unlinkable until the dodBackfillStamp transform recorded the verdicts their DoDs had earned.)
    // sr26/sr27 (conflict resolver, 2026-09-08): the busy gate + stale-preview guard, and the write-before-remove / keep-both order
    #Verify dependency from busyStateGatingDoD to sr26;
    #Verify dependency from conflictModalPerfDoD to sr26;
    #Verify dependency from resolutionStateMachineDoD to sr26;
    #Verify dependency from keepBothResolutionDoD to sr27;
    #Verify dependency from conflictModalPerfDoD to sr27;
    // sr28 (engine terminal state, 2026-09-08): the engine table + its terminal cell, pinned by fsm.test's engineMachine coverage
    #Verify dependency from engineFsmOnPrimitiveDoD to sr28;

    // ---- nesting STPA (composed vaults) #Verify edges, 2026-09-09: each SR -> the passed DoDs whose recorded procedure verifies it ----
    #Verify dependency from mountEngineCoreDoD to sr29;
    #Verify dependency from mountEngineDoD to sr29;
    #Verify dependency from mountHardeningR3DoD to sr29;
    #Verify dependency from mountIoAdaptersDoD to sr30;
    #Verify dependency from mountHardeningR5DoD to sr30;
    #Verify dependency from composedMountPermissionsDoD to sr30;
    #Verify dependency from mountHardeningR2DoD to sr31;
    #Verify dependency from mountHardeningR4DoD to sr32;
    #Verify dependency from mountHardeningR7DoD to sr32;
    #Verify dependency from mountFolderDeleteGuardDoD to sr33;
    #Verify dependency from mountDeleteGuardHardeningDoD to sr33;
    #Verify dependency from mountHardeningR3DoD to sr34;
    #Verify dependency from mountIoAdaptersDoD to sr34;
    #Verify dependency from mountHardeningR4DoD to sr35;
    #Verify dependency from mountHardeningR5DoD to sr35;
    #Verify dependency from mountHardeningR10DoD to sr35;
    #Verify dependency from mountHardeningR1DoD to sr36;
    #Verify dependency from stpaProcessAndFsmModuleDoD to sr36;
    #Verify dependency from composeRecipeFeatureDoD to sr37;
    #Verify dependency from mountHeldResolverSerializeDoD to sr38;
    #Verify dependency from mountHardeningR5DoD to sr39;
    #Verify dependency from mountBaseFreshnessDoD to sr39;
    #Verify dependency from mountHardeningR6DoD to sr40;
    #Verify dependency from mountHardeningR4DoD to sr40;
    #Verify dependency from mountLiveSubscriptionDoD to sr40;
    #Verify dependency from mountSocketLivenessDoD to sr40;
    #Verify dependency from mountHardeningR9DoD to sr40;
    #Verify dependency from mountHardeningR6DoD to sr41;
    #Verify dependency from mountSharedSourceResurrectionPolicyDoD to sr42;
    #Verify dependency from mountResetDetectionDoD to sr42;
    #Verify dependency from mountSyncPushLocalDoD to sr43;
    #Verify dependency from mountMoveSafetyDoD to sr43;

    // ---- authorities STPA (host app / other plugins / other sync tools / release channel) #Verify edges, 2026-09-10.
    // sr47 and sr50 carry NO edge yet: their mitigations are the OPEN tasks syncToolCoexistence / releaseAssetIntegrity. ----
    #Verify dependency from editorStatusCleanupOnUnloadDoD to sr44;
    #Verify dependency from engineFsmOnPrimitiveDoD to sr44;
    #Verify dependency from pluginWiringTimerLeakFixDoD to sr44;
    #Verify dependency from casePathAliasDoD to sr45;
    #Verify dependency from rejectedPushHoldDoD to sr45;
    #Verify dependency from contentIdentityNormalisationDoD to sr46;
    #Verify dependency from frontmatterTrailingSpaceIdentityDoD to sr46;
    #Verify dependency from contentIdentityUnicodeNormaliseDoD to sr46;
    #Verify dependency from timestampIgnoreRedesignDoD to sr46;
    #Verify dependency from normHashDecideDoD to sr46;
    #Verify dependency from conflictModalBinaryViewDoD to sr48;
    #Verify dependency from conflictModalPerfDoD to sr48;
    #Verify dependency from busyStateGatingDoD to sr48;
    #Verify dependency from versionRecordDriftGuardDoD to sr49;
    #Verify dependency from releaseCurrencyGuardDoD to sr49;
    #Verify dependency from switchUploadProbeGuardDoD to sr51;
    #Verify dependency from mountDeleteGuardHardeningDoD to sr51;

    // ---- 2026-09-11 panel: requirements whose mechanism already carried a passed DoD (the sprint DoDs' edges follow at closeOut) ----
    #Verify dependency from tombstonePruneDoD to sr61;
    #Verify dependency from bulkDeleteConfirmDoD to sr62;
    #Verify dependency from switchUploadProbeGuardDoD to sr60;
    #Verify dependency from testHardeningClientDoD to sr60;

    // ---- 2026-09-11 architecture panel sprints (1.30.18) #Verify edges — each DoD carries a recorded pass at 39f31d3d ----
    #Verify dependency from coexistenceHardeningDoD to sr58;
    #Verify dependency from coexistenceHardeningDoD to sr64;
    #Verify dependency from coexistenceHardeningDoD to sr47;
    #Verify dependency from mountScopeBoundaryHardeningDoD to sr52;
    #Verify dependency from mountScopeBoundaryHardeningDoD to sr53;
    #Verify dependency from mountScopeBoundaryHardeningDoD to sr36;
    #Verify dependency from contentIdentityTwoSidedDoD to sr56;
    #Verify dependency from contentIdentityTwoSidedDoD to sr57;
    #Verify dependency from contentIdentityTwoSidedDoD to sr46;
    #Verify dependency from contentIdentityTwoSidedDoD to sr5;
    #Verify dependency from hostCoexistenceHardeningDoD to sr54;
    #Verify dependency from hostCoexistenceHardeningDoD to sr55;
    #Verify dependency from hostCoexistenceHardeningDoD to sr63;
    #Verify dependency from hostCoexistenceHardeningDoD to sr45;
    #Verify dependency from hostCoexistenceHardeningDoD to sr48;
    #Verify dependency from releaseIntegrityHardeningDoD to sr59;
    #Verify dependency from releaseIntegrityHardeningDoD to sr65;
    #Verify dependency from releaseIntegrityHardeningDoD to sr50;
    #Verify dependency from releaseIntegrityHardeningDoD to sr49;

    // ---- 2026-09-12 residual sprints (1.30.19) #Verify edges — each DoD carries a recorded pass at 5e63dcd4 ----
    #Verify dependency from monotonicRewriteDetectionDoD to sr66;
    #Verify dependency from monotonicRewriteDetectionDoD to sr47;
    #Verify dependency from mountCaseSensitiveClaimDoD to sr67;
    #Verify dependency from mountCaseSensitiveClaimDoD to sr29;
    #Verify dependency from mountRoConflictCopyKeeperDoD to sr68;

    // ---- End-to-end encryption (2026-11-10, e2eeCapability; panel SE finding 1: typed, not prose) ----
    #Verify dependency from e2eeServerKeyringAndGuardDoD to srE2eeDowngradeGuard;
    #Verify dependency from e2eeRolledBackRefusalAnalysisDoD to srE2eeRolledBackServerRefuses;
    #Verify dependency from e2eeServerKeyringAndGuardDoD to srE2eePlaintextChunkRefused;
    #Verify dependency from e2eeServerKeyringAndGuardDoD to srE2eeDedupPreserved;
    #Verify dependency from e2eeClientWiringDoD to srE2eeServerNeverSeesPlaintext;
    #Verify dependency from e2eeClientWiringDoD to srE2eeKeysNeverLeaveDevice;
    #Verify dependency from e2eeClientWiringDoD to srE2eeIntegrityDetected;
    #Verify dependency from e2eeClientWiringDoD to srE2eeWrongPasswordDistinct;
    #Verify dependency from e2eeClientFlowsDoD to srE2eeWrongPasswordDistinct;
    #Verify dependency from e2eeClientFlowsDoD to srE2eeCreateFailsClosed;
    #Verify dependency from e2eeClientFlowsDoD to srE2eeKeysNeverLeaveDevice;
    #Verify dependency from e2eeClientFlowsDoD to srE2eePasswordFloorAndWarning;
    #Verify dependency from e2eeRealServerE2eDoD to srE2eeServerNeverSeesPlaintext;
    #Verify dependency from e2eeRealServerE2eDoD to srE2eeIntegrityDetected;
    #Verify dependency from e2eeRealServerE2eDoD to srE2eeDedupPreserved;
    #Verify dependency from e2eeRealServerE2eDoD to srE2eeDowngradeGuard;
}
