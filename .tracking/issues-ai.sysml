// Per-actor issues records for ai (issue210/srDcPerActorWriteTargets): new records
// route here so concurrent contributors never conflict at a shared append anchor.
package IssuesAi {
    private import EngineElement::*;
    private import EngineWork::*;
    private import EngineVerification::*;
    private import EngineRelationships::*;

    part issue007 : Issue {
        :>> id = "fb91c6d9-eb80-4e84-b049-27bb1cefdeac";
        :>> title = "A raw vault event for a synced FOLDER records an unsynced-edit claim for a change nobody made; NTFS last-access updates re-fire it per folder with no write";
        :>> createdAt = "2026-11-04";
        :>> createdBy = "ai";
        :>> description = "OBSERVATION (owner, st008, 2026-11-04). With 1.32.0 installed, the status detail read '7 unsynced edits: .obsidian/themes/Minimal (0s), .obsidian/plugins/quickadd (0s), ...'. The owner saw the same eleven items again and again. The vault log (info level) holds seventeen stale-claim warn lines on 2026-11-04, in three bursts (03:05Z, 07:19Z, 08:51Z). Every path is a FOLDER: eight synced plugin folders and two theme folders. Get-Item on each folder shows directory and file write times months old (quickadd 2026-07-17, themes/Minimal 2026-01-20). All of them share one last-access time, 17:31:42Z, inside a burst of settings-tab config renders. fsutil behavior query disablelastaccess reports 2 (last-access updates enabled). REPEATABLE RESULT (real Obsidian 1.12 on Windows 11, plugin built from HEAD 7f8467f, 2026-11-04). The check is client/e2e-obsidian/configclaim.pwspec.ts ARM B. It ages a synced plugin folder's last-access time two hours back with utimes. It then lists the folder five times from outside, with no write. Obsidian emits 'raw' with the FOLDER path eight times. The plugin's claim map then holds '.obsidian/plugins/testplugin'. The detail reads '1 unsynced edit: .obsidian/plugins/testplugin (0s)'. Two of five fresh launches sat on syncing for the whole 60 s baseline before any arm acted. The same folder claim appeared and vanished during that time. ARM A (a file write inside the folder) reports the file path and settles. ARM C (adapter list, stat, exists, read, readBinary, a walk, pluginSyncClean, a config scan) emits no folder event while the access time is fresh. MECHANISM, as read at 7f8467f. onRawConfigEvent (client/src/main.ts) buffers any path that passes shouldSync. shouldSync accepts a bare plugin or theme folder path. flushRawConfig then calls noteLocalChange for it, which records an unsynced-edit claim, and enqueues a per-path pass. A folder is never a synced item, so the claim is noise for a change nobody made. CORRECTION (panel 2026-11-04, SE F1, PEDANT-1 F1, PEDANT-3 F2): the first record said no pass settles that claim. That is false. A connected per-path pass settles it as in-sync in about a second (the finally block of reconcilePath in client/src/reconcile.ts). The light blinks yellow for that second. A claim stands past 60 s only while no per-path pass runs: syncengine.ts drops a path event when the engine is not connected, and the connect's full pass or the next config pass settles it. That standing-claim class is issue008. NTFS persists a folder's last-access time at most hourly, on any listing. The config scan lists every synced folder at most every 30 s (the 60 s idle poll in practice), so each folder re-fires when NTFS next persists its access time. The owner's warn bursts were 4 h 14 m and 1 h 32 m apart, not hourly. The settings-tab sentence in the first record (re-render on each status change) has no code path behind it; the 400 section.config renders per hour are issue009.";
        :>> discoveredInField = true;
        :>> severity = Severity::High;
    }
    #Resolves dependency from rawFolderEventNoClaim to issue007;

    part issue008 : Issue {
        :>> id = "37767c7f-19d2-4b60-ae1a-b0912b383c70";
        :>> title = "A disk claim raised while no per-path pass runs stands until the next full or config pass; the stale warn line only reports it";
        :>> createdAt = "2026-11-04";
        :>> createdBy = "ai";
        :>> description = "OBSERVATION (owner log, 2026-11-04). Seventeen stale-claim warn lines in three bursts (03:07Z, 07:21Z, 08:52Z) report waits of 61 s to 140 s 'with no pass settling it'. Each burst ends at the next 'end reconcileAll delta+config' line. The 06:37Z to 07:22Z gap in the periodic poll points to a sleep and resume. The same class showed in the harness. Two of five fresh-vault launches of client/e2e-obsidian/configclaim.pwspec.ts sat on syncing for the whole 60 s baseline before any arm acted. MECHANISM (panel 2026-11-04, SE F1, PEDANT-1 F1, PEDANT-3 F2, read at d668698). syncengine.ts drops a path event when the engine is not connected (the isConnected guard in the path case of handle). noteLocalChange already recorded the disk claim before the enqueue (flushRawConfig and onLocalEvent in client/src/main.ts). Nothing settles that claim until a full pass (finishConnect calls settleUnsyncedBefore) or a config pass visits the path. A folder claim raised in that window was the owner's 140 s line. A real file edit in the same window shows the same way. The CLAIM_STALE_WARN_MS line is a symptom report, not a control. It logs and sets warned, and nothing acts (unsyncedEditCount in main.ts). A unit test in client/test/plugin-wiring.test.ts verifies the mechanism. Its name: 'a claim raised while the engine is NOT connected stands (the path event is dropped) until a full pass settles it'. NOT ESTABLISHED. Which engine state held during the owner's three bursts. The vault log is at info level and does not carry the engine transitions. The resolver names the holder in a real-Obsidian probe and adds a settle try at the stale bound.";
        :>> discoveredInField = false;
        :>> severity = Severity::Medium;
    }
    #Resolves dependency from standingClaimSettleTry to issue008;

    part issue009 : Issue {
        :>> id = "745533b4-19dc-4554-aaed-1bbc95a4a478";
        :>> title = "About 400 section.config renders per hour with the settings tab open; the producer is not identified";
        :>> createdAt = "2026-11-04";
        :>> createdBy = "ai";
        :>> description = "OBSERVATION (owner log, 2026-11-04). About 400 section.config render spans in one hour while the settings tab was open. All synced plugin folders shared one last-access time, 17:31:42Z, inside that burst. NOT ESTABLISHED. issue007 first attributed the burst to 'the settings tab re-renders its config section on each status change'. The panel (2026-11-04, PEDANT-1 F3, PESSIMIST-2 F4, PEDANT-3 F2) read the code and found no such path. statusListener runs fillStatus only (client/src/settings.ts). A config section re-render comes only from settingsRefresh('config', ...) at five named producers in client/src/main.ts. Those are: server plugin set changed, plugin name resolved, plugin purged, plugin sync toggled, plugins hot-loaded. The per-plugin walk is cached for the tab session. The producer of the 400 renders is not identified. The vault log carries the span but not the requestRefresh reason. RESOLVER. Log the refresh reason with each section.config span. Reproduce with the settings tab open in real Obsidian. Assert a bound on renders per minute with no settings change.";
        :>> discoveredInField = false;
        :>> severity = Severity::Low;
    }
    #Resolves dependency from configSectionRenderStorm to issue009;

    part issue010 : Issue {
        :>> id = "6a5fc680-7fa1-4c45-9313-ba2cdfd0cb99";
        :>> title = "cargo-audit fails: libsqlite3-sys 0.30.1 carries SQLite CVE-2026-119375 (RUSTSEC-2026-0459)";
        :>> createdAt = "2026-11-10";
        :>> createdBy = "ai";
        :>> description = "The CI job cargo-audit fails on every push since the scheduled run of 2026-11-09, run 42656295355 at 4f5d298, before any E2EE commit. The report names RUSTSEC-2026-0459. The crate libsqlite3-sys 0.30.1 carries C SQLite CVE-2026-119375, severity 6.8 medium, published 2026-10-30. The fix is libsqlite3-sys 0.39.0 or newer, which rusqlite 0.41 pulls in. server/Cargo.toml pins rusqlite 0.32 with the bundled feature, so the vulnerable SQLite is compiled into the server binary. The owner reported the failing CI on 2026-11-10. The bump is a dependency change with a bundled C library behind it. So it is tracked and verified by the full server test suite, not patched silently.";
        :>> discoveredInField = false;
        :>> severity = Severity::Medium;
    }
    #Resolves dependency from rusqliteAuditBump to issue010;

    part issue011 : Issue {
        :>> id = "e9d2a793-5287-452d-a93b-0ba2177a266f";
        :>> title = "E2EE refusal-two mirror scan runs unbounded on every refused open";
        :>> createdAt = "2026-11-10";
        :>> createdBy = "ai";
        :>> description = "Design residual from E2EE panel round 8, PESSIMIST-2 finding 3. The second refusal of Vault::open reads the four-byte magic of every file under vault/ to tell which stale file the operator must move aside. A refused open is never cached. So the scan runs on every request that reaches the vault while the refusal holds, at the client's slow retry. The walk has no size bound. On a large vault with many devices the cost is a full directory walk per retry. Acceptable for v1, because the state is an operator error that the body names and the retry is slow. The E2 sprint records the cost in its result. A later change caps the walk or memoises it on the directory mtime if a fleet ever hits it.";
        :>> discoveredInField = false;
        :>> severity = Severity::Low;
    }
    #Resolves dependency from e2eeMirrorScanCap to issue011;

    part issue012 : Issue {
        :>> id = "2c52a0d7-1f01-4784-8fee-3a2a4b466dc0";
        :>> title = "A vault lock taken on the async worker in api.rs, a comment-only rule";
        :>> createdAt = "2026-11-10";
        :>> createdBy = "ai";
        :>> description = "Sprint 2 review pass 1 found the E2EE header guard in api.rs scoped_with taking the per-vault read lock on the async worker. The same file documents the rule that every vault lock runs on the blocking pool (R10-D3, critique-R8 H1). A commit or reindex holding the write lock stalls async workers for its whole hold. The rule was enforced by comment only, so the class can recur with any new handler. Fix: the flag read moved into blocking. Guard: a test in api.rs scans the source and fails on any rlock or wlock call outside a blocking or spawn_blocking closure.";
        :>> discoveredInField = false;
        :>> severity = Severity::Medium;
    }
    #Resolves dependency from apiLockDisciplineGuard to issue012;

    part issue013 : Issue {
        :>> id = "501e9a88-0b4c-4897-9c07-93c690f326ed";
        :>> title = "A RED test committed at standup turned CI red on main for one commit";
        :>> createdAt = "2026-11-10";
        :>> createdBy = "ai";
        :>> description = "The Sprint 3 standup commit a465b38 carried the RED codec test, client/test/e2ee/codec.test.ts, before its module existed. CI on main went red for that one commit with Cannot find module ../../src/e2ee/codec. The RED-first discipline needs the RED evidence in the standup record, not the test file in the commit. The class can recur at every standup. Guard: .githooks/pre-commit runs client/scripts/check-staged-test-imports.mjs, which refuses a staged client test whose relative import resolves to no file in the index. A vitest test pins the resolver.";
        :>> discoveredInField = false;
        :>> severity = Severity::Low;
    }
    #Resolves dependency from stagedTestImportGuard to issue013;

    part issue014 : Issue {
        :>> id = "706ac76b-625d-4a3c-a84b-dc44eb2eeb62";
        :>> title = "MIN_E2EE_SERVER_VERSION 1.33.0 is not tied to the first schema-4 server tag";
        :>> createdAt = "2026-11-10";
        :>> createdBy = "ai";
        :>> description = "The client constant MIN_E2EE_SERVER_VERSION in client/src/e2ee/flows.ts is 1.33.0. docs/deployment.md, README.md and docs/cmmc-posture.md name the same version as the first tagged server release that stamps index schema 4. No tag with that number exists yet. The latest tag is 1.32.2. Nothing ties the constant to the tag that first ships schema 4, so the two can drift. The E4 release step must cut the first E2EE server tag as 1.33.0. Otherwise it must change the constant and the four doc sites to the tag it cuts, in the same commit. A release-process check that compares the constant with the tag makes the rule permanent.";
        :>> discoveredInField = false;
        :>> severity = Severity::Low;
    }
    #Resolves dependency from e2eeRealServerE2e to issue014;

    part issue015 : Issue {
        :>> id = "c53dafb4-e145-45d3-b33e-859614be5a80";
        :>> title = "D0108 removed-collaborator-keeps-the-key sentence exists in docs only, not in the share UI";
        :>> createdAt = "2026-11-10";
        :>> createdBy = "ai";
        :>> description = "D0108 says the UI copy tells the owner that a removed collaborator keeps the vault key until a rotation. After Sprint 4 that sentence exists in docs/deployment.md only. No share-management surface in the plugin says it. The ShareManageModal revoke action and the Leave action carry no such text. The sentence belongs next to the revoke action, and the rotation follow-up owns the fix, because the sentence changes once rotation exists.";
        :>> discoveredInField = false;
        :>> severity = Severity::Low;
    }
    #Resolves dependency from e2eeVaultKeyRotation to issue015;

    part issue016 : Issue {
        :>> id = "43d95dd3-d7c1-4eff-936d-81585a220f00";
        :>> title = "Release notes say nothing about the hidden Encrypt option (D0112)";
        :>> createdAt = "2026-11-11";
        :>> createdBy = "ai";
        :>> description = "D0112 says the release notes state that a release cut before the KDF default Decision ships with the Encrypt option hidden. release.yml writes the notes from a fixed template with the asset digests, and no sentence about the define exists. The workflow is a locked enforcement surface (D0465), so the AI cannot edit it. The edit is recorded as the proposed D0114 with its diff. Until the owner accepts D0114 and the edit lands, a release note says nothing about the hidden option.";
        :>> discoveredInField = false;
        :>> severity = Severity::Low;
    }
    #Resolves dependency from e2eeReleaseNotesDefineState to issue016;

    part issue017 : Issue {
        :>> id = "8485e38d-4021-48f3-9ef8-dae135ffc232";
        :>> title = "Encrypted vault: an in-sync file's base stored the frame hash, so round trips cascaded conflict copies";
        :>> createdAt = "2026-11-11";
        :>> createdBy = "ai";
        :>> description = "In an encrypted vault, a no-op reconcile of an in-sync file rewrote its base entry with the frame hash instead of the content identity. The in-sync branch of reconcileOne called setBase with rmeta.hash, the one site E3a did not route through remoteIdentity. On the next pass every such file read as locally changed and remotely changed, so each round-trip spawned a new conflict copy. The real-server spec found it in Sprint 5: a binary conflict cascaded into nested conflict copies by the second round, while a plaintext vault converged. The fix routes that site through remoteIdentity. The guard is a lint assertion over reconcile.ts that no setBase call passes a raw meta hash, plus the convergence assertion of the real-server spec.";
        :>> discoveredInField = false;
        :>> severity = Severity::High;
    }
    #Resolves dependency from e2eeRealServerE2e to issue017;

    part issue018 : Issue {
        :>> id = "a8a95e06-77c5-4558-9c69-8e3fe12b3f67";
        :>> title = "Phone KDF protocol cannot run on the release build because D0112 hides the Encrypt option it gates";
        :>> createdAt = "2026-11-11";
        :>> createdBy = "ai";
        :>> description = "The phone KDF protocol in docs/architecture/93-real-device-perf-protocol.md tells the owner to create or join an encrypted vault on the phone. D0112 hides the Encrypt option until that protocol delivers its Measurements. So the release build 1.33.0 cannot run the protocol. The gate depends on the thing it gates. Found 2026-11-11 when the owner asked what to run on the phone. A browser page that runs the same @noble/hashes Argon2id at KDF_DEFAULT gives a wall-time estimate today. It does not run inside Obsidian and cannot read process memory. The fix is a plugin command that runs the derivation at KDF_DEFAULT independent of SELFSYNC_E2EE and shows the wall time. The protocol then names that command as the wall-time instrument. The memory instrument stays dumpsys or Instruments.";
        :>> discoveredInField = false;
        :>> severity = Severity::Medium;
    }
    #Resolves dependency from e2eeKdfMeasureCommand to issue018;

    part issue019 : Issue {
        :>> id = "a21a71b6-e06e-4f1a-8d65-f3be70077601";
        :>> title = "A second device cannot join an encrypted vault: the unpinned status probe meets the server downgrade guard";
        :>> createdAt = "2026-11-11";
        :>> createdBy = "ai";
        :>> description = "Found 2026-11-11 by the first run of client/e2e-obsidian/e2ee.pwspec.ts against the HEAD server binary through real Obsidian. A second device with no pin cannot join an encrypted vault through the plugin. Its status stays blocked with the server text 'vault is end-to-end encrypted. This client version does not support it. Update the plugin.' inside the retry wrapper. Cause, read at client/src/main.ts probe in doConnect: GET keyring runs first and is exempt from the server guard. GET status runs next without the x-selfsync-e2ee header. HttpTransport sends the header only when the device is pinned (main.ts buildApi). The server guard (api.rs scoped) answers 403. The probe treats it as a retry, so resolveCodec and the Join dialog never run. Why the unit layer passed: the fake api in client/test/e2ee/connect.test.ts answered status without the guard. The connect flow passed there and failed against the real server. E4 proved the engine through the test transport, which sent the header on every request. Fix in this sprint: the probe sends the header once GET keyring finds a record and the build supports encryption. A build without support maps the 403 on status to the E2eeUnsupportedBuild block of spec section 4.9. Guards: the fake api mirrors the server guard and starts with the pin like the real transport. The real-Obsidian spec drives the join through the dialog.";
        :>> discoveredInField = false;
        :>> severity = Severity::High;
    }
    #Resolves dependency from e2eeRealObsidianE2e to issue019;

    part issue020 : Issue {
        :>> id = "20da67b5-908a-460c-9a7e-8054ea26cdef";
        :>> title = "Live change latency 62 s against the owner's server, 0.58 s on loopback: the WebSocket change path needs evidence";
        :>> createdAt = "2026-11-11";
        :>> createdBy = "ai";
        :>> description = "Measured 2026-11-11 by e2ee.pwspec.ts run mwceeanp against the owner's server https://notes2.willweatherholtz.com. A note made on device A after both devices were pinned reached device B in 62.47 seconds. The same step on loopback took 0.58 seconds. The note made before B joined arrived in 1.02 seconds, so the pull path is fast and the live change path is slow. What is checked: a WebSocket upgrade to /api/ws through the proxy answers 101 with the plugin's auth protocol. The proxy does not refuse the socket. What is not checked: whether the changed message reaches device B over that socket, and whether B's socket dropped before the change. Also whether the proxy buffers frames. The 62 seconds match a poll fallback, but no log confirms that. The resolver reruns the spec against the server with the plugin log on both devices captured, reads the WebSocket events, and names the cause. If the cause is the proxy, the fix is a documented proxy setting. If the cause is the client, the fix is a code change with a test.";
        :>> discoveredInField = false;
        :>> severity = Severity::Medium;
    }
    #Resolves dependency from e2eeRemoteLiveLatency to issue020;
}
