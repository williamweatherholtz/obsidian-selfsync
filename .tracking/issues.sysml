// =====================================================================
// ProjectIssues — tracked problems (D0077/D0078: every Issue must be TRIAGED with a #Resolves
// edge from a resolving action or a mooting Decision; resolution is COMPUTED, never prose).
// =====================================================================
package ProjectIssues {
    private import EngineElement::*;
    private import EngineWork::*;
    private import ProjectDelivery::*; // requirementTraceabilityBackfill — the resolver
    private import ProjectDecision0020::*; // d0020 — the mooting Decision for the accepted inherent/cosmetic findings
    private import ProjectDecision0027::*; // d0027 — no-CUI scope decision that moots the two CMMC CUI-controls
    private import ProjectDecision0038::*; // d0038 — MFA-deprecation Decision that moots the MFA-login-support issue

    // The test-escape retrospective (2026-07-05): "plugin sync doesn't work at all" shipped
    // despite a large test suite. Root cause is two-layered and recorded here so the class is
    // guarded, not just patched (D0047).
    part issueTraceabilityGap : Issue {
        :>> id = "c0f1a5cc-8001-4a10-9b20-a1b2c3d40071";
        :>> title = "Config-sync feature shipped unrooted, with zero requirement->test traceability";
        :>> createdAt = "2026-07-05";
        :>> createdBy = "wweatherholtz";
        :>> description = "The multi-device config divergence/removal defects (0.10.4: a crash on a divergent community-plugins.json + a phantom-base deletion of a peer's plugin) escaped a 125-test suite. Two-layer cause: (1) the config/customization-sync feature was implemented in code with NO Need or SystemRequirement behind it (an orphan capability), so there were no behavioral acceptance criteria and no use case enumerating the 'two already-configured devices' scenario; (2) tier-satisfaction showed SR-verified-by-Test at 0/15 — every automated test was divorced from the requirements model, so nothing enforced that a requirement carried a behavioral test. Tests were written bottom-up from the code (filter combos, single-file one-way config sync) and never exercised config conflict-copy or removal.";
        :>> discoveredInField = true;
        :>> relatedTask = "requirementTraceabilityBackfill";
        :>> severity = Severity::High;
    }

    // Triage: resolved by the CR d0011 traceability backfill (roots the feature as a #Capability,
    // adds the #Verify acceptance layer for every SR incl. the two scenarios that catch this class).
    #Resolves dependency from requirementTraceabilityBackfill to issueTraceabilityGap;

    // Owner attestation (2026-07-05): settings functionality is right, but the layout atomizes
    // every setting into its own container instead of grouping intelligently like comparable
    // plugins. Cosmetic, not functional; deferred to an end-of-project polish pass to avoid
    // repeated cosmetic rework. srSettingsOneHome's top-level 4-group structure holds; this is
    // the finer within-group organization.
    part issueSettingsGrouping : Issue {
        :>> id = "c0f1a5cc-8002-4a10-9b20-a1b2c3d40072";
        :>> title = "Settings are atomized, not intelligently grouped like comparable plugins";
        :>> createdAt = "2026-07-05";
        :>> createdBy = "wweatherholtz";
        :>> description = "Owner review: every setting sits in its own little container rather than being organized into sensible sub-groups the way well-designed Obsidian plugins do. Functionality is present and correct; the grouping is a cosmetic weakness, and the comparable-plugin study that should have informed it was not done properly. Deferred to a single end-of-project cosmetic pass (explicit owner instruction: don't keep reworking cosmetics mid-build).";
        :>> discoveredInField = true;
        :>> relatedTask = "settingsGroupingPolish";
        :>> severity = Severity::Low;
    }
    #Resolves dependency from settingsGroupingPolish to issueSettingsGrouping;

    // =====================================================================
    // Findings from the 3-lens adversarial critique (data-integrity / security / correctness),
    // by independent critics, 2026-07-05. Each carries a severity + a #Resolves resolver:
    // the 5 client fixes shipped in 0.10.14 (critiqueClientWave, done); the server/coordinated
    // fixes + the Low backlog are triaged to critiqueServerHardening (open).
    // =====================================================================
    // ---- client data-integrity / correctness (fixed in 0.10.14) ----
    part issueBulkDeleteGuard : Issue { :>> id = "c0f1a5cc-9101-4a10-9b20-a1b2c3d49101"; :>> title = "Bulk-delete guard only fired at exactly-empty; a partial manifest shrink deleted the missing files"; :>> createdAt = "2026-07-05"; :>> createdBy = "wweatherholtz"; :>> description = "DI-1: guardBulkDelete = remote.size===0 only, so a partial index (restore/reindex over an incomplete dir) advertising some files and dropping others propagated real delete-local on every device. Fixed: ratio guard (>= half of base missing from a non-empty manifest, min 6)."; :>> discoveredInField = false; :>> relatedTask = "critiqueClientWave"; :>> severity = Severity::High; }
    part issueDownloadIntegrity : Issue { :>> id = "c0f1a5cc-9102-4a10-9b20-a1b2c3d49102"; :>> title = "Downloaded file content was never re-hashed; a corrupt chunk was laundered into known-good state"; :>> createdAt = "2026-07-05"; :>> createdBy = "wweatherholtz"; :>> description = "DI-2: applyPull set base = claimed hash without verifying the reassembled bytes, so a bit-rotted blob was written to the note and re-served to every device. Fixed: verify sha256(bytes)==rmeta.hash; refuse + skip on mismatch."; :>> discoveredInField = false; :>> relatedTask = "critiqueClientWave"; :>> severity = Severity::High; }
    part issueStaleBaseRecreate : Issue { :>> id = "c0f1a5cc-9103-4a10-9b20-a1b2c3d49103"; :>> title = "Both-absent left a stale base, so recreating a file with identical content deleted it"; :>> createdAt = "2026-07-05"; :>> createdBy = "wweatherholtz"; :>> description = "CO-1: the in-sync handler never cleared base when both sides were absent, so a recreate with content equal to the old base hash read as delete-local and wiped the note. Fixed: clear stale base on both-absent."; :>> discoveredInField = false; :>> relatedTask = "critiqueClientWave"; :>> severity = Severity::High; }
    part issueOfflineStuck : Issue { :>> id = "c0f1a5cc-9104-4a10-9b20-a1b2c3d49104"; :>> title = "A transient per-file error pinned the status light 'Offline' forever"; :>> createdAt = "2026-07-05"; :>> createdBy = "wweatherholtz"; :>> description = "CO-2: the FSM cleared 'offline' only on 'connected', which the poll path never emits, so one failed edit left it red while sync kept working. Fixed: offline recovers to idle on a successful sync (syncDone)."; :>> discoveredInField = false; :>> relatedTask = "critiqueClientWave"; :>> severity = Severity::High; }
    part issueConfigEditVsDelete : Issue { :>> id = "c0f1a5cc-9105-4a10-9b20-a1b2c3d49105"; :>> title = "Config edit-vs-delete silently resurrected a removed config file / reverted a removal"; :>> createdAt = "2026-07-05"; :>> createdBy = "wweatherholtz"; :>> description = "CO-3: config edit-wins-* fell through instead of adjudicating, contradicting the never-resurrect invariant (edit-wins-pull pulled a locally-deleted config back). Fixed: config edit-vs-delete is adjudicated like divergence."; :>> discoveredInField = false; :>> relatedTask = "critiqueClientWave"; :>> severity = Severity::Medium; }
    // ---- server + coordinated (open; SEC-2 coded + cargo-green, awaiting redeploy) ----
    part issueDefaultAdminCreds : Issue { :>> id = "c0f1a5cc-9201-4a10-9b20-a1b2c3d49201"; :>> title = "Server seeds a publicly-known admin/admin account by default"; :>> createdAt = "2026-07-05"; :>> createdBy = "wweatherholtz"; :>> description = "SEC-2: SYNC_USER/SYNC_PASSWORD default to admin/admin, seeding the server-admin account; an exposed default server is trivially taken over. Fix (coded, cargo-green): refuse to start when the admin password is unset/'admin' unless ALLOW_WEAK_ADMIN=1 (LAN/dev opt-in). Needs operator redeploy."; :>> discoveredInField = false; :>> relatedTask = "critiqueServerHardening"; :>> severity = Severity::High; }
    part issueWsTokenInUrl : Issue { :>> id = "c0f1a5cc-9202-4a10-9b20-a1b2c3d49202"; :>> title = "Session bearer token is passed in the WebSocket URL query string"; :>> createdAt = "2026-07-05"; :>> createdBy = "wweatherholtz"; :>> description = "SEC-1: the 30-day token rides as ?token=... on the /api/ws upgrade, so it lands in reverse-proxy/LB logs and can be replayed. Fix: authenticate the WS via Sec-WebSocket-Protocol or a short-lived single-use ticket (coordinated client+server change)."; :>> discoveredInField = false; :>> relatedTask = "critiqueServerHardening"; :>> severity = Severity::High; }
    part issueSharePluginRce : Issue { :>> id = "c0f1a5cc-9203-4a10-9b20-a1b2c3d49203"; :>> title = "A read-write share grantee can push plugin code the owner's device auto-loads (cross-share RCE)"; :>> createdAt = "2026-07-05"; :>> createdBy = "wweatherholtz"; :>> description = "SEC-3: the server stores any committed path and the client auto-enables community-plugin code; a RW grantee committing .obsidian/plugins/x/main.js executes code on the owner's device. Fix: never auto-enable plugin code received over a shared (non-owned) vault; require explicit per-plugin confirmation."; :>> discoveredInField = false; :>> relatedTask = "critiqueServerHardening"; :>> severity = Severity::High; }
    part issueAcctDeleteRemanence : Issue { :>> id = "c0f1a5cc-9204-4a10-9b20-a1b2c3d49204"; :>> title = "Deleting an account leaves its vault data on disk; reusing the username inherits it"; :>> createdAt = "2026-07-05"; :>> createdBy = "wweatherholtz"; :>> description = "SEC-MED-2: users_delete removes the record + shares + tokens but never removes DATA_ROOT/<name>/, so recreating the name silently adopts the prior owner's notes. Fix: remove/quarantine the data dir on delete (or refuse to reuse a name with residual data)."; :>> discoveredInField = false; :>> relatedTask = "critiqueServerHardening"; :>> severity = Severity::Medium; }
    part issueRegisterEnumeration : Issue { :>> id = "c0f1a5cc-9205-4a10-9b20-a1b2c3d49205"; :>> title = "Username enumeration via /api/register (409 exists vs 403 closed) before the invite gate"; :>> createdAt = "2026-07-05"; :>> createdBy = "wweatherholtz"; :>> description = "SEC-MED-1: the exists() check returns 409 before the closed-mode/invite 403, so an unauthenticated caller harvests the account list on a closed server. Fix: enforce the invite/mode gate before the existence check; uniform error."; :>> discoveredInField = false; :>> relatedTask = "critiqueServerHardening"; :>> severity = Severity::Medium; }
    part issueLoginRateLimit : Issue { :>> id = "c0f1a5cc-9206-4a10-9b20-a1b2c3d49206"; :>> title = "No rate-limiting on /api/login (+ open /api/register); each attempt runs argon2"; :>> createdAt = "2026-07-05"; :>> createdBy = "wweatherholtz"; :>> description = "SEC-MED-3: unauthenticated auth endpoints run a full argon2 verify/hash per request with no throttle, enabling online brute force + CPU/RAM-exhaustion DoS. Fix: per-IP + per-account rate limiting/backoff + a concurrency cap."; :>> discoveredInField = false; :>> relatedTask = "critiqueServerHardening"; :>> severity = Severity::Medium; }
    part issueCommitOrdering : Issue { :>> id = "c0f1a5cc-9207-4a10-9b20-a1b2c3d49207"; :>> title = "commit writes the bind-mount file before the durable journal; a crash + reindex resurrects uncommitted content"; :>> createdAt = "2026-07-05"; :>> createdBy = "wweatherholtz"; :>> description = "DI-3: std::fs::write precedes the journal append; a crash/rollback in that window leaves disk ahead of the index, and reindex (which rebuilds from disk) then makes the never-committed body canonical. Fix: write the file after the journal is durable (temp + rename post-journal)."; :>> discoveredInField = false; :>> relatedTask = "critiqueServerHardening"; :>> severity = Severity::Medium; }
    part issueReindexDestructive : Issue { :>> id = "c0f1a5cc-9208-4a10-9b20-a1b2c3d49208"; :>> title = "reindex over an incomplete vault dir drops absent files from the manifest and GCs their chunks"; :>> createdAt = "2026-07-05"; :>> createdBy = "wweatherholtz"; :>> description = "DI-4: reindex rebuilds solely from present files and GCs unreferenced blobs, so a transiently-incomplete dir (partial restore / in-flight copy) becomes permanent loss — feeding DI-1's client deletions. Fix: refuse/preserve when a previously-indexed path is missing from disk during a repair; never GC blobs for prior-index paths."; :>> discoveredInField = false; :>> relatedTask = "critiqueServerHardening"; :>> severity = Severity::Medium; }
    part issueCritiqueLows : Issue { :>> id = "c0f1a5cc-9209-4a10-9b20-a1b2c3d49209"; :>> title = "Low-severity critique backlog (path double-separator, switch TOCTOU/streaming, self-write window, CORS, dead invite config)"; :>> createdAt = "2026-07-05"; :>> createdBy = "wweatherholtz"; :>> description = "Lumped Lows: CO-5 (a//b vs a/b distinct index entries — reject empty separators), DI-5 (switchTo upload pairs base with a re-read after the hash — return hashed bytes), DI-6 (switchTo download doesn't stream + skips large files), CO-6 (self-write suppression window swallows a genuine external edit within 4s — make it one-shot), SEC-LOW-2 (permissive CORS on /api/admin — restrict origin), SEC-LOW-1 (dead INVITE_CODE config — implement or remove)."; :>> discoveredInField = false; :>> relatedTask = "critiqueServerHardening"; :>> severity = Severity::Low; }

    #Resolves dependency from critiqueClientWave to issueBulkDeleteGuard;
    #Resolves dependency from critiqueClientWave to issueDownloadIntegrity;
    #Resolves dependency from critiqueClientWave to issueStaleBaseRecreate;
    #Resolves dependency from critiqueClientWave to issueOfflineStuck;
    #Resolves dependency from critiqueClientWave to issueConfigEditVsDelete;
    #Resolves dependency from critiqueServerHardening to issueDefaultAdminCreds;
    #Resolves dependency from critiqueServerHardening to issueWsTokenInUrl;
    #Resolves dependency from critiqueServerHardening to issueSharePluginRce;
    #Resolves dependency from critiqueServerHardening to issueAcctDeleteRemanence;
    #Resolves dependency from critiqueServerHardening to issueRegisterEnumeration;
    #Resolves dependency from critiqueServerHardening to issueLoginRateLimit;
    #Resolves dependency from critiqueServerHardening to issueCommitOrdering;
    #Resolves dependency from critiqueServerHardening to issueReindexDestructive;
    #Resolves dependency from critiqueServerHardening to issueCritiqueLows;

    // =====================================================================
    // ROUND 1 — a SECOND, fresh 3-lens adversarial critique (data-integrity / security /
    // concurrency) by independent critics against the hardened code, 2026-07-05. 18 NEW findings;
    // 15 fixed + shipped 0.10.17 (#Resolves round1CriticFixes, done); 3 dispositioned accept-risk/
    // defer as genuine future work (#Resolves round1DeferredHardening, OPEN).
    // =====================================================================
    // ---- fixed in 0.10.17 (round1CriticFixes) ----
    part issueSwitchNoAcceptsGate : Issue { :>> id = "c0f1a5cc-9301-4a10-9b20-a1b2c3d49301"; :>> title = "Vault switch bypassed the selective-sync accepts() gate, deleting another device's config on the server"; :>> createdAt = "2026-07-05"; :>> createdBy = "wweatherholtz"; :>> description = "DI#1: switchTo iterated the RAW server manifest, so an 'upload' switch from a device filtering out a .obsidian category deleted every such file on the server (wiping another device's plugins/themes/settings), and a 'download' switch recorded a base for filtered paths (later misread as delete-remote). Fixed: switchTo filters the manifest through the same accepts() gate reconcileOne uses."; :>> discoveredInField = false; :>> relatedTask = "round1CriticFixes"; :>> severity = Severity::High; }
    part issueStreamNoVerify : Issue { :>> id = "c0f1a5cc-9302-4a10-9b20-a1b2c3d49302"; :>> title = "Streamed large-file downloads skipped the reassembly hash verification the buffered path enforces"; :>> createdAt = "2026-07-05"; :>> createdBy = "wweatherholtz"; :>> description = "DI#2: streamFileToDisk appended chunks straight to disk and applyPull stamped base=claimed-hash without re-hashing, so on-disk server bit rot laundered into a known-good base and pushed back as canonical corruption. Fixed: verify each fetched chunk against its content address before writing (streaming-friendly; content-addressed ⇒ all-chunks-good ⇒ file good). +negative test."; :>> discoveredInField = false; :>> relatedTask = "round1CriticFixes"; :>> severity = Severity::High; }
    part issuePullRaceClobber : Issue { :>> id = "c0f1a5cc-9303-4a10-9b20-a1b2c3d49303"; :>> title = "A local save landing during a pull's network fetch was silently clobbered (no conflict copy)"; :>> createdAt = "2026-07-05"; :>> createdBy = "wweatherholtz"; :>> description = "DI#3: the applying guard serializes reconcile but not the editor's autosave; a save during fetchVerified's multi-chunk fetch was overwritten by the pull and resolved as clean in-sync. Fixed: applyPull re-checks disk just before writing and preserves a changed local file as a conflict copy."; :>> discoveredInField = false; :>> relatedTask = "round1CriticFixes"; :>> severity = Severity::Medium; }
    part issueEventPathRatioGuard : Issue { :>> id = "c0f1a5cc-9304-4a10-9b20-a1b2c3d49304"; :>> title = "The per-file event path applied only the empty-manifest delete guard, not the widened ratio guard"; :>> createdAt = "2026-07-05"; :>> createdBy = "wweatherholtz"; :>> description = "DI#5: reconcilePath set guardDelete only when the whole manifest was empty, so a PARTIAL server index loss slipped delete-local through the event path (which handles most live-editing deletions). Fixed: reconcilePath computes the same base-missing ratio guard reconcileAll uses."; :>> discoveredInField = false; :>> relatedTask = "round1CriticFixes"; :>> severity = Severity::Medium; }
    part issuePersistLostUpdate : Issue { :>> id = "c0f1a5cc-9305-4a10-9b20-a1b2c3d49305"; :>> title = "Fire-and-forget persist() fan-out raced, dropping a base entry (corrupted merge ancestor)"; :>> createdAt = "2026-07-05"; :>> createdBy = "wweatherholtz"; :>> description = "CONC#1: reconcileAll fired void persist() per setBase, so N concurrent saveData writes to data.json could land out of order and an earlier snapshot overwrote a later one, losing a base entry. Fixed: single-flight coalescing writer — one write at a time, trailing write re-snapshots the latest state."; :>> discoveredInField = false; :>> relatedTask = "round1CriticFixes"; :>> severity = Severity::High; }
    part issueApplyingLeak : Issue { :>> id = "c0f1a5cc-9306-4a10-9b20-a1b2c3d49306"; :>> title = "A throw from the status-callback dispatch (set before the try) leaked the `applying` lock true forever"; :>> createdAt = "2026-07-05"; :>> createdBy = "wweatherholtz"; :>> description = "CONC#2: every 'applying=true; dispatch(); try{}' site set the guard before entering the try; the dispatch fires arbitrary settings-UI code, and a throw left applying/connecting true permanently, wedging all sync until reload. Fixed: dispatch moved INSIDE the try at all sites."; :>> discoveredInField = false; :>> relatedTask = "round1CriticFixes"; :>> severity = Severity::Medium; }
    part issueWsNoRedial : Issue { :>> id = "c0f1a5cc-9307-4a10-9b20-a1b2c3d49307"; :>> title = "A WS-only drop while polling stayed healthy never re-established instant sync"; :>> createdAt = "2026-07-05"; :>> createdBy = "wweatherholtz"; :>> description = "CONC#3: connectWs ran only inside reconnect(), which is re-entered only on a POLL failure; a proxy/idle-timeout WS close (with polls still 200) silently degraded the session to 4s polling. Fixed: spinUpWs self-heals via a guarded, delayed re-dial on close, independent of poll health."; :>> discoveredInField = false; :>> relatedTask = "round1CriticFixes"; :>> severity = Severity::Medium; }
    part issueWsTickBurst : Issue { :>> id = "c0f1a5cc-9308-4a10-9b20-a1b2c3d49308"; :>> title = "Server WS keepalive could false-disconnect a healthy client (interval Burst double-tick)"; :>> createdAt = "2026-07-05"; :>> createdBy = "wweatherholtz"; :>> description = "CONC#4: a busy change stream could starve the ping branch, then two interval ticks fire back-to-back (default Burst) and see awaiting_pong still true with the Pong unread → spurious disconnect. Fixed: MissedTickBehavior::Delay on the ping interval."; :>> discoveredInField = false; :>> relatedTask = "round1CriticFixes"; :>> severity = Severity::Low; }
    part issueDrainDrop : Issue { :>> id = "c0f1a5cc-9309-4a10-9b20-a1b2c3d49309"; :>> title = "drainPending consumed a queued edit before attempting it and never re-queued on failure"; :>> createdAt = "2026-07-05"; :>> createdBy = "wweatherholtz"; :>> description = "CONC#6: the queued path was deleted before reconcilePath and the catch didn't re-add it; a transient failure dropped it from the fast path (recovered only by the next full reconcile). Fixed: re-queue on failure and stop draining (a later poll/reconnect retries) — no drop, no hot-spin."; :>> discoveredInField = false; :>> relatedTask = "round1CriticFixes"; :>> severity = Severity::Low; }
    part issueUserCaseCollision : Issue { :>> id = "c0f1a5cc-9310-4a10-9b20-a1b2c3d49310"; :>> title = "Username case-collision on a case-insensitive FS gave cross-account vault access"; :>> createdAt = "2026-07-05"; :>> createdBy = "wweatherholtz"; :>> description = "SEC#1: the user store keys case-sensitively but DATA_ROOT/<user>/<vault> collapses case on Windows/macOS, so 'Alice' and 'alice' were distinct accounts sharing one directory — one could read/write the other's vault (and 'ADMIN' vs 'admin' the admin's data). Fixed: safe_name is lowercase-canonical, so store-key == on-disk segment; no two names collide. +test."; :>> discoveredInField = false; :>> relatedTask = "round1CriticFixes"; :>> severity = Severity::High; }
    part issueArgonDos : Issue { :>> id = "c0f1a5cc-9311-4a10-9b20-a1b2c3d49311"; :>> title = "Unauthenticated argon2 flood on /api/login ran on async workers with no length cap or concurrency bound"; :>> createdAt = "2026-07-05"; :>> createdBy = "wweatherholtz"; :>> description = "SEC#2: login ran the memory-hard argon2 verify directly on a tokio worker, holding the users mutex, with no password-length cap — a concurrent flood (optionally multi-MB passwords) exhausts CPU/RAM. Fixed: cap password length (1 KiB), release the lock first, run argon2 on a blocking thread bounded by an 8-permit semaphore; register offloaded too."; :>> discoveredInField = false; :>> relatedTask = "round1CriticFixes"; :>> severity = Severity::Medium; }
    part issueVaultCapMissing : Issue { :>> id = "c0f1a5cc-9312-4a10-9b20-a1b2c3d49312"; :>> title = "No per-account vault cap: unbounded never-evicted handles + inodes"; :>> createdAt = "2026-07-05"; :>> createdBy = "wweatherholtz"; :>> description = "SEC#3: create_vault had no limit; an authenticated user could loop-create unique vaults, each a never-evicted cached handle + directory tree, degrading every tenant (RAM + inodes). Fixed: cap at 100 vaults per account."; :>> discoveredInField = false; :>> relatedTask = "round1CriticFixes"; :>> severity = Severity::Medium; }
    part issueCommitRamCeiling : Issue { :>> id = "c0f1a5cc-9313-4a10-9b20-a1b2c3d49313"; :>> title = "A single commit could allocate up to 2 GiB reassembling the body in RAM"; :>> createdAt = "2026-07-05"; :>> createdBy = "wweatherholtz"; :>> description = "SEC#5: commit reassembles the whole file into one Vec bounded only by MAX_FILE_BYTES=2 GiB; several concurrent large commits could OOM. Fixed: lowered MAX_FILE_BYTES to 512 MiB (well above any real attachment) to bound the transient allocation."; :>> discoveredInField = false; :>> relatedTask = "round1CriticFixes"; :>> severity = Severity::Low; }
    part issueInternalErrLeak : Issue { :>> id = "c0f1a5cc-9314-4a10-9b20-a1b2c3d49314"; :>> title = "Internal (500) error bodies returned std::io messages that can carry absolute server paths"; :>> createdAt = "2026-07-05"; :>> createdBy = "wweatherholtz"; :>> description = "SEC#6: AppError::Internal(m) returned m verbatim to the client, disclosing server filesystem/IO detail. Fixed: log the detail server-side, return a generic 'internal error' body."; :>> discoveredInField = false; :>> relatedTask = "round1CriticFixes"; :>> severity = Severity::Low; }
    part issueReservedWinNames : Issue { :>> id = "c0f1a5cc-9315-4a10-9b20-a1b2c3d49315"; :>> title = "Windows reserved device basenames (con/nul/com1..) passed safe_rel_path"; :>> createdAt = "2026-07-05"; :>> createdBy = "wweatherholtz"; :>> description = "SEC#7: a note named e.g. con.md is a DOS device on a Windows host; the mirror write would hang/error and could wedge the write. Fixed: safe_rel_path rejects reserved basenames (case-insensitive, with/without extension). +test."; :>> discoveredInField = false; :>> relatedTask = "round1CriticFixes"; :>> severity = Severity::Low; }
    // ---- dispositioned accept-risk / deferred (round1DeferredHardening, OPEN) ----
    part issueOrphanChunkQuota : Issue { :>> id = "c0f1a5cc-9316-4a10-9b20-a1b2c3d49316"; :>> title = "Uncommitted orphan chunks are reclaimed only at startup; no runtime per-vault byte quota"; :>> createdAt = "2026-07-05"; :>> createdBy = "wweatherholtz"; :>> description = "SEC#4 (DEFERRED): a ReadWrite grantee (or owner) can PUT unlimited unique chunks that never commit, filling the owner's disk until a restart's GC. Mitigated for now by the lowered 512 MiB per-file ceiling; a per-vault stored-bytes quota / runtime orphan GC is the real fix — deferred as its own change. Authenticated-only, DoS not data-loss."; :>> discoveredInField = false; :>> relatedTask = "round1DeferredHardening"; :>> severity = Severity::Medium; }
    part issueReindexBindMount : Issue { :>> id = "c0f1a5cc-9317-4a10-9b20-a1b2c3d49317"; :>> title = "reindex adopts bind-mount bytes over the chunk store, silently rolling back after a mirror-write failure"; :>> createdAt = "2026-07-05"; :>> createdBy = "wweatherholtz"; :>> description = "DI#4 (DEFERRED/ACCEPT): reindex rebuilds solely from materialized files, so if a prior best-effort mirror write failed (bind-mount stale vs index+chunkstore new) an operator reindex adopts the stale bytes. Narrow: reindex is an explicit operator repair for a corrupt index, and DI-3 (write-after-journal) makes the stale-mirror window rare. Fix (prefer chunk-store content when a healthy index disagrees) deferred; low real-world likelihood."; :>> discoveredInField = false; :>> relatedTask = "round1DeferredHardening"; :>> severity = Severity::Low; }
    part issueSwitchPendingClear : Issue { :>> id = "c0f1a5cc-9318-4a10-9b20-a1b2c3d49318"; :>> title = "pendingSwitchMode is cleared up-front, so a mid-switch failure downgrades an authoritative overwrite to a merge"; :>> createdAt = "2026-07-05"; :>> createdBy = "wweatherholtz"; :>> description = "CONC#5 (ACCEPT-RISK): switchTo clears pendingSwitchMode + the base up front, so a throw mid-switch leaves the next reconnect running reconcileAll over an empty base (conflict-copies divergence). This is a deliberate choice — it avoids silently RE-applying a destructive download/upload on a later reconnect, and conflict-copies preserve both sides (no data lost, just a surprising state). Keeping-until-success is the tracked improvement."; :>> discoveredInField = false; :>> relatedTask = "round1DeferredHardening"; :>> severity = Severity::Low; }

    #Resolves dependency from round1CriticFixes to issueSwitchNoAcceptsGate;
    #Resolves dependency from round1CriticFixes to issueStreamNoVerify;
    #Resolves dependency from round1CriticFixes to issuePullRaceClobber;
    #Resolves dependency from round1CriticFixes to issueEventPathRatioGuard;
    #Resolves dependency from round1CriticFixes to issuePersistLostUpdate;
    #Resolves dependency from round1CriticFixes to issueApplyingLeak;
    #Resolves dependency from round1CriticFixes to issueWsNoRedial;
    #Resolves dependency from round1CriticFixes to issueWsTickBurst;
    #Resolves dependency from round1CriticFixes to issueDrainDrop;
    #Resolves dependency from round1CriticFixes to issueUserCaseCollision;
    #Resolves dependency from round1CriticFixes to issueArgonDos;
    #Resolves dependency from round1CriticFixes to issueVaultCapMissing;
    #Resolves dependency from round1CriticFixes to issueCommitRamCeiling;
    #Resolves dependency from round1CriticFixes to issueInternalErrLeak;
    #Resolves dependency from round1CriticFixes to issueReservedWinNames;
    #Resolves dependency from round1DeferredHardening to issueOrphanChunkQuota;
    // issueReindexBindMount was deferred/accepted in Round 1 but INDEPENDENTLY REDISCOVERED by the
    // Round-6 DI critic (a healthy-vault reindex reverting to a stale mirror) — un-deferred + fixed.
    #Resolves dependency from round6CriticFixes to issueReindexBindMount;
    #Resolves dependency from round1DeferredHardening to issueSwitchPendingClear;

    // =====================================================================
    // ROUND 2 — a THIRD fresh 3-lens adversarial critique (independent critics) against the
    // 0.10.17-hardened code, 2026-07-05. 16 NEW findings; 15 fixed + shipped 0.10.18
    // (#Resolves round2CriticFixes, done); several exposed GAPS in the Round-1 fixes themselves
    // (unverified cached chunks bypassing DI-2; stranded requeue from CONC#6; SEC#1 not covering
    // in-vault file paths). The 1 residual (large-file pull TOCTOU) is inherent + accepted.
    // =====================================================================
    part issueCacheUnverified : Issue { :>> id = "c0f1a5cc-9401-4a10-9b20-a1b2c3d49401"; :>> title = "Cached chunks bypassed DI-2 verification, laundering server bit-rot into a streamed file"; :>> createdAt = "2026-07-05"; :>> createdBy = "wweatherholtz"; :>> description = "DI-R2#1 (HIGH): fetchFileBytes cached chunks unverified and streamFileToDisk verified only on a cache MISS, so a corrupt blob cached during an aborted buffered fetch was trusted on a later dedup cache hit and re-pushed as canonical corruption. Fixed: getVerifiedChunk verifies before caching in both paths. +test."; :>> discoveredInField = false; :>> relatedTask = "round2CriticFixes"; :>> severity = Severity::High; }
    part issuePullGapsStreamCreate : Issue { :>> id = "c0f1a5cc-9402-4a10-9b20-a1b2c3d49402"; :>> title = "DI-3 racing-edit guard missed the streamed branch and the racing-create case"; :>> createdAt = "2026-07-05"; :>> createdBy = "wweatherholtz"; :>> description = "DI-R2#2/#4: applyPull's guard ran only on the buffered path and only when the local file was present, so a large-file stream (or a racing local CREATE of an expected-absent path) silently clobbered local content. Fixed: shared conflictCopyIfRaced + guardRace flag covering both paths and the absent-expected case."; :>> discoveredInField = false; :>> relatedTask = "round2CriticFixes"; :>> severity = Severity::Medium; }
    part issueMergeBaseDesync : Issue { :>> id = "c0f1a5cc-9403-4a10-9b20-a1b2c3d49403"; :>> title = "pushBytes discarded committed bytes; clean-merge base could record disagreeing (text,hash)"; :>> createdAt = "2026-07-05"; :>> createdBy = "wweatherholtz"; :>> description = "DI-R2#3: the merge path set base from pre-write merged bytes while the hash came from pushFile's re-read — a racing save between them desynced base.text vs base.hash, poisoning the next merge's ancestor. Fixed: pushBytes returns PushResult; base recorded from committed bytes (DI-5 on the merge path)."; :>> discoveredInField = false; :>> relatedTask = "round2CriticFixes"; :>> severity = Severity::Medium; }
    part issueConflictCopyStale : Issue { :>> id = "c0f1a5cc-9404-4a10-9b20-a1b2c3d49404"; :>> title = "Merge/conflict copies preserved the stale pre-fetch local read, not a racing edit"; :>> createdAt = "2026-07-05"; :>> createdBy = "wweatherholtz"; :>> description = "DI-R2#5: the merge/conflict-copy and read-only-share fallbacks wrote the localBytes read before the remote fetch as the conflict copy, so an edit made DURING the fetch was lost. Fixed: re-read current on-disk bytes for the copy. Also: bulk-delete ratio denominator now counts only accepted base paths (note)."; :>> discoveredInField = false; :>> relatedTask = "round2CriticFixes"; :>> severity = Severity::Medium; }
    part issueDrainStranded : Issue { :>> id = "c0f1a5cc-9405-4a10-9b20-a1b2c3d49405"; :>> title = "A re-queued edit was stranded on the idle-poll short-circuit under a green light"; :>> createdAt = "2026-07-05"; :>> createdBy = "wweatherholtz"; :>> description = "CONC-R2#1 (HIGH): onRemoteChanged's idle short-circuit returned before the drainPending() call, so a path re-queued by the CONC#6 fix was never retried while syncDone flipped the light green over the unsynced edit. Fixed: drainPending runs in the finally on every path."; :>> discoveredInField = false; :>> relatedTask = "round2CriticFixes"; :>> severity = Severity::High; }
    part issueDirectOpNoRequeue : Issue { :>> id = "c0f1a5cc-9406-4a10-9b20-a1b2c3d49406"; :>> title = "A directly-attempted local op that failed was neither re-queued nor retried"; :>> createdAt = "2026-07-05"; :>> createdBy = "wweatherholtz"; :>> description = "CONC-R2#2: onLocalEvent/Delete/Rename only logged on catch, relying on the next full reconcile; on an idle remote a transient failure left the edit unsynced for a long time. Fixed: re-queue the path(s) into pendingLocal on catch so the drain retries."; :>> discoveredInField = false; :>> relatedTask = "round2CriticFixes"; :>> severity = Severity::Medium; }
    part issueVersionRewindPin : Issue { :>> id = "c0f1a5cc-9407-4a10-9b20-a1b2c3d49407"; :>> title = "Math.max version cursor pinned high after a server rewind, forcing a full reconcile every poll"; :>> createdAt = "2026-07-05"; :>> createdBy = "wweatherholtz"; :>> description = "CONC-R2#3: reconcileAll/switchTo advanced the cursor with Math.max, so after a server reindex/restore rewound the version, every idle poll saw a mismatch and re-ran a full reconcile forever. Fixed: ASSIGN resp.version after a full reconcile (the client is consistent with it), so the incremental path converges."; :>> discoveredInField = false; :>> relatedTask = "round2CriticFixes"; :>> severity = Severity::Medium; }
    part issueWsRedialRaces : Issue { :>> id = "c0f1a5cc-9408-4a10-9b20-a1b2c3d49408"; :>> title = "WS self-heal redial: stale-timer race, backoff inflation on lock-defer, expired-token redial storm"; :>> createdAt = "2026-07-05"; :>> createdBy = "wweatherholtz"; :>> description = "CONC-R2#4/#5/#6: the CONC#3 redial could be armed by the old socket during a reconnect (racing it on failure); deferring reconnect for the applying lock doubled backoff toward the cap; a socket that never opened (expired token) re-dialed every 3s with the dead token. Fixed: reconnect cancels wsRedialTimer; lock-defer passes bumpBackoff=false; a never-opened socket escalates to a full reconnect."; :>> discoveredInField = false; :>> relatedTask = "round2CriticFixes"; :>> severity = Severity::Low; }
    part issueSelfFolderCase : Issue { :>> id = "c0f1a5cc-9409-4a10-9b20-a1b2c3d49409"; :>> title = "Case-sensitive self-folder exclusion let a shared vault overwrite the victim's SelfSync credentials"; :>> createdAt = "2026-07-05"; :>> createdBy = "wweatherholtz"; :>> description = "SEC-R2#1 (MED, connection hijack): shouldSync compared the self-folder path case-sensitively while SEC#1 canonicalized only user/vault segments (not in-vault file paths), so a shared-vault owner committing .obsidian/plugins/NEW-LIVESYNC/data.json overwrote the victim's stored server URL+creds on a case-insensitive FS. Fixed: case-insensitive self-folder exclusion. +test."; :>> discoveredInField = false; :>> relatedTask = "round2CriticFixes"; :>> severity = Severity::Medium; }
    part issueReindexJunkBrick : Issue { :>> id = "c0f1a5cc-940a-4a10-9b20-a1b2c3d4940a"; :>> title = "A committed junk-named file (.DS_Store/.git) permanently bricks reindex (cross-account)"; :>> createdAt = "2026-07-05"; :>> createdBy = "wweatherholtz"; :>> description = "SEC-R2#2: commit accepted names that reindex's collect_files skips as junk, so a later reindex counted them as 'indexed file missing from disk' (DI-4) and aborted every time — leaving the vault stuck in ERROR; a readWrite grantee could inflict it on the owner. Fixed: safe_rel_path rejects junk basenames. +test."; :>> discoveredInField = false; :>> relatedTask = "round2CriticFixes"; :>> severity = Severity::Medium; }
    part issueWsRevokeLeak : Issue { :>> id = "c0f1a5cc-940b-4a10-9b20-a1b2c3d4940b"; :>> title = "Share revocation didn't evict an in-flight WebSocket; revoked grantee kept getting change metadata"; :>> createdAt = "2026-07-05"; :>> createdBy = "wweatherholtz"; :>> description = "SEC-R2#3: the WS authorized only at connect and never re-checked, so after share_delete the grantee's open socket kept receiving {type:changed,version} frames (content stays protected by per-request HTTP re-auth, but edit-timing + version counts leaked). Fixed: re-check the ACL before forwarding each notification; drop on revoke."; :>> discoveredInField = false; :>> relatedTask = "round2CriticFixes"; :>> severity = Severity::Low; }
    part issueAdminCreateArgon : Issue { :>> id = "c0f1a5cc-940c-4a10-9b20-a1b2c3d4940c"; :>> title = "Admin users_create bypassed the SEC-2 password cap + argon2 blocking-thread/semaphore"; :>> createdAt = "2026-07-05"; :>> createdBy = "wweatherholtz"; :>> description = "SEC-R2#4: users_create hashed on the async runtime with no length cap, outside the auth_slots/spawn_blocking path (admin-gated, so low impact, matters more under ALLOW_WEAK_ADMIN=1). Fixed: enforce MAX_PASSWORD_LEN + run via the semaphore-bounded blocking path."; :>> discoveredInField = false; :>> relatedTask = "round2CriticFixes"; :>> severity = Severity::Low; }
    part issuePullTOCTOUResidual : Issue { :>> id = "c0f1a5cc-940d-4a10-9b20-a1b2c3d4940d"; :>> title = "Residual TOCTOU in the pull racing-edit check (edit landing between hash and write)"; :>> createdAt = "2026-07-05"; :>> createdBy = "wweatherholtz"; :>> description = "CONC-R2#7 / DI-adjacent (ACCEPT — inherent): the DI-3 disk re-check narrows but cannot fully close the window, since a local save can land between curHash and the final io.write; closing it entirely would require blocking Obsidian's own disk writes. Accepted as an inherent narrowing; the common cases are guarded."; :>> discoveredInField = false; :>> relatedTask = "residualLowFindings"; :>> severity = Severity::Low; }

    #Resolves dependency from round2CriticFixes to issueCacheUnverified;
    #Resolves dependency from round2CriticFixes to issuePullGapsStreamCreate;
    #Resolves dependency from round2CriticFixes to issueMergeBaseDesync;
    #Resolves dependency from round2CriticFixes to issueConflictCopyStale;
    #Resolves dependency from round2CriticFixes to issueDrainStranded;
    #Resolves dependency from round2CriticFixes to issueDirectOpNoRequeue;
    #Resolves dependency from round2CriticFixes to issueVersionRewindPin;
    #Resolves dependency from round2CriticFixes to issueWsRedialRaces;
    #Resolves dependency from round2CriticFixes to issueSelfFolderCase;
    #Resolves dependency from round2CriticFixes to issueReindexJunkBrick;
    #Resolves dependency from round2CriticFixes to issueWsRevokeLeak;
    #Resolves dependency from round2CriticFixes to issueAdminCreateArgon;
    #Resolves dependency from d0020 to issuePullTOCTOUResidual;

    // =====================================================================
    // ROUND 3 — a FOURTH fresh 3-lens critique (independent critics) vs the 0.10.18 code,
    // 2026-07-05. 8 NEW findings (convergence: 18 → 16 → 8, severity falling). 6 fixed + shipped
    // 0.10.19 (#Resolves round3CriticFixes); 2 deferred (#Resolves round1DeferredHardening). Two
    // of the fixed were GAPS in Round-2 fixes (clean-merge stale local; Lagged skipping the ACL).
    // =====================================================================
    part issueMergeStaleLocal : Issue { :>> id = "c0f1a5cc-9501-4a10-9b20-a1b2c3d49501"; :>> title = "Clean auto-merge fed stale localBytes into merge3, silently dropping a save that raced the fetch"; :>> createdAt = "2026-07-05"; :>> createdBy = "wweatherholtz"; :>> description = "DI-R3#1 (MED-HIGH): the DI-R2#5 fix re-read current disk for the conflict-copy + read-only paths but NOT the clean-merge branch, which still merged base+STALE-local+remote and overwrote disk — losing keystrokes autosaved during the multi-chunk fetch, with no conflict copy. Fixed: re-read current disk (liveLocal) after the fetch and use it for the whole merge/conflict decision."; :>> discoveredInField = false; :>> relatedTask = "round3CriticFixes"; :>> severity = Severity::High; }
    part issueWsRedialMidReconnect : Issue { :>> id = "c0f1a5cc-9502-4a10-9b20-a1b2c3d49502"; :>> title = "A WS redial armed mid-reconnect wasn't cancelled on the reconnect-failure path"; :>> createdAt = "2026-07-05"; :>> createdBy = "wweatherholtz"; :>> description = "CONC-R3#1: the CONC-R2#4 clear ran only at reconnect ENTRY, so a redial armed by the old socket's close DURING the reconnect's awaits survived a failed reconnect and fired spinUpWs with a stale token, racing the backoff reconnect. Fixed: scheduleReconnect cancels any pending wsRedialTimer (a full reconnect supersedes a redial)."; :>> discoveredInField = false; :>> relatedTask = "round3CriticFixes"; :>> severity = Severity::Low; }
    part issueRemoteChangeDropped : Issue { :>> id = "c0f1a5cc-9503-4a10-9b20-a1b2c3d49503"; :>> title = "A remote notification arriving during an active reconcile was dropped (waited for the 4s poll)"; :>> createdAt = "2026-07-05"; :>> createdBy = "wweatherholtz"; :>> description = "CONC-R3#3: onRemoteChanged returned on the applying guard without noting the pending remote change, so a commit landing mid-reconcile synced only at the next 4s poll (losing the WS's instant property). Fixed: a remoteDirty flag re-runs onRemoteChanged once the current reconcile finishes."; :>> discoveredInField = false; :>> relatedTask = "round3CriticFixes"; :>> severity = Severity::Low; }
    part issueLaggedNoAcl : Issue { :>> id = "c0f1a5cc-9504-4a10-9b20-a1b2c3d49504"; :>> title = "The WS Lagged arm skipped the per-notification ACL re-check (revoked-but-lagging grantee leak)"; :>> createdAt = "2026-07-05"; :>> createdBy = "wweatherholtz"; :>> description = "CONC-R3#2: the SEC-R2#3 ACL re-check was only on the Ok(version) arm; a continuously-lagging revoked grantee kept getting {type:changed} activity nudges (timing metadata; no version/paths, follow-up reads are 403). Fixed: re-check the ACL in the Lagged arm too and break if unauthorized."; :>> discoveredInField = false; :>> relatedTask = "round3CriticFixes"; :>> severity = Severity::Low; }
    part issueTrailingNameDesync : Issue { :>> id = "c0f1a5cc-9505-4a10-9b20-a1b2c3d49505"; :>> title = "Trailing-dot/space names bypassed safe_rel_path, desyncing index key vs on-disk name (Windows)"; :>> createdAt = "2026-07-05"; :>> createdBy = "wweatherholtz"; :>> description = "SEC-R3#1 (MED): safe_rel_path didn't reject a component ending in '.' or space (or all-dots), which Windows strips on write — so index key 'evil.md.' != on-disk 'evil.md', re-opening the DI-4 reindex-brick, and 'aux ' evaded the reserved-device check (→ AUX). Fixed: reject trailing-dot/space + all-dot components (safe superset on Linux). +test."; :>> discoveredInField = false; :>> relatedTask = "round3CriticFixes"; :>> severity = Severity::Medium; }
    part issuePurgeOrdering : Issue { :>> id = "c0f1a5cc-9506-4a10-9b20-a1b2c3d49506"; :>> title = "Account-delete removed the user row before a best-effort data purge; a failed purge left inheritable data"; :>> createdAt = "2026-07-05"; :>> createdBy = "wweatherholtz"; :>> description = "SEC-R3#2 (SEC-MED-2 residual): users_delete removed the users.json row first, then purged data best-effort (WARN on failure), so a locked-file purge failure left DATA_ROOT/<name>/ for a same-name recreation to inherit. Fixed: purge data FIRST and hard-error on failure, so a failure leaves the account intact + retryable and the row is removed only once data is provably gone."; :>> discoveredInField = false; :>> relatedTask = "round3CriticFixes"; :>> severity = Severity::Low; }
    // ---- deferred (round1DeferredHardening, OPEN) ----
    part issueStreamWholeHash : Issue { :>> id = "c0f1a5cc-9507-4a10-9b20-a1b2c3d49507"; :>> title = "Streamed download verifies each chunk but not the reassembled whole-file hash (wrong chunk LIST)"; :>> createdAt = "2026-07-05"; :>> createdBy = "wweatherholtz"; :>> description = "DI-R3#2 (LOW, DEFERRED): streamFileToDisk verifies each chunk's content address but not that the concatenation equals rmeta.hash, so a wrong chunk LIST (valid chunks, wrong order/set) isn't caught the way the buffered fetchVerified catches it. Not a live path (chunk lists are verified at commit; corrupt manifest JSON → ERROR state, not a valid-but-wrong list) and a true streaming whole-file verify needs an incremental SHA-256 the client's WebCrypto (one-shot digest) doesn't provide without buffering. Deferred defense-in-depth parity."; :>> discoveredInField = false; :>> relatedTask = "residualLowFindings"; :>> severity = Severity::Low; }
    part issueReindexSingleChunk : Issue { :>> id = "c0f1a5cc-9508-4a10-9b20-a1b2c3d49508"; :>> title = "reindex stores each whole file as ONE chunk, defeating client streaming + the chunk-size ceiling"; :>> createdAt = "2026-07-05"; :>> createdBy = "wweatherholtz"; :>> description = "DI-R3#3 (LOW, DEFERRED): reindex (operator recovery) rebuilds from materialized files but stores each whole file as a single blob, so a large reindexed file becomes one huge chunk that getVerifiedChunk buffers whole (OOM risk on mobile) until the file is next edited client-side. Content stays correct + hash-verified. Fixing needs a Rust CDC chunker matching the client's gear-hash — a tracked enhancement; low real-world impact (operator-triggered, self-corrects on next edit)."; :>> discoveredInField = false; :>> relatedTask = "residualLowFindings"; :>> severity = Severity::Low; }

    #Resolves dependency from round3CriticFixes to issueMergeStaleLocal;
    #Resolves dependency from round3CriticFixes to issueWsRedialMidReconnect;
    #Resolves dependency from round3CriticFixes to issueRemoteChangeDropped;
    #Resolves dependency from round3CriticFixes to issueLaggedNoAcl;
    #Resolves dependency from round3CriticFixes to issueTrailingNameDesync;
    #Resolves dependency from round3CriticFixes to issuePurgeOrdering;
    #Resolves dependency from residualLowFindings to issueStreamWholeHash;
    #Resolves dependency from residualLowFindings to issueReindexSingleChunk;

    // =====================================================================
    // ROUND 4 — a FIFTH fresh 3-lens critique vs the 0.10.19 code, 2026-07-05. Convergence:
    // 18 → 16 → 8 → 2 NEW findings. SECURITY LENS CONVERGED (0 findings — every attack surface
    // traced, all prior fixes confirmed present+correct). 2 fixed + shipped 0.10.20
    // (#Resolves round4CriticFixes); 1 sub-LOW cosmetic accepted (#Resolves round1DeferredHardening).
    // =====================================================================
    part issueNoncanonicalPath : Issue { :>> id = "c0f1a5cc-9601-4a10-9b20-a1b2c3d49601"; :>> title = "Non-canonical path (notes//a.md, trailing slash) desyncs the raw index key from the on-disk name"; :>> createdAt = "2026-07-05"; :>> createdBy = "wweatherholtz"; :>> description = "DI-R4#1 (MED): commit used the RAW req.path as the index key but derived the on-disk mirror from a Path-normalized value that collapses redundant/trailing slashes, so a non-conforming/hostile client could commit two keys (notes/a.md + notes//a.md) aliasing ONE disk file (silent overwrite + double manifest entry → client phantom-delete ping-pong), or desync key-vs-disk (reindex brick). Same integrity boundary as the case-collision/junk/trailing-dot guards. Fixed: safe_rel_path rejects any path that isn't its own canonical forward-slash form. +test."; :>> discoveredInField = false; :>> relatedTask = "round4CriticFixes"; :>> severity = Severity::Medium; }
    part issueRemoteDirtyCoverage : Issue { :>> id = "c0f1a5cc-9602-4a10-9b20-a1b2c3d49602"; :>> title = "remoteDirty instant re-run honored only on the onRemoteChanged exit path (poke dropped to poll latency elsewhere)"; :>> createdAt = "2026-07-05"; :>> createdBy = "wweatherholtz"; :>> description = "CONC-R4#1 (LOW): the CONC-R3#3 remoteDirty re-run fired only in onRemoteChanged's finally (and even there drainPending could grab the lock first), so a remote poke arriving during other local activity (drain/reconnect/config-flush/delete/rename) waited for the 4s poll — losing the WS instant property (not data loss; poll backstops). Fixed: centralized the remoteDirty re-run into drainPending's exit, which every applying-releasing path already calls."; :>> discoveredInField = false; :>> relatedTask = "round4CriticFixes"; :>> severity = Severity::Low; }
    part issueTransientGreenLight : Issue { :>> id = "c0f1a5cc-9603-4a10-9b20-a1b2c3d49603"; :>> title = "Transient 'fully synced' green light while polling is briefly stopped after a blip"; :>> createdAt = "2026-07-05"; :>> createdBy = "wweatherholtz"; :>> description = "CONC-R4 cosmetic (sub-LOW, ACCEPT): after a transient reconcile error stops the poll timer + schedules reconnect, a queued edit succeeding in the same finally dispatches syncDone → FSM offline+syncDone→idle (green) while the poll interval is momentarily stopped, until the reconnect timer restarts it. Self-correcting within the backoff window, no data impact — a sub-second wrong indicator not worth a code change on its own. Accepted."; :>> discoveredInField = false; :>> relatedTask = "residualLowFindings"; :>> severity = Severity::Low; }

    #Resolves dependency from round4CriticFixes to issueNoncanonicalPath;
    #Resolves dependency from round4CriticFixes to issueRemoteDirtyCoverage;
    #Resolves dependency from d0020 to issueTransientGreenLight;

    // =====================================================================
    // ROUND 5 — the HOLISTIC + completeness + final-adversary round vs 0.10.20, 2026-07-05.
    // The final cross-boundary adversary found 5 LOW/LOW-MED (3 fixed → 0.10.21, 2 cosmetic/CAS
    // tracked) and VERIFIED the cross-cutting invariants sound. The holistic reviewer's verdict:
    // the data-safety core holds; remaining gaps are robustness/coverage/operability ENHANCEMENTS
    // (tracked open under round5CompletenessFollowups, to land before a broad release), not defects.
    // =====================================================================
    // ---- fixed in 0.10.21 (round5CriticFixes) ----
    part issueUnicodeCaseCollision : Issue { :>> id = "c0f1a5cc-9701-4a10-9b20-a1b2c3d49701"; :>> title = "PROTO-4 case-collision guard folded ASCII only; a Unicode case pair (café/CAFÉ) evaded it"; :>> createdAt = "2026-07-05"; :>> createdBy = "wweatherholtz"; :>> description = "DI-R5#1 (LOW-MED, deployment-conditional): eq_ignore_ascii_case let café.md and CAFÉ.md both enter the index while a case-insensitive Unicode-folding FS (macOS/Windows) collapses them to one file → reindex brick + phantom-delete; a readWrite grantee could inflict it. Fixed: fold full Unicode case (to_lowercase) in the collision check. +test."; :>> discoveredInField = false; :>> relatedTask = "round5CriticFixes"; :>> severity = Severity::Medium; }
    part issueLegacyKeyUndeletable : Issue { :>> id = "c0f1a5cc-9702-4a10-9b20-a1b2c3d49702"; :>> title = "A legacy file whose name the tightened safe_rel_path now rejects was undeletable (404 loop)"; :>> createdAt = "2026-07-05"; :>> createdBy = "wweatherholtz"; :>> description = "DI-R5#4 (LOW, upgrade-only): delete() returned None for a name safe_rel_path now rejects, so a file committed before the tightening (or ingested via bind-mount+reindex) 404-looped on every client delete-remote and its tombstone never propagated. Fixed: if the exact index key is present, evict it even when the name is now invalid (skip only the on-disk mirror removal). +test."; :>> discoveredInField = false; :>> relatedTask = "round5CriticFixes"; :>> severity = Severity::Low; }
    part issueDeleteRevokeRace : Issue { :>> id = "c0f1a5cc-9703-4a10-9b20-a1b2c3d49703"; :>> title = "Account delete didn't revoke the token before purge (data-remanence self-race)"; :>> createdAt = "2026-07-05"; :>> createdBy = "wweatherholtz"; :>> description = "SEC-R5#2 (LOW): between purge_user_data and revoke_user, the victim's still-valid token could create_vault / land an in-flight commit, re-materializing DATA_ROOT/<name>/ after remove_dir_all for a same-name recreation to inherit. Fixed: revoke tokens FIRST, then purge, then remove the row."; :>> discoveredInField = false; :>> relatedTask = "round5CriticFixes"; :>> severity = Severity::Low; }
    // ---- completeness/robustness enhancements, tracked OPEN (round5CompletenessFollowups) ----
    part issueVersionHandshake : Issue { :>> id = "c0f1a5cc-9704-4a10-9b20-a1b2c3d49704"; :>> title = "No client<->server protocol/schema version negotiation (independent-upgrade skew is undiagnosable)"; :>> createdAt = "2026-07-05"; :>> createdBy = "wweatherholtz"; :>> description = "Holistic#1 (MED, OPEN): /health returns bare 'ok'; no apiVersion field, no min-client check, and the on-disk Index has no schema tag. The plugin auto-updates (BRAT) independently of the server, so version skew is the most likely real-world breakage — and it surfaces as a generic 'malformed response' retry loop (SAFE, never mutates, but undiagnosable) or a scary CORRUPT→reindex. Add a version handshake + a clear 'incompatible, upgrade' message. Pre-broad-release."; :>> discoveredInField = false; :>> relatedTask = "round5CompletenessFollowups"; :>> severity = Severity::Medium; }
    part issueOrchestrationUntested : Issue { :>> id = "c0f1a5cc-9705-4a10-9b20-a1b2c3d49705"; :>> title = "The imperative main.ts orchestration layer (incl. 2 MUST reqs + the SEC-3 gate + WS push) has no automated tests"; :>> createdAt = "2026-07-05"; :>> createdBy = "wweatherholtz"; :>> description = "Holistic#2/#3/#4 (MED, OPEN): srConfigLiveDetect + srSelfHealingReconnect (both priority=must), the SEC-3 no-plugin-code-from-shared-vault gate, and WS instant-push + revocation eviction are verified by inspect+attestation only — reconnect/scheduleReconnect/connectWs/onRawConfigEvent/flushRawConfig/flushConfigReload have zero test references. This is the 0.10.4-escape code family; a regression wouldn't fail CI. Extract the FSM + raw-event pipeline into injectable units (like the pure modules) and test them. Pre-broad-release."; :>> discoveredInField = false; :>> relatedTask = "round5CompletenessFollowups"; :>> severity = Severity::Medium; }
    part issueAdminReindex : Issue { :>> id = "c0f1a5cc-9706-4a10-9b20-a1b2c3d49706"; :>> title = "Corrupt-vault reindex is owner-only via curl; no admin surface for a shared/non-owned vault"; :>> createdAt = "2026-07-05"; :>> createdBy = "wweatherholtz"; :>> description = "Holistic#5 (LOW-MED, OPEN): reindex is registered only on the own-vault route (owner==caller) with no admin-UI button, so a shared vault that goes corrupt can be repaired only by its owner via a manual curl — the selfHostOperator persona wants an admin interface. Add an admin reindex route/button."; :>> discoveredInField = false; :>> relatedTask = "round5CompletenessFollowups"; :>> severity = Severity::Low; }
    part issueCommitCas : Issue { :>> id = "c0f1a5cc-9707-4a10-9b20-a1b2c3d49707"; :>> title = "No optimistic-concurrency on commit: exact-simultaneous double-first-commit on a shared vault loses an update"; :>> createdAt = "2026-07-05"; :>> createdBy = "wweatherholtz"; :>> description = "Adversary#3 (LOW, OPEN): if owner+grantee both read meta at the same base before either commits, both decide push; the write lock serializes them, the second overwrites the first, and the first committer later pulls (B===L → pull) with no conflict copy → lost edit. The common case is safe (the second committer normally sees R!=B → merge). Add expected_version/if-match to commit so a mismatch rejects and the client re-reconciles into a merge. Pre-broad-release for multi-writer shares."; :>> discoveredInField = false; :>> relatedTask = "round5CompletenessFollowups"; :>> severity = Severity::Low; }
    part issueDataMigration : Issue { :>> id = "c0f1a5cc-9708-4a10-9b20-a1b2c3d49708"; :>> title = "No explicit forward-migration path for client base/settings or the server index schema"; :>> createdAt = "2026-07-05"; :>> createdBy = "wweatherholtz"; :>> description = "Holistic#7 + GC-wording#6 (LOW, OPEN): loadSettings best-effort backfills but has no hook if the base map shape changes; the server Index has no version tag so any struct evolution forces CORRUPT→reindex. Also tighten the 'startup orphan GC' requirement wording to 'lazy first-access GC' (idle vaults GC on first open, not at boot). Related to the version handshake."; :>> discoveredInField = false; :>> relatedTask = "round5CompletenessFollowups"; :>> severity = Severity::Low; }
    part issueConflictCopyCosmetic : Issue { :>> id = "c0f1a5cc-9709-4a10-9b20-a1b2c3d49709"; :>> title = "Cosmetic conflict-copy edges: orphan copy if a streamed pull throws; tag can mismatch content on a racing save"; :>> createdAt = "2026-07-05"; :>> createdBy = "wweatherholtz"; :>> description = "Adversary#5 (cosmetic, OPEN): streamed conflictCopyIfRaced runs before streamFileToDisk, so if the stream then throws the conflict copy is orphaned (no overwrite); and the merge-fallback tags the copy name with the pre-fetch localHash, which no longer matches on a racing save. Neither loses data. Cleanup nicety."; :>> discoveredInField = false; :>> relatedTask = "round5CompletenessFollowups"; :>> severity = Severity::Low; }

    #Resolves dependency from round5CriticFixes to issueUnicodeCaseCollision;
    #Resolves dependency from round5CriticFixes to issueLegacyKeyUndeletable;
    #Resolves dependency from round5CriticFixes to issueDeleteRevokeRace;
    // Three of the round-5 completeness items SHIPPED in 0.10.26 → re-pointed to preReleaseHardening
    // (DONE). The remaining three (orchestration-untested — materially reduced by the FSM refactor +
    // the version/auth wiring tests but not fully covered; data-migration; conflict-copy-cosmetic)
    // stay open under round5CompletenessFollowups.
    #Resolves dependency from preReleaseHardening to issueVersionHandshake;
    #Resolves dependency from round5CompletenessFollowups to issueOrchestrationUntested;
    #Resolves dependency from preReleaseHardening to issueAdminReindex;
    #Resolves dependency from preReleaseHardening to issueCommitCas;
    #Resolves dependency from round5CompletenessFollowups to issueDataMigration;
    #Resolves dependency from round5CompletenessFollowups to issueConflictCopyCosmetic;

    // =====================================================================
    // FIELD DATA-LOSS ESCAPE (2026-07-06): the owner switched a populated vault onto a new build /
    // wrong server; the client reported "kept 2 local files" but then DELETED every local file.
    // Root cause + the test-coverage gap that let it ship, recorded per D0047 (a recurrable
    // correction MUST become a tracked Issue + a permanent guard — here the guard is the realistic
    // tombstone-modeling harness + a regression test that reproduces the exact sequence).
    // Both resolved by deleteLocalTombstoneGate (0.10.25).
    // =====================================================================
    part issueDeleteOnAbsence : Issue {
        :>> id = "c0f1a5cc-9801-4a10-9b20-a1b2c3d49801";
        :>> title = "delete-local fired on a file's ABSENCE from the remote, not a real tombstone — wrong/empty server silently wiped the vault";
        :>> createdAt = "2026-07-06";
        :>> createdBy = "wweatherholtz";
        :>> description = "CRITICAL field data-loss: reconcile.decide() returned delete-local whenever a file present locally with an unchanged base was ABSENT from the remote (L!=null, R==null, L==B). Pointing a populated vault at a WRONG / FRESH / RESTORED server (a server that legitimately lacks our files but has issued NO deletion tombstones for them) therefore read every local file as a remote deletion and removed it. The one-shot C2 empty-server guard did not survive across reconcile passes — the client's own pushes made the remote non-empty on the second pass, disarming it — so even the '(server said it kept 2 local files)' log was immediately undone by the next reconcile (v1->v13). Fix: deletion is now TOMBSTONE-AUTHORITATIVE — reconcileOne takes a hasTombstone(path) predicate (reconcileAll from resp.deletes, reconcilePath from manifest.deletes); on absence WITHOUT a tombstone the file is RESTORED (pushed back), and it is removed ONLY when the server genuinely tombstoned it. Absence is never proof of deletion.";
        :>> discoveredInField = true;
        :>> relatedTask = "deleteLocalTombstoneGate";
        :>> severity = Severity::High;
    }
    part issueDeleteTestGap : Issue {
        :>> id = "c0f1a5cc-9802-4a10-9b20-a1b2c3d49802";
        :>> title = "The reconcile test suite CODIFIED the absence-delete bug and never covered a vault switch onto a wrong/empty server";
        :>> createdAt = "2026-07-06";
        :>> createdBy = "wweatherholtz";
        :>> description = "The 181-test suite missed the data-loss because the fake server modeled deletion as mere ABSENCE (files.delete with no tombstone), so tests could not distinguish a real deletion from a file the server never had — and TWO tests actively asserted the buggy delete-on-absence as correct behavior. Coverage was happy-path (deletion propagation) + a single-pass empty-server guard; nothing exercised the two-pass 'switch to a wrong/empty/restored server' sequence that reproduces in the field. Fix (the permanent guard, D0047): the fake server now models tombstones (deletions[] with versions; changes() returns them), the two mis-asserting tests were rewritten to correct tombstone semantics, and a DATA-LOSS REGRESSION test reproduces the exact field sequence (Welcome.md + 'test file.md' survive two reconciles against a wrong/empty server). Also hardened the orchestration seam: main.ts injection seams + an obsidian stub let plugin-wiring.test.ts cover the wiring, and the e2e harness was repaired (ALLOW_WEAK_ADMIN + createVault for protocol-6).";
        :>> discoveredInField = true;
        :>> relatedTask = "deleteLocalTombstoneGate";
        :>> severity = Severity::High;
    }
    #Resolves dependency from deleteLocalTombstoneGate to issueDeleteOnAbsence;
    #Resolves dependency from deleteLocalTombstoneGate to issueDeleteTestGap;

    // =====================================================================
    // TIMING CRUTCHES (the AI-baked-in arbitrary-timing anti-pattern the owner flagged, 2026-07-06):
    // two places where behavior was gated on a fabricated time/count guess rather than on the actual
    // condition. Removed in 0.10.26 (preReleaseHardening) — recorded so the anti-pattern is tracked,
    // not just quietly fixed.
    // =====================================================================
    part issueTokenTtlCrutch : Issue {
        :>> id = "c0f1a5cc-9803-4a10-9b20-a1b2c3d49803";
        :>> title = "Token validity was guessed via a 30s 'recently-validated' TTL + a proactive probe, not driven by the server";
        :>> createdAt = "2026-07-06";
        :>> createdBy = "wweatherholtz";
        :>> description = "acquireToken probed listVaults to 'validate' the stored token and cached that result for a fabricated 30-second window, skipping re-probes within it. The TTL is a guess: a token can be revoked/expire the instant after a probe, so the cache neither guarantees validity nor is needed — it's the AI-timing anti-pattern (bake in a number to paper over not modeling the real condition). Fixed: the token is used OPTIMISTICALLY and validity is the server's actual answer — a real 401 triggers a single reactive re-login (withAuth wraps the account calls; doConnect retries status() once). No probe, no TTL.";
        :>> discoveredInField = false;
        :>> relatedTask = "preReleaseHardening";
        :>> severity = Severity::Low;
    }
    part issueConfigScanPollCrutch : Issue {
        :>> id = "c0f1a5cc-9804-4a10-9b20-a1b2c3d49804";
        :>> title = "The periodic config-aware reconcile fired every Nth POLL (a tick count), not on a wall-clock bound";
        :>> createdAt = "2026-07-06";
        :>> createdBy = "wweatherholtz";
        :>> description = "The config-scan safety-net reconcile was gated on CONFIG_SCAN_EVERY_POLLS=8 — a decrement-per-poll counter. Coupling a real latency requirement ('detect a config change within ~N seconds') to an arbitrary poll count is the timing anti-pattern: change the poll cadence and the actual detection latency silently changes. Fixed: gate on a CONFIG_SCAN_INTERVAL_MS wall-clock bound (Date.now() - lastConfigScanAt), which states the real requirement and is stable regardless of poll cadence.";
        :>> discoveredInField = false;
        :>> relatedTask = "preReleaseHardening";
        :>> severity = Severity::Low;
    }
    #Resolves dependency from preReleaseHardening to issueTokenTtlCrutch;
    #Resolves dependency from preReleaseHardening to issueConfigScanPollCrutch;

    // =====================================================================
    // ROUND 6 — a SIXTH fresh 3-lens critique (independent DI/security/concurrency critics) vs the
    // 0.10.26 code, 2026-07-07. Did NOT converge: 9 findings, mostly NEW interactions introduced by
    // the 0.10.24 FSM refactor + the 0.10.26 CAS/reactive-token work. 8 fixed + shipped 0.10.27
    // (#Resolves round6CriticFixes); 1 Low accepted (D0018). A tracked follow-up (historyRebase)
    // is the proper bound that replaces the removed tombstone cap.
    // =====================================================================
    part issueTombstoneResurrection : Issue { :>> id = "c0f1a5cc-9a01-4a10-9b20-a1b2c3d49a01"; :>> title = "Arbitrary tombstone cap (MAX_TOMBSTONES) resurrects deleted files under tombstone-authoritative delete"; :>> createdAt = "2026-07-07"; :>> createdBy = "wweatherholtz"; :>> description = "DI-R6#1 (HIGH): the server capped retained deletion tombstones at 10,000 on the pre-0.10.25 premise that 'a full reconcile infers deletion from absence' — a premise 0.10.25 INVERTED (absence -> restore, not delete). A long-offline client returning after >10k deletions finds the tombstone compacted away, reads the genuine deletion as 'server never had it', and RE-UPLOADS the file — resurrecting it fleet-wide (induced, user-perceived integrity violation, though not byte-loss). Two subsystems hardened in different rounds against opposite failure modes contradicted each other. Fixed 0.10.27: removed the arbitrary cap; tombstones are durable, so a genuine deletion is always distinguishable from a wrong/fresh server. The proper bound on growth is a deliberate history rebase (historyRebase), not an arbitrary count."; :>> discoveredInField = false; :>> relatedTask = "round6CriticFixes"; :>> severity = Severity::High; }
    part issueUnboundedTombstones : Issue { :>> id = "c0f1a5cc-9a02-4a10-9b20-a1b2c3d49a02"; :>> title = "Tombstones now grow unbounded until a history-rebase mechanism exists"; :>> createdAt = "2026-07-07"; :>> createdBy = "wweatherholtz"; :>> description = "Consequence of removing the MAX_TOMBSTONES cap (issueTombstoneResurrection): the deletions Vec now grows without an automatic bound. Accepted as the lesser evil (each tombstone is tiny — a path + a u64 — so realistic vaults are unaffected for a long time, and an arbitrary cap silently corrupted deletion semantics). The correct, non-arbitrary bound is a deliberate HISTORY REBASE: reset history to a floor version, expose that floor as a client horizon, and have a client whose cursor is below it do a PROMPTED reconcile instead of auto-restoring. The horizon (historyRebase, 0.10.31) is the correctness bound; the deliberate space-reclaiming PRUNE is tracked as tombstonePrune (open, deferred)."; :>> discoveredInField = false; :>> relatedTask = "tombstonePrune"; :>> severity = Severity::Low; }
    part issueCasEventOffline : Issue { :>> id = "c0f1a5cc-9a03-4a10-9b20-a1b2c3d49a03"; :>> title = "A CAS 409 on the single-path event reconcile flaps the engine offline (regression from 0.10.26 CAS)"; :>> createdAt = "2026-07-07"; :>> createdBy = "wweatherholtz"; :>> description = "CONC-R6#1 (HIGH): reconcileAll isolates a per-file CommitConflictError (skip -> merge next pass), but reconcilePath had no such guard, and the SyncEngine turns any thrown effect into failToOffline. So a routine same-file concurrent edit (the common desktop path) — which the 0.10.26 CAS work made 409 — dropped the client to offline + backoff, flapping on repeated edits. Fixed 0.10.27: reconcilePath isolates a CommitConflictError like reconcileAll (leave base unchanged -> next reconcile merges); any OTHER error still propagates -> offline."; :>> discoveredInField = false; :>> relatedTask = "round6CriticFixes"; :>> severity = Severity::High; }
    part issueOwnerDirectionRce : Issue { :>> id = "c0f1a5cc-9a04-4a10-9b20-a1b2c3d49a04"; :>> title = "SEC-3 gate's owner-direction hole: a readWrite peer's plugin code auto-executes on the vault owner"; :>> createdAt = "2026-07-07"; :>> createdBy = "wweatherholtz"; :>> description = "SEC-R6#1 (HIGH): the config-apply gate only suppressed auto-enable when vaultOwner was set (i.e. syncing a NON-owned vault). But a vault you OWN and share readWrite also holds an untrusted writer's content — a peer commits .obsidian/plugins/<id>/main.js and the owner's client auto-disables+enables the plugin, executing the peer's code (RCE, full Node access). The SEC-3 predicate was written too narrowly ('non-owned vault') vs the real one ('any vault with an untrusted writer'). Fixed 0.10.27: flushConfigReload never auto-enables synced plugin code for ANY vault — the user reloads manually. Refines STPA UCA-7 / SR-5."; :>> discoveredInField = false; :>> relatedTask = "round6CriticFixes"; :>> severity = Severity::High; }
    part issueCssInjection : Issue { :>> id = "c0f1a5cc-9a05-4a10-9b20-a1b2c3d49a05"; :>> title = "Synced theme/snippet CSS is auto-applied with no trust gate (injection via un-CSP'd renderer)"; :>> createdAt = "2026-07-07"; :>> createdBy = "wweatherholtz"; :>> description = "SEC-R6#2 (MED): unlike the plugin branch, the appearance/theme/snippet CSS branch of flushConfigReload had NO ownership guard at all — it unconditionally called customCss.loadData/loadSnippets for any vault. A peer/owner commits malicious CSS; Obsidian's un-CSP'd renderer allows url()/attribute-selector exfil + phishing overlays. Fixed 0.10.27: synced CSS is never auto-applied; the user reloads to apply."; :>> discoveredInField = false; :>> relatedTask = "round6CriticFixes"; :>> severity = Severity::Medium; }
    part issueReloginRace : Issue { :>> id = "c0f1a5cc-9a06-4a10-9b20-a1b2c3d49a06"; :>> title = "Concurrent re-login race clears the password mid-flight (spurious 'session expired' + orphan token)"; :>> createdAt = "2026-07-07"; :>> createdBy = "wweatherholtz"; :>> description = "CONC-R6#3 (MED): freshLogin READS the password (loginRemote) then destructively CLEARS it (token-only mode); the engine's reactive-401 path (doConnect) and the non-engine withAuth path (setup/switch modals) can both run it concurrently — a read-modify-write race across await with two entrants. The second reads an emptied password -> spurious 'session expired' prompt while a login is actually succeeding, minting an orphan token. Fixed 0.10.27: freshLogin is single-flight (concurrent calls coalesce into one login)."; :>> discoveredInField = false; :>> relatedTask = "round6CriticFixes"; :>> severity = Severity::Medium; }
    part issueFailToOfflineRecovery : Issue { :>> id = "c0f1a5cc-9a07-4a10-9b20-a1b2c3d49a07"; :>> title = "failToOffline leaves connected=true -> a WS redial + the backoff reconnect both run (two recovery paths)"; :>> createdAt = "2026-07-07"; :>> createdBy = "wweatherholtz"; :>> description = "CONC-R6#2 (MED): failToOffline set state=offline + scheduled a reconnect but did NOT clear `connected`, so a WS `close` firing in the offline window enqueued {rews}, passed the `if(!connected) return` guard, and re-dialed a socket while the backoff reconnect was also pending — the exact redial-vs-reconnect double-recovery the FSM was meant to make impossible. Fixed 0.10.27: failToOffline sets connected=false, so path/remote/rews are ignored until the single backoff {connect} recovers."; :>> discoveredInField = false; :>> relatedTask = "round6CriticFixes"; :>> severity = Severity::Medium; }
    part issueReindexCollision : Issue { :>> id = "c0f1a5cc-9a08-4a10-9b20-a1b2c3d49a08"; :>> title = "reindex bypasses the case/Unicode collision + safe_rel_path guards that commit enforces"; :>> createdAt = "2026-07-07"; :>> createdBy = "wweatherholtz"; :>> description = "DI-R6#3 (MED): the PROTO-4 case/fold collision guard + safe_rel_path run only on the commit path. reindex (the other way index entries are created) ingested colliding names straight off the Linux bind-mount, minting two index keys that a case-insensitive/Unicode-folding client FS collapses to one file -> overwrite + phantom-delete churn. Fixed 0.10.27: reindex runs the same conflicting_or_unsafe_rels check (unsafe or fold-colliding names abort the reindex with a clear message)."; :>> discoveredInField = false; :>> relatedTask = "round6CriticFixes"; :>> severity = Severity::Medium; }
    part issueWsRedialSpurious : Issue { :>> id = "c0f1a5cc-9a09-4a10-9b20-a1b2c3d49a09"; :>> title = "doConnect's intentional ws.close() enqueues a spurious {rews} (extra redial after each reconnect)"; :>> createdAt = "2026-07-07"; :>> createdBy = "wweatherholtz"; :>> description = "CONC-R6#4 (LOW): doConnect calls this.ws?.close() then awaits token acquisition; the close fires during the await while this.ws still references the old socket, so the close handler's only guard (this.ws !== ws) can't fire and it enqueues {rews} -> one extra WS teardown+redial after every reconnect over a live socket. Benign. Fixed 0.10.27: doConnect clears this.ws immediately after close()."; :>> discoveredInField = false; :>> relatedTask = "round6CriticFixes"; :>> severity = Severity::Low; }
    part issuePathSizeCoalesce : Issue { :>> id = "c0f1a5cc-9a0a-4a10-9b20-a1b2c3d49a0a"; :>> title = "path-event coalescing pins the first event's size, defeating the RAM/size gate at the boundary"; :>> createdAt = "2026-07-07"; :>> createdBy = "wweatherholtz"; :>> description = "CONC-R6#5 (LOW): the engine dedups queued {path} events by path only, keeping the STALE size; a file saved small then grown past the size gate before the queue drains is judged on the small size, so the pre-read RAM/size guard is bypassed (content stays correct via live re-read; only the OOM guard is defeated, a narrow mobile edge). Fixed 0.10.27: coalescing keeps the LARGER size."; :>> discoveredInField = false; :>> relatedTask = "round6CriticFixes"; :>> severity = Severity::Low; }
    part issueShareEnumeration : Issue { :>> id = "c0f1a5cc-9a0b-4a10-9b20-a1b2c3d49a0b"; :>> title = "Authenticated username-enumeration oracle via /api/admin/shares (400 'no such account' vs 200)"; :>> createdAt = "2026-07-07"; :>> createdBy = "wweatherholtz"; :>> description = "SEC-R6#3 (LOW, ACCEPTED): share_create returns a distinct 400 'no such account' vs 200 depending on whether the grantee exists, giving any authenticated user a present/absent oracle to enumerate accounts (the same oracle class de-oracled on /register). ACCEPT-RISK (decided in Round 6, not fixed): authenticated-only, the side effect is confined to the attacker's own vault, and a clear 'no such account' error is materially better UX for the legitimate typo case; a uniform error would degrade the common path for a low-value oracle on a self-hosted server. Revisit if registration ever becomes fully open + adversarial."; :>> discoveredInField = false; :>> relatedTask = "round6CriticFixes"; :>> severity = Severity::Low; }

    #Resolves dependency from round6CriticFixes to issueTombstoneResurrection;
    #Resolves dependency from tombstonePrune to issueUnboundedTombstones;
    #Resolves dependency from round6CriticFixes to issueCasEventOffline;
    #Resolves dependency from round6CriticFixes to issueOwnerDirectionRce;
    #Resolves dependency from round6CriticFixes to issueCssInjection;
    #Resolves dependency from round6CriticFixes to issueReloginRace;
    #Resolves dependency from round6CriticFixes to issueFailToOfflineRecovery;
    #Resolves dependency from round6CriticFixes to issueReindexCollision;
    #Resolves dependency from round6CriticFixes to issueWsRedialSpurious;
    #Resolves dependency from round6CriticFixes to issuePathSizeCoalesce;
    // issueShareEnumeration was ACCEPTED (not fixed) as Round-6's disposition for that finding —
    // round6CriticFixes accounts for it (its DoD records the accept-risk); the rationale lives in
    // the issue's own description (a mooting Decision would have to reference this tracking package,
    // which keel's .engine-before-.tracking parse order disallows).
    #Resolves dependency from round6CriticFixes to issueShareEnumeration;

    // =====================================================================
    // ROUND 7 — recovery/operability + resource/scale critique (independent critics) vs 0.10.28,
    // 2026-07-07. Recovery bugs RC-2/3/4 fixed + shipped 0.10.28 (round7RecoveryFixes); RC-1 folds
    // into historyRebase; the resource/scale set (RS-1..7) is tracked under scaleHardening — the
    // scale-agnostic resolution is the storage-engine decision (SQLite recommended, pending).
    // =====================================================================
    part issueCorruptReindexResurrection : Issue { :>> id = "c0f1a5cc-9b01-4a10-9b20-a1b2c3d49b01"; :>> title = "Corrupt-index reindex drops ALL tombstones, resurrecting deleted files (recovery path induces loss)"; :>> createdAt = "2026-07-07"; :>> createdBy = "wweatherholtz"; :>> description = "RC-R7#1 (HIGH): a parse-corrupt index opens as Index::default() (empty deletions); reindex rebuilds files from disk but never restores tombstones (they existed only in the now-unparseable index), so changes(0) reports zero deletes and a long-offline client reads its since-deleted files as absence-without-tombstone -> RESTORES them (induced, user-perceived resurrection). The documented repair itself induces the resurrection Round 6 fixed for the cap case. Tombstones can't be reconstructed from disk, so the correct fix is the horizon + prompted-reconcile: a corrupt reindex IS a history reset. Folded into historyRebase."; :>> discoveredInField = false; :>> relatedTask = "historyRebase"; :>> severity = Severity::High; }
    part issueReindexBrick : Issue { :>> id = "c0f1a5cc-9b02-4a10-9b20-a1b2c3d49b02"; :>> title = "reindex aborts wholesale on one unrecoverable file -> permanent vault brick, shell-only escape"; :>> createdAt = "2026-07-07"; :>> createdBy = "wweatherholtz"; :>> description = "RC-R7#2 (HIGH): the DI-4 'refuse to drop indexed-but-missing files' guard becomes a brick when a file is genuinely gone (mirror-write failed AND chunk lost) — every reindex (owner or admin) aborts, the vault stays ERROR forever, escapable only by hand-deleting files in a shell. Fixed 0.10.28: reindex RECOVERS a missing-from-disk file from the authoritative chunk store where its chunks survive (the common failed-mirror case, no data loss); only truly-lost files abort, and an admin force drops them so the rest is repaired."; :>> discoveredInField = false; :>> relatedTask = "round7RecoveryFixes"; :>> severity = Severity::High; }
    part issueVaultGone404 : Issue { :>> id = "c0f1a5cc-9b03-4a10-9b20-a1b2c3d49b03"; :>> title = "A deleted/missing server vault shows as 'Can't reach the server — retrying' forever"; :>> createdAt = "2026-07-07"; :>> createdBy = "wweatherholtz"; :>> description = "RC-R7#3 (MED): doConnect distinguishes 401/version/not-ready but not 404 (vault-not-found), so a deleted/renamed server-side vault collapses into the catch-all connectivity message + indefinite backoff — the server IS reachable, the vault is gone, but the signal says the opposite. Fixed 0.10.28: a 404 surfaces 'this vault no longer exists — re-create or switch (local files untouched)'."; :>> discoveredInField = false; :>> relatedTask = "round7RecoveryFixes"; :>> severity = Severity::Medium; }
    part issueNoPerVaultDelete : Issue { :>> id = "c0f1a5cc-9b04-4a10-9b20-a1b2c3d49b04"; :>> title = "Operator toolkit gap: no per-vault delete (only whole-account) and no forced repair"; :>> createdAt = "2026-07-07"; :>> createdBy = "wweatherholtz"; :>> description = "RC-R7#4 (MED): the admin surface could create/reindex/share but not delete a single vault (only whole-account users_delete) nor force a repair past an unrecoverable file. Fixed 0.10.28: DELETE /api/admin/vault + admin-UI button (per-vault delete) and the forced reindex (RC-2). Residual (tracked): a UI to reset a latched client-side bulk-delete guard."; :>> discoveredInField = false; :>> relatedTask = "round7RecoveryFixes"; :>> severity = Severity::Medium; }
    part issueBasePersistConflict : Issue { :>> id = "c0f1a5cc-9b05-4a10-9b20-a1b2c3d49b05"; :>> title = "Client base-persist failure (full disk) -> stale base on reload -> spurious conflict copies"; :>> createdAt = "2026-07-07"; :>> createdBy = "wweatherholtz"; :>> description = "RC-R7#5 (LOW): persist() swallows a saveData error with a warning; the in-memory base advanced but data.json didn't, so a reload restores a stale base and files whose base was lost conflict-copy instead of merging cleanly (no data loss — the safe direction — but spurious copies + no clear cause). Tracked with the base-size/persistence robustness work (RS-4 area)."; :>> discoveredInField = false; :>> relatedTask = "scaleHardening"; :>> severity = Severity::Low; }
    part issueHandleNoEviction : Issue { :>> id = "c0f1a5cc-9b06-4a10-9b20-a1b2c3d49b06"; :>> title = "RS-1: VaultHandle map is never evicted — every vault ever opened stays fully resident in RAM"; :>> createdAt = "2026-07-07"; :>> createdBy = "wweatherholtz"; :>> description = "RS-R7#1 (scale): the ns map is only inserted-to (removed only on account delete) — no LRU/idle eviction, so a multi-vault server pins every touched vault's whole Index in RAM for process life (~40-60 MB per 100k-file vault). Storage-independent; needs idle-handle eviction. Tracked under scaleHardening."; :>> discoveredInField = false; :>> relatedTask = "scaleHardening"; :>> severity = Severity::Medium; }
    part issueIndexClonePerWrite : Issue { :>> id = "c0f1a5cc-9b07-4a10-9b20-a1b2c3d49b07"; :>> title = "RS-2: every commit/delete deep-clones the ENTIRE index for rollback (O(vault) per write)"; :>> createdAt = "2026-07-07"; :>> createdBy = "wweatherholtz"; :>> description = "RS-R7#2 (scale): commit/delete take `self.idx.clone()` (full deep copy of files+deletions+chunk_refs) purely for journal-failure rollback, so per-write cost grows with vault size — large vaults get slower to write regardless of change size. Mooted by the SQLite storage decision (row-level writes, no whole-index clone); until then, a targeted rollback would fix it. Tracked under scaleHardening."; :>> discoveredInField = false; :>> relatedTask = "scaleHardening"; :>> severity = Severity::Medium; }
    part issueFullReconcileOnRemote : Issue { :>> id = "c0f1a5cc-9b08-4a10-9b20-a1b2c3d49b08"; :>> title = "RS-3: reconcileAll re-pulls the whole manifest AND re-hashes the whole local vault on ANY remote change"; :>> createdAt = "2026-07-07"; :>> createdBy = "wweatherholtz"; :>> description = "RS-R7#3 (scale, mobile even at modest size): doReconcileAll fetches the incremental changes(since) then DISCARDS it and runs reconcileAll (changes(0) + full path-union rehash), so one remote edit re-hashes the entire local vault — seconds-to-minutes of CPU + battery on a large vault on a phone. Storage-independent: reconcile only the delta's paths on a remote poke; full pass only on the periodic config scan / version rewind. Tracked under scaleHardening (first to pull forward)."; :>> discoveredInField = false; :>> relatedTask = "scaleHardening"; :>> severity = Severity::Medium; }
    part issueBaseFullText : Issue { :>> id = "c0f1a5cc-9b09-4a10-9b20-a1b2c3d49b09"; :>> title = "RS-4: client base keeps the full TEXT of every mergeable file, re-serialized to data.json on every base change"; :>> createdAt = "2026-07-07"; :>> createdBy = "wweatherholtz"; :>> description = "RS-R7#4 (scale, mobile): setBase stores {hash,text} for every mergeable file, so base is a second full copy of all note text in RAM, and persist() stringifies the whole map on every base change -> a data.json the size of the vault, rewritten repeatedly. Storage-independent: cap per-file base text (large text -> hash-only, losing clean merge for those). Tracked under scaleHardening."; :>> discoveredInField = false; :>> relatedTask = "scaleHardening"; :>> severity = Severity::Medium; }
    part issueLinearChangesScan : Issue { :>> id = "c0f1a5cc-9b0a-4a10-9b20-a1b2c3d49b0a"; :>> title = "RS-5: changes(since) is an O(all files + all tombstones) linear scan run by every device every 4s"; :>> createdAt = "2026-07-07"; :>> createdBy = "wweatherholtz"; :>> description = "RS-R7#5 (scale): changes filters both collections by linear scan (no version index); every 4s idle poll from N devices is N x O(files+tombstones) for zero results, and the (now-durable, growing) tombstones make each poll ever more expensive. Mooted by SQLite (indexed WHERE version > ?). Tracked under scaleHardening."; :>> discoveredInField = false; :>> relatedTask = "scaleHardening"; :>> severity = Severity::Medium; }
    part issueFullSnapshotCost : Issue { :>> id = "c0f1a5cc-9b0b-4a10-9b20-a1b2c3d49b0b"; :>> title = "RS-6: snapshot re-serializes the whole index to one in-RAM JSON blob every 500 mutations"; :>> createdAt = "2026-07-07"; :>> createdBy = "wweatherholtz"; :>> description = "RS-R7#6 (scale): journal compaction serde_json::to_vec's the entire index (~50-100 MB for 100k files) under the write lock every 500 commits, stalling writers, and grows unbounded with tombstones. Mooted by SQLite (no full snapshot). Tracked under scaleHardening."; :>> discoveredInField = false; :>> relatedTask = "scaleHardening"; :>> severity = Severity::Low; }
    part issueColdOpenCost : Issue { :>> id = "c0f1a5cc-9b0c-4a10-9b20-a1b2c3d49b0c"; :>> title = "RS-7: cold-open does full deserialize + journal replay + chunk_refs recompute + list every blob"; :>> createdAt = "2026-07-07"; :>> createdBy = "wweatherholtz"; :>> description = "RS-R7#7 (scale): first access to a large vault deserializes the whole index, replays the journal, recomputes chunk_refs, and list_hashes() walks every blob dir (millions on a churny vault) — a multi-second-to-minutes stall. Amortized (lazy/rare), hence Low. Mooted by SQLite (no full deserialize; indexed integrity). Tracked under scaleHardening."; :>> discoveredInField = false; :>> relatedTask = "scaleHardening"; :>> severity = Severity::Low; }

    #Resolves dependency from historyRebase to issueCorruptReindexResurrection;
    #Resolves dependency from round7RecoveryFixes to issueReindexBrick;
    #Resolves dependency from round7RecoveryFixes to issueVaultGone404;
    #Resolves dependency from round7RecoveryFixes to issueNoPerVaultDelete;
    #Resolves dependency from scaleHardening to issueBasePersistConflict;
    // Storage-INDEPENDENT scale fixes — RS-1/3/4 now DONE; only RS-5 base-persist remains open.
    #Resolves dependency from resourceScaleFixes to issueHandleNoEviction;         // RS-1 (DONE 0.10.30)
    #Resolves dependency from incrementalReconcile to issueFullReconcileOnRemote;  // RS-3 (DONE 0.10.29)
    #Resolves dependency from resourceScaleFixes to issueBaseFullText;             // RS-4 (DONE 0.10.30)
    // Storage-FORMAT-dependent findings are resolved BY the SQLite migration (D0018) — SQLite's
    // row writes / indexed queries / WAL moot them; patching the JSON index for these was throwaway.
    #Resolves dependency from sqliteMigration to issueIndexClonePerWrite;  // RS-2
    #Resolves dependency from sqliteMigration to issueLinearChangesScan;   // RS-5
    #Resolves dependency from sqliteMigration to issueFullSnapshotCost;    // RS-6
    #Resolves dependency from sqliteMigration to issueColdOpenCost;        // RS-7

    // Critique R8 (4-lens) residual — the two MED concurrency findings NOT fixed in the R8 batch
    // (0.10.35). The HIGH/MED findings that WERE fixed are enumerated + resolved in critiqueR8FixesDoD.
    part issueDoubleOpenRace : Issue { :>> id = "c0f1a5cc-9c01-4a10-9b20-a1b2c3d49c01"; :>> title = "Concurrent first-access to a cold corrupt vault can leave the cached handle stuck corrupt (SQLITE_BUSY)"; :>> createdAt = "2026-07-08"; :>> createdBy = "wweatherholtz"; :>> description = "Conc-R8 M1 (MED): state.vault() releases the ns-map lock across Vault::open, so two concurrent first-accesses to the same cold, corrupt (user,vault) both run reindex on separate SQLite connections. SQLite serializes writers → one hits SQLITE_BUSY, its reindex errors, and that Vault stays corrupt=true; if it wins the or_insert race it's the CACHED handle → every sync op 503s until a manual reindex, though the DB is fine. Fix: a per-(user,vault) open/reindex lock so only one thread opens. Low real-world likelihood (needs simultaneous cold first-access to the same corrupt vault)."; :>> discoveredInField = false; :>> relatedTask = "serverConcurrencyResidual"; :>> severity = Severity::Medium; }
    part issueChangesOnAsyncWorker : Issue { :>> id = "c0f1a5cc-9c02-4a10-9b20-a1b2c3d49c02"; :>> title = "Full-manifest changes(since=0) scans SQLite under the read lock on the async worker"; :>> createdAt = "2026-07-08"; :>> createdBy = "wweatherholtz"; :>> description = "Conc-R8 M2 (MED): the changes handler holds rlock(vault) and runs SqliteIndex::changes on the async worker; for since=0 (first sync / full reconcile) that's a whole-files-table scan blocking a runtime worker for its duration (the write ops correctly use spawn_blocking; this read path does not). No deadlock (no await under the guard). Fix: offload the full-manifest read to the blocking pool. Lower-impact cousin of the now-fixed cold-open-on-worker (Conc-H1)."; :>> discoveredInField = false; :>> relatedTask = "serverConcurrencyResidual"; :>> severity = Severity::Medium; }
    #Resolves dependency from serverConcurrencyResidual to issueDoubleOpenRace;
    #Resolves dependency from serverConcurrencyResidual to issueChangesOnAsyncWorker;

    // ---- CMMC / NIST SP 800-171 rev2 POA&M: the 5 code-addressable compliance gaps surfaced by
    // modeling the 110 controls (see .tracking/compliance/nist-800-171.sysml + docs/cmmc-posture.md).
    // Triaged (accounted-for) via the open cmmcComplianceBacklog action; honestly OPEN (planned work /
    // operator decision), not resolved. ----
    part issueCmmcMfa : Issue { :>> id = "c0f1a5cc-a001-4a10-9b20-a1b2c3d4a001"; :>> title = "3.5.3: No multifactor authentication (IA)"; :>> createdAt = "2026-07-10"; :>> createdBy = "wweatherholtz"; :>> description = "No multifactor authentication (IA.3.5.3). RESOLVED: TOTP (RFC 6238) second factor + single-use recovery codes for privileged (server-admin) accounts — self-enrolled via /admin, verified at login. Self-contained crypto (totp.rs, no new deps) pinned to RFC 4231/6238 test vectors. Real tests: totp.rs totp_rfc6238_vectors + hmac_sha1_rfc4231; admin.rs mfa_totp_full_lifecycle. Non-privileged (plugin) MFA is a follow-up."; :>> discoveredInField = false; :>> relatedTask = "cmmcMfa"; :>> severity = Severity::Medium; }
    part issueCmmcPwReuse : Issue { :>> id = "c0f1a5cc-a002-4a10-9b20-a1b2c3d4a002"; :>> title = "3.5.8: No password-reuse history (IA)"; :>> createdAt = "2026-07-10"; :>> createdBy = "wweatherholtz"; :>> description = "No password-reuse history (IA.3.5.8). RESOLVED: users.rs retains the last 5 argon2 hashes and change_password rejects reuse of the current or any recent password. Real tests: users.rs reuse_history_rejects_current_and_recent_passwords + admin.rs password_change_rejects_reuse_of_a_recent_password."; :>> discoveredInField = false; :>> relatedTask = "cmmcForcedChangeReuse"; :>> severity = Severity::Medium; }
    part issueCmmcForcedChange : Issue { :>> id = "c0f1a5cc-a003-4a10-9b20-a1b2c3d4a003"; :>> title = "3.5.9: No forced-change-on-reset (IA)"; :>> createdAt = "2026-07-10"; :>> createdBy = "wweatherholtz"; :>> description = "No forced-change-on-reset (IA.3.5.9). RESOLVED: admin create/reset flags must_change; the AuthToken extractor blocks every route but change-password/logout until the account sets a new password. Real tests: admin.rs admin_created_account_is_forced_to_change_password_before_use + users.rs must_change_flag_set_clear_and_cleared_on_remove."; :>> discoveredInField = false; :>> relatedTask = "cmmcForcedChangeReuse"; :>> severity = Severity::Medium; }
    part issueCmmcFips : Issue { :>> id = "c0f1a5cc-a004-4a10-9b20-a1b2c3d4a004"; :>> title = "3.13.11: Crypto is not FIPS-validated (SC)"; :>> createdAt = "2026-07-10"; :>> createdBy = "wweatherholtz"; :>> description = "Crypto is not FIPS-validated (SC.3.13.11). Decision: FIPS provider if genuine CUI is stored."; :>> discoveredInField = false; :>> relatedTask = "cmmcComplianceBacklog"; :>> severity = Severity::Medium; }
    part issueCmmcAtRest : Issue { :>> id = "c0f1a5cc-a005-4a10-9b20-a1b2c3d4a005"; :>> title = "3.13.16: CUI at rest is plaintext (SC)"; :>> createdAt = "2026-07-10"; :>> createdBy = "wweatherholtz"; :>> description = "CUI at rest is plaintext (SC.3.13.16). Near-term: operator volume encryption; E2EE deferred."; :>> discoveredInField = false; :>> relatedTask = "cmmcComplianceBacklog"; :>> severity = Severity::Medium; }
    #Resolves dependency from cmmcMfa to issueCmmcMfa;                        // DONE (real-tested)
    #Resolves dependency from cmmcForcedChangeReuse to issueCmmcPwReuse;      // DONE (real-tested)
    #Resolves dependency from cmmcForcedChangeReuse to issueCmmcForcedChange; // DONE (real-tested)
    // Mooted by D0027 (no CUI → these two CUI-DATA-specific controls are Not Applicable), NOT by an
    // implementation action. Re-homed off cmmcComplianceBacklog onto the mooting Decision (D0077).
    #Resolves dependency from d0027 to issueCmmcFips;
    #Resolves dependency from d0027 to issueCmmcAtRest;

    // ---- UI functional-correctness audit (2026-07): 9 wiring defects found by tracing every control in
    // BOTH UIs end-to-end. All RESOLVED by the DONE, real-tested uiFunctionalAudit action. ----
    part issueUiSignoutNoRevoke : Issue { :>> id = "c0f1a5cc-b001-4a10-9b20-a1b2c3d4b001"; :>> title = "Admin A1: Sign out doesn't revoke the server session"; :>> createdAt = "2026-07-10"; :>> createdBy = "wweatherholtz"; :>> description = "Admin page 'Sign out' cleared only local sessionStorage; it never called POST /api/logout, so the bearer token stayed valid for its 30-day TTL. RESOLVED: signOut() now revokes server-side (best-effort). Class: discarded control effect."; :>> discoveredInField = false; :>> relatedTask = "uiFunctionalAudit"; :>> severity = Severity::High; }
    part issueUiMfaStaleIndicator : Issue { :>> id = "c0f1a5cc-b002-4a10-9b20-a1b2c3d4b002"; :>> title = "Admin A2: MFA panel shows 'disabled' after a successful enable"; :>> createdAt = "2026-07-10"; :>> createdBy = "wweatherholtz"; :>> description = "MFA confirm succeeded but never re-read status, so the panel kept the enroll/disabled view while the server was enabled. RESOLVED: confirm re-reads status (renderMfa) while preserving the one-time recovery codes. Class: dual-truth/stale indicator."; :>> discoveredInField = false; :>> relatedTask = "uiFunctionalAudit"; :>> severity = Severity::Medium; }
    part issueUiMustChangeDeadEnd : Issue { :>> id = "c0f1a5cc-b003-4a10-9b20-a1b2c3d4b003"; :>> title = "Admin A3: forced-change accounts bounce at login with no way in"; :>> createdAt = "2026-07-10"; :>> createdBy = "wweatherholtz"; :>> description = "Login ignored must_change_password; an admin-created/reset account stored a token, then /api/admin/me 403'd and the UI silently returned to login with no message and no change-password control. RESOLVED: a forced-change screen (POST /api/password). Class: dead-end dialog path."; :>> discoveredInField = false; :>> relatedTask = "uiFunctionalAudit"; :>> severity = Severity::High; }
    part issueUiOwnerVaultStale : Issue { :>> id = "c0f1a5cc-b004-4a10-9b20-a1b2c3d4b004"; :>> title = "Admin A4: owner-vault sub-row not reconciled after Repair/Delete"; :>> createdAt = "2026-07-10"; :>> createdBy = "wweatherholtz"; :>> description = "In the account→Vaults sub-row, Repair/Delete only set a message; the row wasn't re-fetched, so a deleted vault lingered and a repaired vault's health chip stayed stale. RESOLVED: the sub-row re-fetches + re-renders after each action. Class: stale indicator."; :>> discoveredInField = false; :>> relatedTask = "uiFunctionalAudit"; :>> severity = Severity::Medium; }
    part issueUiRepairMissing : Issue { :>> id = "c0f1a5cc-b005-4a10-9b20-a1b2c3d4b005"; :>> title = "Admin A5: Repair offered on a 'missing' vault where the endpoint 404s"; :>> createdAt = "2026-07-10"; :>> createdBy = "wweatherholtz"; :>> description = "The health chip called a 'missing' vault 'no data yet' but a Repair button was still shown; clicking it 404'd (reindex requires an existing vault). RESOLVED: Repair is gated to genuinely-degraded vaults in both panels. Class: dual-truth (chip vs action)."; :>> discoveredInField = false; :>> relatedTask = "uiFunctionalAudit"; :>> severity = Severity::Medium; }
    part issueUiWizardPassword : Issue { :>> id = "c0f1a5cc-b006-4a10-9b20-a1b2c3d4b006"; :>> title = "Plugin P1: setup wizard persists the plaintext password in token-only mode"; :>> createdAt = "2026-07-10"; :>> createdBy = "wweatherholtz"; :>> description = "finish() wrote st.password unconditionally AND set authToken, so freshLogin (the only place that clears the password when !storePassword) never ran — the plaintext password lingered in data.json against the token-only-at-rest default. RESOLVED: wizardCredentials() (pure, unit-tested) only persists it when storePassword. Class: security side-effect."; :>> discoveredInField = false; :>> relatedTask = "uiFunctionalAudit"; :>> severity = Severity::High; }
    part issueUiConfigToggleLatency : Issue { :>> id = "c0f1a5cc-b007-4a10-9b20-a1b2c3d4b007"; :>> title = "Plugin P2: config-sync toggles look inert (apply only on the ~2-min tick)"; :>> createdAt = "2026-07-10"; :>> createdBy = "wweatherholtz"; :>> description = "Config-sync master/category/plugin toggles only persisted + re-rendered; they took effect only on the next periodic config scan (up to CONFIG_SCAN_INTERVAL_MS ~2 min), so flipping one appeared to do nothing. RESOLVED: applyConfigSyncChange() forces a config scan and kicks a reconcile immediately. Class: switch appears inert."; :>> discoveredInField = false; :>> relatedTask = "uiFunctionalAudit"; :>> severity = Severity::Medium; }
    part issueUiLastSyncedPersist : Issue { :>> id = "c0f1a5cc-b008-4a10-9b20-a1b2c3d4b008"; :>> title = "Plugin P3: lastSyncedAt on the poll path not persisted"; :>> createdAt = "2026-07-10"; :>> createdBy = "wweatherholtz"; :>> description = "The poll path set settings.lastSyncedAt without saveSettings (the persist snapshot ran earlier in the pass), so 'Last synced' could lag after a restart. RESOLVED: explicit saveSettings on the poll path. Class: minor stale."; :>> discoveredInField = false; :>> relatedTask = "uiFunctionalAudit"; :>> severity = Severity::Low; }
    part issueUiLightVsWs : Issue { :>> id = "c0f1a5cc-b009-4a10-9b20-a1b2c3d4b009"; :>> title = "Plugin P4: status light shows green 'Fully synced' while the WebSocket is closed"; :>> createdAt = "2026-07-10"; :>> createdBy = "wweatherholtz"; :>> description = "The light was a pure projection of the reconcile FSM phase and never read ws.readyState; on a WS drop with polling still succeeding it stayed green 'Fully synced' though realtime was down. RESOLVED: a realtimeConnected flag threads into light() — idle-without-realtime is no longer green and says it's polling. Class: dual-truth (status vs transport)."; :>> discoveredInField = false; :>> relatedTask = "uiFunctionalAudit"; :>> severity = Severity::Medium; }
    #Resolves dependency from uiFunctionalAudit to issueUiSignoutNoRevoke;
    #Resolves dependency from uiFunctionalAudit to issueUiMfaStaleIndicator;
    #Resolves dependency from uiFunctionalAudit to issueUiMustChangeDeadEnd;
    #Resolves dependency from uiFunctionalAudit to issueUiOwnerVaultStale;
    #Resolves dependency from uiFunctionalAudit to issueUiRepairMissing;
    #Resolves dependency from uiFunctionalAudit to issueUiWizardPassword;
    #Resolves dependency from uiFunctionalAudit to issueUiConfigToggleLatency;
    #Resolves dependency from uiFunctionalAudit to issueUiLastSyncedPersist;
    #Resolves dependency from uiFunctionalAudit to issueUiLightVsWs;

    // ---- Standard critique round (2026-07, 3 lenses: data-integrity + security + sync). 6 FIXED +
    // real-tested (critRoundStd); the 4 residuals were since closed one by one - 2 fixed (critResidualEasy,
    // critResidual2), 2 accepted-risk by the owner (acceptOpenEnumRisk, acceptMobileFsyncRisk). The placeholder
    // action critRoundResidual was removed 2026-09-07: it resolved nothing and had no DoD, so it sat in the
    // ready list as a phantom. ----
    part issueCritDeltaGuard : Issue { :>> id = "c0f1a5cc-c001-4a10-9b20-a1b2c3d4c001"; :>> title = "reconcileDelta doesn't supply locallyPresent → C1 guard inert on the poll-delta path"; :>> createdAt = "2026-07-10"; :>> createdBy = "wweatherholtz"; :>> description = "KEYSTONE (found independently by the data-integrity AND sync critics, same reconcile.ts:396 citation): the incremental delta path called reconcileOne without locallyPresent, so the C1 'present-but-unreadable != deleted' guard was dead there. A momentarily-unreadable file (AV lock / unhydrated cloud placeholder) during a poll delta could be mis-decided as an unguarded delete-remote (wiping a fully-synced note fleet-wide) or cleared-then-resurrected. RESOLVED: reconcileDelta probes io.exists (defaulting to present) and passes locallyPresent, so the guard fires (skip + retry). Class: silent divergence / data loss."; :>> discoveredInField = false; :>> relatedTask = "critRoundStd"; :>> severity = Severity::High; }
    part issueCritCommitDoS : Issue { :>> id = "c0f1a5cc-c002-4a10-9b20-a1b2c3d4c002"; :>> title = "Authenticated memory-amplification DoS via concurrent large commits"; :>> createdAt = "2026-07-10"; :>> createdBy = "wweatherholtz"; :>> description = "A single commit is bounded to req.size <= MAX_FILE_BYTES (512 MiB), but a client owning up to 100 vaults could fire many ~512 MiB reassemblies concurrently (each transient) and OOM a modest box. RESOLVED: large commits (req.size > 16 MiB) acquire a small global permit pool (MAX_CONCURRENT_LARGE_COMMITS=4) with a 30s bounded wait (503 on shed); small note commits are unthrottled — aggregate large-reassembly RAM is bounded. Class: availability."; :>> discoveredInField = false; :>> relatedTask = "critRoundStd"; :>> severity = Severity::High; }
    part issueCritRestoreCas : Issue { :>> id = "c0f1a5cc-c003-4a10-9b20-a1b2c3d4c003"; :>> title = "delete-local restore push had no CAS → lost update"; :>> createdAt = "2026-07-10"; :>> createdBy = "wweatherholtz"; :>> description = "The tombstone-authoritative 'restore, never destroy' branch pushed with no expectedVersion, so a peer that created the path between this device's manifest read and the restore commit was silently overwritten. RESOLVED: the restore commits with expectedVersion 0 ('expected absent') → a concurrent create 409s → next reconcile merges. Class: recoverable-but-wrong."; :>> discoveredInField = false; :>> relatedTask = "critRoundStd"; :>> severity = Severity::Medium; }
    part issueCritDownloadSwitch : Issue { :>> id = "c0f1a5cc-c004-4a10-9b20-a1b2c3d4c004"; :>> title = "'download' vault-switch bypassed the bulk-delete guard"; :>> createdAt = "2026-07-10"; :>> createdBy = "wweatherholtz"; :>> description = "switchTo('download') removed every accepted local file absent from the target manifest with no ratio guard; a target reindexed over a PARTIAL directory reports status:ready while missing files, so mirroring it mass-deleted legitimate local-only notes (recoverable via .trash). RESOLVED: the same BULK_DELETE ratio guard reconcileAll uses now gates the download-mode removal — a suspiciously-incomplete manifest keeps local files (surfaced via onGuard); a genuine populated target still mirrors. Class: recoverable-but-wrong."; :>> discoveredInField = false; :>> relatedTask = "critRoundStd"; :>> severity = Severity::Medium; }
    part issueCritWsMustChange : Issue { :>> id = "c0f1a5cc-c005-4a10-9b20-a1b2c3d4c005"; :>> title = "must_change gate not enforced on the WebSocket path"; :>> createdAt = "2026-07-10"; :>> createdBy = "wweatherholtz"; :>> description = "The AuthToken extractor blocks a forced-change account on all HTTP routes, but ws_handler resolved the token manually and skipped the check, so a locked account could still open change-notification subscriptions (metadata only, ACL-gated). RESOLVED: ws_handler now rejects a must_change account with 403, mirroring the extractor. Class: authz gate gap."; :>> discoveredInField = false; :>> relatedTask = "critRoundStd"; :>> severity = Severity::Medium; }
    part issueCritRealtimeStale : Issue { :>> id = "c0f1a5cc-c006-4a10-9b20-a1b2c3d4c006"; :>> title = "realtimeConnected stale-true after a non-network reconcile failure"; :>> createdAt = "2026-07-10"; :>> createdBy = "wweatherholtz"; :>> description = "On a non-socket failure the close handler's superseded-socket early-return left realtimeConnected true, so the status light briefly showed green 'Fully synced' during connect->idle before the new socket opened. RESOLVED: doConnect resets realtimeConnected=false up front. Class: cosmetic/stale indicator."; :>> discoveredInField = false; :>> relatedTask = "critRoundStd"; :>> severity = Severity::Low; }
    part issueCritOpenEnum : Issue { :>> id = "c0f1a5cc-c007-4a10-9b20-a1b2c3d4c007"; :>> title = "Open-registration mode leaks username existence (enumeration)"; :>> createdAt = "2026-07-10"; :>> createdBy = "wweatherholtz"; :>> description = "In open-registration mode /api/register returns 409 for a taken username vs 200 for a free one. ACCEPTED/DEFERRED: open mode lets anyone create accounts, so existence is inherently low-value, and de-oracling it harms the UX (a user must be told a name is taken to pick another). Documented as an open-mode property; the closed-mode path is already de-oracled. Class: info leak (accepted tradeoff)."; :>> discoveredInField = false; :>> relatedTask = "critRoundResidual"; :>> severity = Severity::Low; }
    part issueCritTotpReplay : Issue { :>> id = "c0f1a5cc-c008-4a10-9b20-a1b2c3d4c008"; :>> title = "TOTP codes replayable within their ~90s window (no last-step tracking)"; :>> createdAt = "2026-07-10"; :>> createdBy = "wweatherholtz"; :>> description = "totp::verify accepted step +/-1 with no last-consumed step recorded, so a captured code was replayable for the rest of its window. RESOLVED: users.rs now records the last consumed 30s step per user (totp_last_step); totp_verify_second_factor rejects a code whose step <= the last (RFC 6238 s5.2). Test: totp_code_cannot_be_replayed_within_its_window. Class: hardening."; :>> discoveredInField = false; :>> relatedTask = "critResidualEasy"; :>> severity = Severity::Low; }
    part issueCritWsLiveness : Issue { :>> id = "c0f1a5cc-c009-4a10-9b20-a1b2c3d4c009"; :>> title = "No client-side WebSocket liveness check (half-open socket stalls realtime)"; :>> createdAt = "2026-07-10"; :>> createdBy = "wweatherholtz"; :>> description = "The client treated the WS as healthy until the browser fired close; a half-open socket (radio sleep / NAT rebind) kept realtimeConnected true with the poll downshifted, so the light showed green over a dead channel. RESOLVED: the server sends an application heartbeat every ~30s (ws.rs) that the client CAN see (browsers hide protocol ping/pong from JS), and the client runs a liveness timer (isWsStale) that drops realtime health + upshifts the poll + re-dials if no frame arrives within WS_STALE_MS (~75s). Test: syncstate.test isWsStale. Class: latency / misleading state."; :>> discoveredInField = false; :>> relatedTask = "critResidual2"; :>> severity = Severity::Medium; }
    part issueCritMobileFsync : Issue { :>> id = "c0f1a5cc-c00a-4a10-9b20-a1b2c3d4c00a"; :>> title = "Mobile buffered write is not fsync-durable (crash-window delete-remote)"; :>> createdAt = "2026-07-10"; :>> createdBy = "wweatherholtz"; :>> description = "On mobile io.write can't fsync, so a pulled note's bytes can sit in cache while data.json (the base map) persists; a crash in that window leaves the note absent-on-disk but base==remote, which decide() resolves to delete-remote. ACCEPTED/DEFERRED: inherent to the mobile adapter's lack of an fsync API; desktop is durable. Mitigation options (persist base only after a read-back barrier) tracked. Class: durability (platform-inherent, accepted)."; :>> discoveredInField = false; :>> relatedTask = "critRoundResidual"; :>> severity = Severity::Medium; }
    #Resolves dependency from critRoundStd to issueCritDeltaGuard;
    #Resolves dependency from critRoundStd to issueCritCommitDoS;
    #Resolves dependency from critRoundStd to issueCritRestoreCas;
    #Resolves dependency from critRoundStd to issueCritDownloadSwitch;
    #Resolves dependency from critRoundStd to issueCritWsMustChange;
    #Resolves dependency from critRoundStd to issueCritRealtimeStale;
    #Resolves dependency from acceptOpenEnumRisk to issueCritOpenEnum;         // ACCEPTED-RISK (wweatherholtz, human-attested) — invite-only guidance
    #Resolves dependency from critResidualEasy to issueCritTotpReplay;         // DONE (real-tested)
    #Resolves dependency from critResidual2 to issueCritWsLiveness;            // DONE (real-tested)
    #Resolves dependency from acceptMobileFsyncRisk to issueCritMobileFsync;  // ACCEPTED-RISK (wweatherholtz, human-attested)

    // ---- CMMC assessor round (2026-07, AC/IA/AU + SC/SI/CM). 5 FIXED + real-tested (critRoundCmmc),
    // 2 deferred, since closed by critResidualEasy / critResidual2 (the critRoundResidual placeholder is gone). ----
    part issueCmmc2Mfa : Issue { :>> id = "c0f1a5cc-d001-4a10-9b20-a1b2c3d4d001"; :>> title = "IA.3.5.3 overstated MET — MFA not required for privileged accounts"; :>> createdAt = "2026-07-10"; :>> createdBy = "wweatherholtz"; :>> description = "ASSESSOR-CRITICAL: MFA was purely opt-in self-enrollment; nothing required a privileged account to have it (totp_enabled consulted only at login; admin_grant had no MFA precondition; bootstrap admin is password-only), so the 'MET' claim overstated the control ('USE MFA FOR privileged accounts'). RESOLVED: added REQUIRE_ADMIN_MFA=1 — require_admin denies a privileged account until it enrolls TOTP (enrollment reachable while blocked, no lockout); posture reworded to an operator-configured control (like TLS). Class: overstated MET / authz."; :>> discoveredInField = false; :>> relatedTask = "critRoundCmmc"; :>> severity = Severity::High; }
    part issueCmmc2AuditMfa : Issue { :>> id = "c0f1a5cc-d002-4a10-9b20-a1b2c3d4d002"; :>> title = "AU.3.3.1 — failed MFA enable/disable attempts not audited"; :>> createdAt = "2026-07-10"; :>> createdBy = "wweatherholtz"; :>> description = "A wrong-code MFA disable (a stolen-token probe to strip the second factor) and a failed enrollment-confirm emitted no audit event — only the success paths did. RESOLVED: mfa.rs emits MFA_DISABLE/MFA_ENABLE with outcome=FAILURE on the wrong-code branches. Class: audit coverage gap."; :>> discoveredInField = false; :>> relatedTask = "critRoundCmmc"; :>> severity = Severity::Medium; }
    part issueCmmc2WsPerUser : Issue { :>> id = "c0f1a5cc-d003-4a10-9b20-a1b2c3d4d003"; :>> title = "SC.3.13.1 — global WS budget with no per-user sub-cap (single-account notification DoS)"; :>> createdAt = "2026-07-10"; :>> createdBy = "wweatherholtz"; :>> description = "MAX_WS_CONNECTIONS was a single global cap, so one authenticated account could open all 512 sockets and deny change-notifications to every other user. RESOLVED: added a per-user WS sub-cap (MAX_WS_PER_USER=16) checked alongside the global reserve, released by the connection guard on every exit path. Class: authenticated availability."; :>> discoveredInField = false; :>> relatedTask = "critRoundCmmc"; :>> severity = Severity::Medium; }
    part issueCmmc2Cleartext : Issue { :>> id = "c0f1a5cc-d004-4a10-9b20-a1b2c3d4d004"; :>> title = "SC.3.13.8 — client cleartext-http refusal not complete across account calls"; :>> createdAt = "2026-07-10"; :>> createdBy = "wweatherholtz"; :>> description = "The 'whole channel' claim was overstated: only the sync constructor + login/register checked isInsecureRemote; the token-bearing account-management static methods (listVaults/createVault/changePassword/shares/myVaults) did not, so a persisted cleartext-remote baseUrl could transmit the token (and a new password) in the clear. RESOLVED: centralized the check in httpReq — every request refuses http-to-remote (loopback still allowed); 3.13.8 now genuinely whole-channel (met). Class: transmission confidentiality (was narrowly overstated)."; :>> discoveredInField = false; :>> relatedTask = "critRoundCmmc"; :>> severity = Severity::Medium; }
    part issueCmmc2BootGuard : Issue { :>> id = "c0f1a5cc-d005-4a10-9b20-a1b2c3d4d005"; :>> title = "CM.3.4.2 — boot guard rejected only the literal 'admin'"; :>> createdAt = "2026-07-10"; :>> createdBy = "wweatherholtz"; :>> description = "The secure-baseline boot refusal triggered only on the exact string 'admin'; SYNC_PASSWORD=password/admin123/a short pin booted without objection. RESOLVED: weak_admin_refused now rejects a known-weak set OR anything <8 chars (still gated by ALLOW_WEAK_ADMIN=1). Class: secure-baseline strengthening."; :>> discoveredInField = false; :>> relatedTask = "critRoundCmmc"; :>> severity = Severity::Low; }
    part issueCmmc2AuditSource : Issue { :>> id = "c0f1a5cc-d006-4a10-9b20-a1b2c3d4d006"; :>> title = "AU.3.3.2/3.3.8 — audit SOURCE spoofable + absent on authz-denied events"; :>> createdAt = "2026-07-10"; :>> createdBy = "wweatherholtz"; :>> description = "The audit source takes the leftmost X-Forwarded-For (client-spoofable unless the proxy replaces it), and the cross-tenant/require_admin denial events pass source='-' (IP not threaded into those choke-points). RESOLVED (high-value half): require_admin now threads the caller's ClientIp, so the privileged-function-DENIED events — the assessor's primary concern — carry the source. The lower-value per-vault read denials in scoped() keep source '-' (accepted: proxy-correlated by timestamp), and the XFF-trust remains the documented proxy contract (a spoofed XFF is only possible if the proxy doesn't overwrite it). Class: audit accountability."; :>> discoveredInField = false; :>> relatedTask = "critResidual2"; :>> severity = Severity::Medium; }
    part issueCmmc2MobileCodeWording : Issue { :>> id = "c0f1a5cc-d007-4a10-9b20-a1b2c3d4d007"; :>> title = "SC.3.13.13 — 'trust-prompt gate' wording describes a mechanism not in the reviewed code"; :>> createdAt = "2026-07-10"; :>> createdBy = "wweatherholtz"; :>> description = "The default-OFF plugin allowlist is real and correctly gates whether plugin CODE PROPAGATES, but the 3.13.13 phrasing 'never auto-executed (trust-prompt gate)' described an execution gate governed by Obsidian's own enable step, not SelfSync code. RESOLVED: the model rationale now reads 'community-plugin code does not propagate by default (per-plugin sync allowlist); execution is Obsidian's enable step'. Class: claim precision."; :>> discoveredInField = false; :>> relatedTask = "critResidualEasy"; :>> severity = Severity::Low; }
    #Resolves dependency from critRoundCmmc to issueCmmc2Mfa;
    #Resolves dependency from critRoundCmmc to issueCmmc2AuditMfa;
    #Resolves dependency from critRoundCmmc to issueCmmc2WsPerUser;
    #Resolves dependency from critRoundCmmc to issueCmmc2Cleartext;
    #Resolves dependency from critRoundCmmc to issueCmmc2BootGuard;
    #Resolves dependency from critResidual2 to issueCmmc2AuditSource;         // DONE (privileged-denial half real-tested; read-denial remainder accepted/proxy-correlated)
    #Resolves dependency from critResidualEasy to issueCmmc2MobileCodeWording; // DONE

    // ---- Client-audit follow-up (2026-07-12): a dual-source sweep of the SERVER, prompted after the
    // client conflict-model re-architecture (D0024). One LOW cross-store ordering defect found + fixed;
    // the rest verified clean (share membership is a single list, chunk refcounts are computed by query
    // not stored, the version epoch is irreducibly stored — all safe by construction). ----
    part issueShareLinkBurnedOnFailedGrant : Issue { :>> id = "c0f1a5cc-e001-4a10-9b20-a1b2c3d4e001"; :>> title = "Share-link redeem consumes the single-use link before the grant is secured (a failed grant burns the invite)"; :>> createdAt = "2026-07-12"; :>> createdBy = "wweatherholtz"; :>> description = "share_link_redeem marked the link consumed + fsynced (.share-links.json) BEFORE minting the grant (.shares.json) — two stores, two writes, no shared lock. If the follow-on grant then failed for a recoverable reason (owner at MAX_GRANTS_PER_OWNER, or a grant I/O error), or the process crashed between the two writes, the single-use link was permanently burned with NO grant created: the invitee had no access and the owner had to mint a fresh link. redeemed_by never feeds an authz decision (authorized() reads only the Grant), so it fails CLOSED — availability/correctness, not security or data-integrity. RESOLVED (1.0.30 server): redeem still CLAIMS the link atomically first (preserving single-use under concurrency), but the handler now rolls the claim back via ShareLinkStore::unredeem on both recoverable failure branches, so the invite survives to be retried; only the narrow crash-between-two-file-writes window remains (accepted — far narrower than the prior any-cap/any-error window). Test: sharelinks unredeem_rolls_back_a_claim_so_a_failed_grant_does_not_burn_the_link. Found by the client-audit-driven server dual-source sweep. Class: cross-store non-atomic write."; :>> discoveredInField = false; :>> relatedTask = "shareLinkRedeemConsumeLast"; :>> severity = Severity::Low; }
    #Resolves dependency from shareLinkRedeemConsumeLast to issueShareLinkBurnedOnFailedGrant;

    // ---- 3-lens adversarial critique of the session's shipped code (conflict re-arch D0024 + 1.0.30
    // client/server fixes), 2026-07-12, triggered by a FIELD report of a read-only vault still
    // false-flagging conflicts. Independent critics (correctness / security / concurrency); every
    // finding below verified against the code by the author before recording. All ACT except the
    // accepted redeem-cap oracle (informational, not modeled). ----
    part issueFalseConflictReadOnlyBinary : Issue { :>> id = "c0f1a5cc-f001-4a10-9b20-a1b2c3d4f001"; :>> title = "Read-only shared vault manufactures unsyncable, permanently-flagged conflict copies for a no-base divergence (FIELD)"; :>> createdAt = "2026-07-12"; :>> createdBy = "wweatherholtz"; :>> description = "FIELD-REPORTED: a read-only shared vault kept false-flagging conflicts. Root cause: reconcile's conflict-copy branch fired on read-only for a NO-COMMON-BASE divergence (decide()'s conservative default, not a real reader edit). A binary attachment (PNG) present on both the reader and the owner with differing bytes and no base → conflict-copy → the read-only branch wrote a local '(conflict …)' copy. On a read-only share that copy can NEVER push, so it's permanent litter: deriveNoteConflicts flags it forever AND it fires 'local change won't sync' every reconcile (the reported log line's path was the copy itself). RESOLVED (1.0.31): on read-only, only preserve a copy for a genuine both-sides edit against a KNOWN base (action 'merge'); a no-base divergence adopts the owner's bytes with NO copy. Also: the push case no longer reports an existing conflict-copy file as 'won't sync' (it's deliberately local). Class: false-positive conflict / read-only semantics."; :>> discoveredInField = true; :>> relatedTask = "conflictReadOnlyAndBinaryCorrectness"; :>> severity = Severity::High; }
    part issueCosmeticGuardBinaryClobber : Issue { :>> id = "c0f1a5cc-f002-4a10-9b20-a1b2c3d4f002"; :>> title = "sameIgnoringEol / cosmeticEqual lossy-decode BINARY → two different attachments collapse to equal → silent local data loss"; :>> createdAt = "2026-07-12"; :>> createdBy = "wweatherholtz"; :>> description = "Correctness critic (High). The cosmetic-EOL guard (reconcile.ts) and the modal auto-dismiss (noteconflict.ts) normalized via a NON-fatal TextDecoder, which maps every invalid byte to U+FFFD. Two genuinely different binary blobs whose differing bytes are both invalid UTF-8 normalize to the SAME string → the guard adopts remote over local with NO conflict copy (reconcile), or the modal auto-deletes this device's only copy — silent data loss for attachments, the exact 'never clobber on divergence' invariant the module protects. RESOLVED (1.0.31): both loci gate the cosmetic check on isMergeable(path,bytes) (extension- AND fatal-UTF-8-gated), so binary / invalid-UTF-8 content is excluded and can never be lossy-collapsed; genuine text keeps the false-EOL fix. Test: reconcile 'NO-BASE BINARY divergence keeps BOTH — never lossy-collapsed'. Class: data-integrity (silent clobber)."; :>> discoveredInField = false; :>> relatedTask = "conflictReadOnlyAndBinaryCorrectness"; :>> severity = Severity::High; }
    part issueGrantSaveRollback : Issue { :>> id = "c0f1a5cc-f003-4a10-9b20-a1b2c3d4f003"; :>> title = "shares.rs grant() leaves an in-memory grant when its save() fails → redeem rollback breaks single-use"; :>> createdAt = "2026-07-12"; :>> createdBy = "wweatherholtz"; :>> description = "Concurrency critic (Medium). grant() mutated self.file.grants then save()'d; on a save I/O error (disk full/EIO) the in-memory grant persisted while only Err was returned. The redeem handler, which unredeems (restores the link) on grant Err, then left BOTH a live in-memory grant AND a re-redeemable single-use link — violating single-use and the 'fails closed' contract. RESOLVED (server): grant() snapshots grants, mutates, saves, and restores the snapshot on save failure so in-memory always matches the last durable state. Test: shares grant_rolls_back_in_memory_when_save_fails. Class: cross-store consistency under I/O failure."; :>> discoveredInField = false; :>> relatedTask = "shareRedeemStoreConsistency"; :>> severity = Severity::Medium; }
    part issueSelfRedeemBurnsLink : Issue { :>> id = "c0f1a5cc-f004-4a10-9b20-a1b2c3d4f004"; :>> title = "Share-link self-redeem (owner redeems own link) burns the single-use invite (contradicts documented no-op)"; :>> createdAt = "2026-07-12"; :>> createdBy = "wweatherholtz"; :>> description = "Correctness + security critics (Medium). redeem() claims (consumes) the link before the owner==user check; the self-redeem branch skipped the grant AND the unredeem, returning success with the link consumed — so an owner testing their own link destroyed it for the intended recipient, contradicting the handler's 'self-redeem is a no-op success' comment. RESOLVED (server): the owner==user branch now unredeems (releases the claim), leaving the invite redeemable. Test: admin self_redeem_does_not_burn_the_link. Class: availability / single-use."; :>> discoveredInField = false; :>> relatedTask = "shareRedeemStoreConsistency"; :>> severity = Severity::Medium; }
    part issueResolveMineToctou : Issue { :>> id = "c0f1a5cc-f005-4a10-9b20-a1b2c3d4f005"; :>> title = "resolveNoteConflict 'keep mine' TOCTOU — stale-preview guard, then two awaits before the write → a reconcile can be clobbered"; :>> createdAt = "2026-07-12"; :>> createdBy = "wweatherholtz"; :>> description = "Concurrency critic (Medium). 'keep mine' checked the stale-preview guard, then yielded twice (io.exists, io.read) before writing original; the modal runs OUTSIDE the engine queue, so a poll-driven reconcile could pull a newer original into that gap and get silently overwritten + pushed. RESOLVED (1.0.31): re-check original===previewedOther immediately before the write (no await between the re-check and the write), narrowing the window to nothing actionable. Class: data-loss (narrow race)."; :>> discoveredInField = false; :>> relatedTask = "conflictReadOnlyAndBinaryCorrectness"; :>> severity = Severity::Medium; }
    part issueUnloadPollLeak : Issue { :>> id = "c0f1a5cc-f006-4a10-9b20-a1b2c3d4f006"; :>> title = "unload during in-flight connect() leaks a poll interval (startPolling has no unloading guard; widened by the 1.0.30 refreshShareGrant await)"; :>> createdAt = "2026-07-12"; :>> createdBy = "wweatherholtz"; :>> description = "Concurrency critic (Low-Med). unload is handled synchronously and can run while connect() is suspended at an await; on resume spinUpWs early-returns (guarded) but startPolling did not, installing a fresh setInterval that outlives teardown and pins the plugin (one leaked timer per disable/re-enable). The 1.0.30 refreshShareGrant await added a full round-trip to this window, materially widening it. RESOLVED (1.0.31): startPolling returns early when unloading (matches spinUpWs). Class: resource leak on unload (regression-adjacent)."; :>> discoveredInField = false; :>> relatedTask = "conflictReadOnlyAndBinaryCorrectness"; :>> severity = Severity::Low; }
    part issueConflictCopyLookalikeDelete : Issue { :>> id = "c0f1a5cc-f007-4a10-9b20-a1b2c3d4f007"; :>> title = "A user note literally named like a conflict copy is flagged and can be offered as a deletable version"; :>> createdAt = "2026-07-12"; :>> createdBy = "wweatherholtz"; :>> description = "Correctness critic (Low). originalOfConflictCopy matches any stem ending ' (conflict <name> <14 digits>)'; a user could craft one. deriveNoteConflicts would surface it, and if the derived 'original' doesn't exist, the modal could offer the user's real note as a deletable copy. RESOLVED (1.0.31): listNoteConflicts now requires the derived original to EXIST in the vault — a genuine conflict copy always sits beside its original; an orphan/look-alike isn't flagged. Also reduces false-flagging generally. Class: false-positive / accidental delete."; :>> discoveredInField = false; :>> relatedTask = "conflictReadOnlyAndBinaryCorrectness"; :>> severity = Severity::Low; }
    part issueShareGrantFailOpen : Issue { :>> id = "c0f1a5cc-f008-4a10-9b20-a1b2c3d4f008"; :>> title = "resolveShareGrant fails OPEN for an unknown perm string (defaults to read-write)"; :>> createdAt = "2026-07-12"; :>> createdBy = "wweatherholtz"; :>> description = "Correctness critic (Low). readOnly = perm==='read' meant any value that isn't exactly 'read' (a future/renamed/malformed perm) yielded read-write — the wrong default direction for a security flag (server enforcement still prevents actual unauthorized writes, hence Low). RESOLVED (1.0.31): readOnly = perm!=='readWrite' — fails closed (read-only unless explicitly readWrite). Test: sharelink 'fails CLOSED — unknown/malformed perm is read-only'. Class: fail-open default (defense-in-depth)."; :>> discoveredInField = false; :>> relatedTask = "conflictReadOnlyAndBinaryCorrectness"; :>> severity = Severity::Low; }
    #Resolves dependency from conflictReadOnlyAndBinaryCorrectness to issueFalseConflictReadOnlyBinary;
    #Resolves dependency from conflictReadOnlyAndBinaryCorrectness to issueCosmeticGuardBinaryClobber;
    #Resolves dependency from conflictReadOnlyAndBinaryCorrectness to issueResolveMineToctou;
    #Resolves dependency from conflictReadOnlyAndBinaryCorrectness to issueUnloadPollLeak;
    #Resolves dependency from conflictReadOnlyAndBinaryCorrectness to issueConflictCopyLookalikeDelete;
    #Resolves dependency from conflictReadOnlyAndBinaryCorrectness to issueShareGrantFailOpen;
    #Resolves dependency from shareRedeemStoreConsistency to issueGrantSaveRollback;
    #Resolves dependency from shareRedeemStoreConsistency to issueSelfRedeemBurnsLink;

    // ---- Field follow-up (2026-07-12): a mobile resume before DNS was ready flooded the log with
    // ~200 per-file UnknownHostException errors — a whole-connection failure isolated per-file. ----
    part issueConnErrorPerFileFlood : Issue { :>> id = "c0f1a5cc-f009-4a10-9b20-a1b2c3d4f009"; :>> title = "A connection-level failure (DNS unresolvable) is isolated per-file, flooding the log with one error per file instead of aborting the pass"; :>> createdAt = "2026-07-12"; :>> createdBy = "wweatherholtz"; :>> description = "FIELD: on mobile resume (app switched away → the OS suspended the app + dropped the network), reconcile started before DNS was ready and every file's pull threw the SAME UnknownHostException; the per-file error isolation (meant for one bad file while the rest continue) caught each and continued, logging ~200 identical 'couldn't sync … No address associated with hostname' lines and churning the whole vault pointlessly. It's a connectivity-timing condition (not a sync-logic bug), but the handling turned one outage into a flood + wasted battery. RESOLVED (1.0.33): a new isConnectionError classifier (host-resolution + connection-refused/reset/unreachable — deliberately NOT per-file content/read errors) makes the reconcileAll / reconcileDelta / config loops ABORT the pass on the first connection error (a shared connAbort flag short-circuits the remaining files) → the engine goes offline + backs off ONCE. A genuine single-file error (corrupt chunk, locked file, full disk) still isolates. Tests: reconcile 'a CONNECTION failure (DNS) ABORTS the pass — one error, not one-per-file' + 'single-file error is still ISOLATED' + isConnectionError boundary cases. Class: error-handling (connection-level vs per-file)."; :>> discoveredInField = true; :>> relatedTask = "connErrorAbortsPass"; :>> severity = Severity::Low; }
    #Resolves dependency from connErrorAbortsPass to issueConnErrorPerFileFlood;

    part issueEditorStatusIconLeakOnReload : Issue { :>> id = "c0f1a5cc-f00a-4a10-9b20-a1b2c3d4f00a"; :>> title = "In-editor sync icon (view.addAction) isn't removed on unload → every plugin update stacks another stale icon in the note header"; :>> createdAt = "2026-07-12"; :>> createdBy = "wweatherholtz"; :>> description = "FIELD: the note header showed SIX sync icons (one green check + five red triangles). Root cause: the opt-in in-editor indicator is added via view.addAction, which — unlike addRibbonIcon / addStatusBarItem — Obsidian does NOT auto-remove when a plugin unloads, and onunload didn't remove it either. So every plugin RELOAD/UPDATE (~5 today) orphaned the prior instance's header icon and the new instance added another; the dead ones froze at their last-rendered phase (green=synced, red=offline). Within one run it was already idempotent (an editorViews WeakSet guard); the leak was purely across reloads. RESOLVED (1.0.34): onunload removes all editorActionEls (mirrors the existing setEditorStatus-off cleanup), so unload leaves nothing behind and the next load shows exactly one icon. Orphans from pre-1.0.34 updates clear on a one-time Obsidian restart. Class: lifecycle/resource leak (non-idempotent add across reloads)."; :>> discoveredInField = true; :>> relatedTask = "editorStatusCleanupOnUnload"; :>> severity = Severity::Low; }
    #Resolves dependency from editorStatusCleanupOnUnload to issueEditorStatusIconLeakOnReload;

    // ---- UI/UX critique pass (2026-07-13, 3 independent lens critics: IA / copy / flows). Findings
    // verified against the code before recording; ≥Medium dispositioned ACT by wweatherholtz (chose all
    // four fix buckets). Split across releases 1.3.1 (polish) / 1.3.2 (destructive guards) / 1.4.0
    // (plugin-adoption ending) / 1.5.0 (sharing+conflicts surfacing). ----
    part issueUxQuickWins : Issue { :>> id = "c0f1a5cc-e00a-4a10-9b20-a1b2c3d4e00a"; :>> title = "UX polish: misdirecting recovery copy, jammed consent banner, silent max-file-size failure, inconsistent terminology + dead code"; :>> createdAt = "2026-07-13"; :>> createdBy = "wweatherholtz"; :>> description = "UX critique quick-win bundle. (HIGH) The session-expired / vault-gone recovery messages told the user to 'use Set up / switch vault' — a COMMAND name, not a button; the real buttons are 'Reconfigure' and 'Switch' — misdirecting exactly when stuck. (MED) The setup server/consent banner used \\n\\n in a <p> with no white-space:pre-wrap, collapsing the compliance banner to one run-on line. (MED) 'Max file size' invalid/empty input failed SILENTLY — no save, no message, no revert. (MED) A broken breadcrumb: a log line pointed to 'Settings → Config differences', a section that doesn't exist (it's 'Conflicts'). (LOW) 3 log-viewer toasts dropped the 'SelfSync:' prefix; 'Keep the other' had no referent; 'reload Obsidian' is undefined on mobile; change-password didn't warn other token-only devices need the NEW password; statusTitle() was dead code diverged from statusDisplay(). RESOLVED (1.3.1): recovery copy names the real buttons; banner gets pre-wrap; max-file-size validates on blur (notice + revert); breadcrumb → 'Conflicts'; toast prefixes fixed; 'Keep the other device's'; 'fully close and reopen Obsidian'; change-password warning extended; statusTitle + its test removed. Class: copy/feedback/clarity."; :>> discoveredInField = false; :>> relatedTask = "uxPolishBundle"; :>> severity = Severity::Medium; }
    #Resolves dependency from uxPolishBundle to issueUxQuickWins;

    part issueUnguardedDestructiveActions : Issue { :>> id = "c0f1a5cc-e00b-4a10-9b20-a1b2c3d4e00b"; :>> title = "Irreversible actions (mirror-switch delete, fork-overwrite, sign-out) are less guarded than harmless ones"; :>> createdAt = "2026-07-13"; :>> createdBy = "wweatherholtz"; :>> description = "UX critique (flows lens), HIGH. The plugin guarded SAFE actions but under-guarded IRREVERSIBLE ones: (1) the vault-switch 'Download'/'Upload' mirror modes DELETE local-only / remote-only files on a single warning-styled tap with no confirmation — while the non-destructive 'Leave share' has a full confirm(); (2) Fork uploads unconditionally (skips the switch resolve-prompt), so a fork name that already matches an owned vault would OVERWRITE it with no check; (3) 'Sign out' (token-only mode → no saved password) sits next to 'Change password' with no confirm, easy to fat-finger, and strands the user needing their password. RESOLVED (1.3.2): applySwitch confirm()s Download/Upload naming which side loses files ('can't be undone'); doFork refuses/confirms when the name already exists (checks the loaded vault list); Sign out confirm()s ('you'll need your password to sign back in; local files kept'). Merge (safe) still needs no confirm. Class: destructive-action guarding / data-safety."; :>> discoveredInField = false; :>> relatedTask = "guardDestructiveActions"; :>> severity = Severity::High; }
    #Resolves dependency from guardDestructiveActions to issueUnguardedDestructiveActions;

    part issuePluginAdoptionSilentRestart : Issue { :>> id = "c0f1a5cc-e00c-4a10-9b20-a1b2c3d4e00c"; :>> title = "Plugin adoption ends in an invisible restart requirement; a fresh vault's empty plugin list reads as 'nothing to sync'"; :>> createdAt = "2026-07-13"; :>> createdBy = "wweatherholtz"; :>> description = "UX critique (all 3 lenses), HIGH. After 'Install all from the sync', the settings pane re-renders showing the plugins as synced, but nothing is active: files download on the next reconcile and Obsidian only loads plugins at STARTUP, so they stay dormant until a full restart — the only hint was a transient async toast saying 'reload Obsidian' (meaningless on mobile). Looks done, isn't → users re-tap or conclude it failed. Separately, on a fresh vault before the first reconcile reports server plugins, the checklist was EMPTY and read as 'nothing to sync' (the list populates minutes later). RESOLVED (1.4.0): a STANDING banner in the Synced-community-plugins group counts plugins adopted-but-not-installed-locally and says 'fully close and reopen Obsidian (on mobile, swipe the app away) to enable them'; and a 'Checking the server for plugins…' placeholder shows while the server list is still empty. Class: silent-until-later step / discoverability."; :>> discoveredInField = false; :>> relatedTask = "pluginAdoptionRestartHint"; :>> severity = Severity::High; }
    #Resolves dependency from pluginAdoptionRestartHint to issuePluginAdoptionSilentRestart;

    part issueSharingConflictsDiscoverability : Issue { :>> id = "c0f1a5cc-e00d-4a10-9b20-a1b2c3d4e00d"; :>> title = "Inbound sharing + conflicts are undiscoverable; redeem-while-signed-in ends in a toast that syncs nothing"; :>> createdAt = "2026-07-13"; :>> createdBy = "wweatherholtz"; :>> description = "UX critique (IA + flows). Redeeming a share link — the primary INBOUND action — was reachable only by opening a button labelled 'Switch' and scrolling; a new recipient had no labelled path at all. Conflicts (data-safety, urgent) had no command/ribbon surface — only the transient toast + a settings section that exists only when conflicts are pending. And an already-signed-in redeem added the grant but relied on a 9s toast ('Open Settings → Switch vault to sync it') then synced NOTHING — easy to miss on mobile, so redeem looked like it did nothing. RESOLVED (1.5.0): added command-palette commands 'Switch vault', 'Redeem a share link', and 'Resolve conflicts' (routes to whichever kind is pending), renamed the setup command to 'Set up / reconfigure connection'; added a 'Redeem a share link' button to the unconfigured status card (the new-recipient entry point); and startRedeem now OPENS the Switch modal after an already-signed-in redeem (the redeemed vault is in its 'Shared with you' list) instead of leaving the second step to a toast. Class: discoverability / silent-until-later step."; :>> discoveredInField = false; :>> relatedTask = "surfaceSharingAndConflicts"; :>> severity = Severity::Medium; }
    #Resolves dependency from surfaceSharingAndConflicts to issueSharingConflictsDiscoverability;

    // ---- UX-critique findings the user DECLINED to act on now (2026-07-13, "record these as declined
    // items"). Real but larger; deferred by an explicit human disposition (deferUxEnhancements). ----
    part issueNoProtocolHandler : Issue { :>> id = "c0f1a5cc-e00e-4a10-9b20-a1b2c3d4e00e"; :>> title = "No obsidian:// protocol handler — tapped share/setup links can't deep-link into the flow"; :>> createdAt = "2026-07-13"; :>> createdBy = "wweatherholtz"; :>> description = "UX critique (IA lens), Medium. The plugin registers no registerObsidianProtocolHandler; share/setup payloads use bespoke selfsync:// / selfsync-share:// schemes the OS won't route into Obsidian, so every hand-off degrades to copy-paste. Fix would register an obsidian://selfsync?… handler that opens the setup-or-redeem flow prefilled, and re-encode payloads as obsidian:// URLs (keeping copyable text as fallback). DECLINED for now (larger change; deferred by wweatherholtz 2026-07-13). Class: onboarding friction (deferred)."; :>> discoveredInField = false; :>> relatedTask = "deferUxEnhancements"; :>> severity = Severity::Medium; }
    part issueWizardStatePersistence : Issue { :>> id = "c0f1a5cc-e00f-4a10-9b20-a1b2c3d4e00f"; :>> title = "Setup-wizard state is in-memory only — a mid-flow suspend can orphan a just-registered account"; :>> createdAt = "2026-07-13"; :>> createdBy = "wweatherholtz"; :>> description = "UX critique (flows lens), Medium. The wizard keeps server/username/password/token in memory and persists only on finish; on mobile a suspend after 'Create account' registers the account server-side but reopening starts blank, so a second create attempt errors confusingly. Fix would persist wizard progress (at least server+username+registered-flag+token) or transition to a persisted logged-in state right after register. DECLINED for now (non-trivial; deferred by wweatherholtz 2026-07-13). Class: re-entrancy / mobile-suspend (deferred)."; :>> discoveredInField = false; :>> relatedTask = "deferUxEnhancements"; :>> severity = Severity::Medium; }
    part issueDeepIaRestructure : Issue { :>> id = "c0f1a5cc-e010-4a10-9b20-a1b2c3d4e010"; :>> title = "Deeper IA restructures deferred: overlapping connection verbs + a unified Vaults & sharing surface"; :>> createdAt = "2026-07-13"; :>> createdBy = "wweatherholtz"; :>> description = "UX critique (IA lens), Low-Medium. Two structural items beyond the 1.3–1.5 fixes: (a) three overlapping stop/change-connection verbs (Sign out / Disconnect / Reconfigure) split across sections with a disambiguating paragraph — should be one clearer model; (b) inbound vs outbound sharing split across 'Share' and 'Switch' — a single 'Vaults & sharing' surface would unify 'shared with me' (redeem/leave) and 'people I share with' (grants/links). 1.5.0 added redeem/switch/resolve COMMANDS + a redeem button, which mitigates discoverability, but the deeper consolidation is DECLINED for now (deferred by wweatherholtz 2026-07-13). Also folds the residual UX lows the user didn't select (conflict-modal nested scroll + destructive default; 'Install all' label flip). Class: information architecture (deferred)."; :>> discoveredInField = false; :>> relatedTask = "deferUxEnhancements"; :>> severity = Severity::Low; }
    #Resolves dependency from deferUxEnhancements to issueNoProtocolHandler;
    #Resolves dependency from deferUxEnhancements to issueWizardStatePersistence;
    #Resolves dependency from deferUxEnhancements to issueDeepIaRestructure;

    // ---- Human-factors critique pass (2026-07-13, independent HF/cognitive-ergonomics expert). Findings
    // verified against the code; ≥Medium dispositioned ACT by wweatherholtz (all four buckets). ----
    part issueStatusIndicatorMisleads : Issue { :>> id = "c0f1a5cc-e011-4a10-9b20-a1b2c3d4e011"; :>> title = "Status indicator misleads: green 'Fully synced' on a read-only vault, and one yellow SPINNER covers healthy-polling + connecting + syncing"; :>> createdAt = "2026-07-13"; :>> createdBy = "wweatherholtz"; :>> description = "HF critique, HIGH (gulf of evaluation / mode error / alarm habituation). (F1) On a read-only shared vault Obsidian still lets the user EDIT, but those edits never upload — yet statusDisplay's idle branch showed a plain green 'Fully synced', implying the user's changes are safe on the server (they're stranded or overwritten). (F3) idle-over-polling rendered the SAME yellow refresh-cw SPINNER as connecting/syncing, so a healthy device on a dropped websocket sat at a permanent spinner — indistinguishable from 'stuck', training panic or habituation. RESOLVED (1.5.1): idle on a read-only vault reads 'Synced (read-only) — your edits stay on this device' with a lock glyph; idle (realtime OR polling) now uses a STEADY glyph (check/lock), never the spinner — the spinner is reserved for the active connecting/syncing states; colour still distinguishes green vs yellow. Test: plugin-wiring statusDisplay read-only case. Class: status legibility / mode error."; :>> discoveredInField = false; :>> relatedTask = "hfStatusAndWarnings"; :>> severity = Severity::High; }
    part issueMiscalibratedSwitchWarning : Issue { :>> id = "c0f1a5cc-e012-4a10-9b20-a1b2c3d4e012"; :>> title = "Vault-switch download warning cried 'can't be undone', but local removals go to the recoverable vault trash"; :>> createdAt = "2026-07-13"; :>> createdBy = "wweatherholtz"; :>> description = "HF critique, Low-Med (Nielsen #9 / warning calibration). The 1.3.2 download confirm said local files 'will be DELETED from this device. This can't be undone.' — but ObsidianVaultIo.remove routes sync-driven deletions to the vault trash (recoverable). Over-warning on a recoverable action erodes the credibility of 'can't be undone' where it IS true (server upload). RESOLVED (1.5.1): download confirm now says local files are 'moved to this device's trash (recoverable there)'; upload says 'removed on the server'; dropped the blanket 'can't be undone'. Class: warning calibration."; :>> discoveredInField = false; :>> relatedTask = "hfStatusAndWarnings"; :>> severity = Severity::Low; }
    #Resolves dependency from hfStatusAndWarnings to issueStatusIndicatorMisleads;
    #Resolves dependency from hfStatusAndWarnings to issueMiscalibratedSwitchWarning;

    part issueSidePickingInconsistent : Issue { :>> id = "c0f1a5cc-e013-4a10-9b20-a1b2c3d4e013"; :>> title = "Four 'pick a side' surfaces use inconsistent wording + a biasing CTA on the unbiased note-conflict choice"; :>> createdAt = "2026-07-13"; :>> createdBy = "wweatherholtz"; :>> description = "HF critique, Med (mental-model instability + capture error). The same 'which side wins?' decision was worded differently across note-conflict / config-conflict / config-direction / vault-switch, and the CTA (highlighted default) jumped sides — worst, the note-conflict highlighted 'Keep this device's' on a genuinely 50/50 IRREVERSIBLE content choice, inviting a reflexive tap that discards the other device's edits. RESOLVED (1.5.2): removed the CTA from the unbiased destructive choices (note-conflict + config-conflict); standardized config vocabulary to 'Use this device's' / 'Use the synced version'; CTA now reserved for a genuinely-safe default (vault-switch Merge). Class: mental-model consistency / capture-error prevention."; :>> discoveredInField = false; :>> relatedTask = "hfConfirmAndSidePicking"; :>> severity = Severity::Medium; }
    part issueNativeConfirmMobile : Issue { :>> id = "c0f1a5cc-e014-4a10-9b20-a1b2c3d4e014"; :>> title = "Destructive guards used native window.confirm() — out-of-context / unstyled on the mobile Capacitor webview"; :>> createdAt = "2026-07-13"; :>> createdBy = "wweatherholtz"; :>> description = "HF critique, Low (consistency / error-prevention trust). The confirmations added in 1.3.2 (mirror-switch, fork-overwrite, leave-share, sign-out) used window.confirm(), which on Obsidian mobile renders as a bare OS dialog divorced from the plugin's visual context — reading as less trustworthy exactly at a destructive step. RESOLVED (1.5.2): a small in-app ConfirmModal (confirm.ts, confirmModal()) consistent with the plugin's other modals replaces all four confirm() calls (warn-styled confirm button, named consequence). Class: consistency / confirmation reliability."; :>> discoveredInField = false; :>> relatedTask = "hfConfirmAndSidePicking"; :>> severity = Severity::Low; }
    #Resolves dependency from hfConfirmAndSidePicking to issueSidePickingInconsistent;
    #Resolves dependency from hfConfirmAndSidePicking to issueNativeConfirmMobile;

    part issueMobileStatusTextless : Issue { :>> id = "c0f1a5cc-e015-4a10-9b20-a1b2c3d4e015"; :>> title = "On mobile the only persistent status is a textless icon in the sidebar drawer with no reachable tooltip"; :>> createdAt = "2026-07-13"; :>> createdBy = "wweatherholtz"; :>> description = "HF critique, High (gulf of evaluation / Nielsen #1). Mobile gets a ribbon icon only; the informative text lives in an aria-label (no touch tooltip) and the settings card — so 'did my note sync?' takes 2-3 taps on the platform whose goal is glanceable. PARTIALLY RESOLVED (1.6.0): added a 'Sync status' command that toasts the current status text (a one-tap words readout, works on mobile). NOTE: a truly persistent on-screen TEXT indicator isn't available — Obsidian mobile has no status bar and view.addAction is icon-only; the opt-in in-editor indicator (glanceable colour at the note) remains the persistent option. Class: status legibility (platform-limited; partially mitigated)."; :>> discoveredInField = false; :>> relatedTask = "hfStatusSurfacingAndPreview"; :>> severity = Severity::High; }
    part issueBlindConfigOverwrite : Issue { :>> id = "c0f1a5cc-e016-4a10-9b20-a1b2c3d4e016"; :>> title = "Config first-contact direction is a whole-side overwrite with no preview, unlike the diff-showing conflict screens"; :>> createdAt = "2026-07-13"; :>> createdBy = "wweatherholtz"; :>> description = "HF critique, Med (gulf of evaluation before commit). Turning on a config surface asks download/upload but shows nothing about what will change, while the more-recoverable per-file conflict shows a diff. PARTIALLY RESOLVED (1.6.0): the ConfigDirectionModal copy now sets expectations — 'only files that differ change, everything else is left alone, and later edits on either side reconcile normally'. NOTE: a true diff/count preview needs a local-vs-server compare the modal doesn't have; deferred as a possible follow-up. Class: pre-commit evaluation (copy-level mitigation)."; :>> discoveredInField = false; :>> relatedTask = "hfStatusSurfacingAndPreview"; :>> severity = Severity::Medium; }
    part issueLongOpTransientCompletion : Issue { :>> id = "c0f1a5cc-e017-4a10-9b20-a1b2c3d4e017"; :>> title = "Fork/switch report progress only via a transient toast, lost when the app suspends"; :>> createdAt = "2026-07-13"; :>> createdBy = "wweatherholtz"; :>> description = "HF critique, Med (gulf of evaluation for long ops). A fork/switch that uploads a whole vault can run for minutes; the modal closes and completion is a toast that fires into a suspended app, with only a generic yellow 'syncing' meanwhile — the user can't tell if it finished. RESOLVED (1.6.0): statusDisplay shows a persistent 'Switching vault…' state whenever a switch/fork is in flight, DERIVED from the saved pendingSwitch flag, so it survives suspend/resume and clears when the switch reconcile completes. Test: plugin-wiring statusDisplay pendingSwitch case. Class: long-op evaluation."; :>> discoveredInField = false; :>> relatedTask = "hfStatusSurfacingAndPreview"; :>> severity = Severity::Medium; }
    #Resolves dependency from hfStatusSurfacingAndPreview to issueMobileStatusTextless;
    #Resolves dependency from hfStatusSurfacingAndPreview to issueBlindConfigOverwrite;
    #Resolves dependency from hfStatusSurfacingAndPreview to issueLongOpTransientCompletion;

    // Caught by the new tests (D0026 comprehensive-testing overhaul), NOT in the field — the intended
    // win: a MEDIUM correctness defect found by a fail-first regression test instead of a critique pass.
    part issueMergeCrlf : Issue { :>> id = "c0f1a5cc-e018-4a10-9b20-a1b2c3d4e018"; :>> title = "merge3 didn't normalize CRLF → cross-platform edits exploded into spurious whole-file conflicts"; :>> createdAt = "2026-07-14"; :>> createdBy = "ai"; :>> description = "src/merge.ts splitLines() split on raw \\n, leaving a trailing \\r on every CRLF line, so the LCS found ZERO common anchors between a CRLF base and an LF re-save — collapsing the whole file into one conflict region even when the real content edits didn't overlap. Obsidian vaults sync across Windows (CRLF) and macOS/Linux/mobile (LF), so this fired on nearly every cross-platform merge, undermining Merge as the 'nothing is lost' safe default in the vault-switch flow. Found by test/merge-eol.test.ts (authored it.fails, flipped to a passing regression on fix). FIX: normalize CRLF→LF before any comparison in merge3 (merged output already joins with \\n, so this is consistent, not lossy). Severity Medium. discoveredInField=false — caught pre-release by the new merge suite."; :>> discoveredInField = false; :>> relatedTask = "testHardeningClient"; :>> severity = Severity::Medium; }
    #Resolves dependency from testHardeningClient to issueMergeCrlf;

    part issueDockerfileEnvSecret : Issue { :>> id = "c0f1a5cc-e019-4a10-9b20-a1b2c3d4e019"; :>> title = "server Dockerfile baked SYNC_PASSWORD into an ENV instruction (persisted in image layers)"; :>> createdAt = "2026-07-15"; :>> createdBy = "ai"; :>> description = "The server Dockerfile set `ENV SYNC_PASSWORD=admin` (+ SYNC_USER=admin), which BuildKit flags SecretsUsedInArgOrEnv: an ENV value is persisted into the image layers (readable via `docker history`/`inspect`), so a credential in ENV leaks. Surfaced as a warning in the server-image CI build. Low real impact (the value was the well-known default 'admin', which the boot weak-password guard already REFUSES unless ALLOW_WEAK_ADMIN=1, so it was never a usable live credential), but it's a genuine hygiene defect. FIX: drop SYNC_USER/SYNC_PASSWORD from the image ENV (keep non-sensitive DATA_ROOT/BIND_ADDR); the code defaults (config.rs admin/admin) still apply and are still refused at boot, so the operator must provide a real password at RUNTIME (docker -e / compose / secret). Severity Low. discoveredInField=false (CI docker lint)."; :>> discoveredInField = false; :>> relatedTask = "postOverhaulHardening"; :>> severity = Severity::Low; }
    #Resolves dependency from postOverhaulHardening to issueDockerfileEnvSecret;

    part issueFalseAbsenceDelete : Issue { :>> id = "c0f1a5cc-e01a-4a10-9b20-a1b2c3d4e01a"; :>> title = "delete-remote tombstoned on absence-from-the-LISTING, not CONFIRMED absence (cloud-placeholder / failed-enumeration data-loss vector)"; :>> createdAt = "2026-07-15"; :>> createdBy = "wweatherholtz"; :>> description = "The batch reconcile path (reconcileAll/reconcileDelta) derived a file's local presence from io.list(), which UNDER-REPORTS when a directory fails to enumerate (ObsidianVaultIo.enumerateConfig swallowed the adapter.list error as an empty dir) or a cloud-drive placeholder (OneDrive Files-On-Demand) isn't hydrated. A still-present file then looked absent → locallyPresent=false DEFEATED the existing C1 read-failure guard (which requires locallyPresent) → decide()=delete-remote → an UNGUARDED tombstone (delete-remote had no absence/bulk guard), which on the next restart delete-locals fleet-wide. This is the SelfSync-side latent cause of the 'all plugins vanished from the list after restart' CLASS. NOTE: it did NOT cause the specific field report — that vault's server index had 0 tombstones (proving SelfSync deleted nothing there; its config sync was pointed at an offline local server), and the true cause was OneDrive Files-On-Demand dehydrating the plugin files so Obsidian couldn't read them at startup. But this is exactly the trap OneDrive-style placeholders + config sync ON + a reachable server would spring. FIX: delete-remote now requires CONFIRMED absence via a direct per-path probe (confirmedAbsent — io.exists/read, never the listing); an unreadable-but-existing file is KEPT. enumerateConfig now LOGS a dir-list failure instead of silently treating it as empty. Correct-by-construction, not a bulk guard (per the owner's explicit direction). Regression: reconcile.test 'CONFIRMED absence' (fail-first verified: guard disabled → the placeholder test fails; genuine deletes still propagate). Severity High (data-loss class). discoveredInField=false (found by analysis while diagnosing the OneDrive report)."; :>> discoveredInField = false; :>> relatedTask = "falseAbsenceDeleteFix"; :>> severity = Severity::High; }
    #Resolves dependency from falseAbsenceDeleteFix to issueFalseAbsenceDelete;

    part issueConfigListDisable : Issue { :>> id = "c0f1a5cc-e01b-4a10-9b20-a1b2c3d4e01b"; :>> title = "community-plugins.json synced as an opaque blob → a shorter synced copy DISABLES a locally-installed plugin"; :>> createdAt = "2026-07-15"; :>> createdBy = "wweatherholtz"; :>> description = "community-plugins.json is the SET of enabled community-plugin ids (and gates whether installed plugins RUN), but config sync treated it as an opaque whole-file blob resolved by taking ONE whole side. So adopting a shorter synced copy (a pull where the remote dropped an id, or a divergence resolved to 'remote') would DISABLE every plugin not in that list — including SelfSync's own id — even though the plugin is installed+enabled locally. This is the DISABLE half of the 'all my plugins vanished' class (distinct from issueFalseAbsenceDelete's DELETE half). Surfaced while diagnosing the OneDrive field report, where the owner explicitly asked for proper behavior rather than a guard. FIX (correct-by-construction): community-plugins.json is now UNION-merged (isEnabledListConfig + mergeEnabledPluginsJson in configsync.ts; a dedicated branch in reconcileOne) — a grow-only set of enabled ids. A pull/divergence keeps every locally-enabled id and adds the remote's, and pushes the union so the server converges; a read-only share keeps the union locally. Enables propagate; a disable does not (toggled per device) — the catastrophe-proof asymmetry the owner chose. Verified: configsync.test (mergeEnabledPluginsJson union/empty/null), reconcile.test (fail-first: a shorter pull keeps the local plugin + converges the server; adopts a longer list), and a real-Obsidian two-device e2e (configsync.pwspec: A's plugin propagates to B, B's own plugin not disabled). Severity High (availability/data class). discoveredInField=false."; :>> discoveredInField = false; :>> relatedTask = "configListSetMerge"; :>> severity = Severity::High; }
    #Resolves dependency from configListSetMerge to issueConfigListDisable;

    part issuePendingCountsDeclinedFiles : Issue { :>> id = "c0f1a5cc-f00c-4a10-9b20-a1b2c3d4f00c"; :>> title = "The pending-sync count includes remote files this device declined (config off / plugin not allowlisted) → a phantom count that never drains"; :>> createdAt = "2026-07-13"; :>> createdBy = "wweatherholtz"; :>> description = "FIELD: reopening a vault showed 20+ pending syncs that 'never do anything'; the server log showed login OK then no transfers. Root cause: reconcileAll/reconcileDelta pre-classified the pending set from remote-vs-base WITHOUT applying the accepts() filter, so a remote file this device is set NOT to sync (a config surface off, or a community plugin not in the allowlist) was counted as pending even though reconcileOne correctly SKIPS it — it can never transfer, so the count never drained (and on mobile, which backgrounds mid-pass, it looked permanently stuck). The user also had no way to see WHAT was waiting or learn that plugin sync is opt-in on BOTH ends. RESOLVED (1.0.39): the pending pre-classifier now excludes accepts()-filtered files in both paths (honest 'work this device will do'); those files are surfaced via a new onDeclined callback → a coalesced, change-only log ('N community plugins / config files on the server are NOT in this device's sync selection — enable them in Settings → Obsidian configuration to sync them here'), which both explains the count and tells the user how to adopt a plugin another vault added. Test: reconcile 'does NOT count a remote file this device DECLINES as pending'. Class: misleading state / discoverability."; :>> discoveredInField = true; :>> relatedTask = "pendingExcludesDeclined"; :>> severity = Severity::Medium; }
    #Resolves dependency from pendingExcludesDeclined to issuePendingCountsDeclinedFiles;

    part issueConfigSyncMobileLatency : Issue { :>> id = "c0f1a5cc-f00b-4a10-9b20-a1b2c3d4f00b"; :>> title = "Config sync is slow (~minutes) on mobile — the local-change detector is a 2-min periodic scan, and mobile suspends when backgrounded"; :>> createdAt = "2026-07-12"; :>> createdBy = "wweatherholtz"; :>> description = "FIELD: config sync felt like it took ~5 min on mobile. Not broken — DESKTOP is live (the low-level vault `raw` event fires on any .obsidian/ change → immediate push), but that event is unreliable on mobile (Capacitor), so mobile fell back to a periodic config-only re-hash gated at CONFIG_SCAN_INTERVAL_MS=120s; add mobile suspend-on-background (timers frozen) and the sender-side detection could take minutes. RESOLVED (1.0.35), user chose 'cheap fast scan': (1) reconcileLocalConfig now skips a file whose on-disk (size,mtime) match the stat stamp from the last time it equalled base — so the scan can run OFTEN without re-hashing every synced plugin's bytes; (2) CONFIG_SCAN_INTERVAL_MS 120s→30s; (3) a visibilitychange listener forces a config scan on app-resume (mobile) rather than waiting for the next tick. Detection drops ~2 min → ~30s (instant on reopen); the receiving device already pulled promptly via WS poke/poll. Tests: reconcile config-scan fast-path skip / new-file still-detected / stamp-then-skip. Class: latency (platform-inherent detection gap, mitigated)."; :>> discoveredInField = true; :>> relatedTask = "fastCheapConfigScan"; :>> severity = Severity::Low; }
    #Resolves dependency from fastCheapConfigScan to issueConfigSyncMobileLatency;

    // ---- Top-20 critical-functions critique pass (2026-07-17): five independent critics audited the
    // 20 most safety-critical functions line-by-line (idiom / design / concision). Findings verified
    // against the code before recording; these four are the verified real defects (the rest were
    // maintainability/design cleanups, tracked as the cleanup effort). All resolved by postCritiqueDefectFixes. ----
    part issueDiagnoseJsonThrows : Issue { :>> id = "c0f1a5cc-e01c-4a10-9b20-a1b2c3d4e01c"; :>> title = "diagnose() read the throwing .json getter OUTSIDE its try/catch → a 200 with a non-JSON body threw out of the documented never-throws path"; :>> createdAt = "2026-07-17"; :>> createdBy = "ai"; :>> description = "RequestUrlResponse.json is a getter that JSON-parses .text and THROWS on a non-JSON body, and a reverse proxy / captive portal can answer 200 with an HTML error page. HttpTransport.diagnose (documented 'Never throws') read health.json (transport.ts:107) and st.json (:125) OUTSIDE the try/catch that wrapped only the httpReq await — so such a body threw a SyntaxError, precisely in the 'tell me why sync is broken' path where a misconfigured proxy is most likely. The codebase's own errText helper exists to dodge exactly this getter hazard, making the direct reads an oversight. Found by the top-20 critique pass (Agent D), verified against the code. FIX: a tryJson() safe accessor (try{return r.json}catch{return undefined}); diagnose reads both bodies through it, skipping the version/degraded checks on an unreadable body instead of throwing. Regression: transport.test 'diagnose never throws even when the body isnt JSON' (2 tests, a throwing json getter mirroring real Obsidian; fail-first by construction — the old unguarded getter read rejected where the test asserts resolves). Severity Medium. discoveredInField=false (critique pass, pre-release)."; :>> discoveredInField = false; :>> relatedTask = "postCritiqueDefectFixes"; :>> severity = Severity::Medium; }
    part issueOpensMapUnbounded : Issue { :>> id = "c0f1a5cc-e01d-4a10-9b20-a1b2c3d4e01d"; :>> title = "AppState.opens per-key open-lock map grew unbounded (RS-1 leak class) — inserted per (user,vault), never removed"; :>> createdAt = "2026-07-17"; :>> createdBy = "ai"; :>> description = "state.rs vault() inserts an Arc<Mutex<()>> per (user,vault) into `opens` to serialize cold opens, but never removed it — not on RS-1 eviction (which bounds the sibling `ns` handle map) nor in purge_user_data / purge_vault (which clear `ns` but left `opens`). So `opens` grew one tiny entry per distinct vault ever accessed, for the process's life — the same insert-only-map leak RS-1 fixed for `ns`, reproduced in the map added beside it. Per-entry cost is tiny so growth is slow, but genuinely unbounded (and a purged+recreated vault left a stale lock). Found by the top-20 critique pass (Agent E), verified against the code. FIX: release_open_lock drops the key when the caller is its last holder (Arc::strong_count<=2 → no waiters; safe because the handle is cached in `ns` before teardown, so a fresh caller hits the fast path and never re-opens); both purge paths now clear `opens` too. Test: state::opens_map_does_not_grow_across_distinct_vault_opens (20 distinct opens leave 0 residual entries; purge clears). Severity Low. discoveredInField=false."; :>> discoveredInField = false; :>> relatedTask = "postCritiqueDefectFixes"; :>> severity = Severity::Low; }
    part issueCommitDoubleMetaQuery : Issue { :>> id = "c0f1a5cc-e01e-4a10-9b20-a1b2c3d4e01e"; :>> title = "Vault::commit queried file_meta twice on the write path (idempotent check + CAS) — a redundant DB round-trip"; :>> createdAt = "2026-07-17"; :>> createdBy = "ai"; :>> description = "vault.rs commit() read self.index.file_meta(&req.path) at the idempotent short-circuit (:535) AND again at the CAS check (:549) — two DB reads of the same row on the hot write path. No correctness impact (&mut self serializes writes, so the row can't change between them), purely a redundant round-trip and a second chance to read inconsistently. Found by the top-20 critique pass (Agent E), verified against the code. FIX: read `existing` ONCE and reuse it for both the idempotent match (returning a clone) and the CAS current-version. Covered by the existing commit idempotency/CAS tests (still green). Severity Low. discoveredInField=false."; :>> discoveredInField = false; :>> relatedTask = "postCritiqueDefectFixes"; :>> severity = Severity::Low; }
    part issueScopedOpenError404 : Issue { :>> id = "c0f1a5cc-e01f-4a10-9b20-a1b2c3d4e01f"; :>> title = "scoped() flattened a genuine vault-open failure to 404, hiding the real fault and misleading the client"; :>> createdAt = "2026-07-17"; :>> createdBy = "ai"; :>> description = "api.rs scoped() mapped the st.vault() open Err to AppError::NotFound. But vault_exists already confirmed the directory + safe names just above, so reaching an open-Err is an UNEXPECTED IO/DB failure, not 'not found' — reporting 404 tells the client the vault was deleted and discards the diagnostic (contrast the sibling spawn_blocking join-error arm, already Internal). Found by the top-20 critique pass (Agent E), verified against the code. FIX: map the open failure to AppError::Internal(cause), reserving 404 for the vault_exists precheck. Severity Low. discoveredInField=false."; :>> discoveredInField = false; :>> relatedTask = "postCritiqueDefectFixes"; :>> severity = Severity::Low; }
    #Resolves dependency from postCritiqueDefectFixes to issueDiagnoseJsonThrows;
    #Resolves dependency from postCritiqueDefectFixes to issueOpensMapUnbounded;
    #Resolves dependency from postCritiqueDefectFixes to issueCommitDoubleMetaQuery;
    #Resolves dependency from postCritiqueDefectFixes to issueScopedOpenError404;

    // Found 2026-07-17 while trying to clear deliverableTestGate after the critique cleanup.
    part issueClippyNotInCi : Issue { :>> id = "c0f1a5cc-e020-4a10-9b20-a1b2c3d4e020"; :>> title = "CI never ran clippy though the reverify gate requires clippy -D warnings → lint drift accumulated silently + blocked keel reverify"; :>> createdAt = "2026-07-17"; :>> createdBy = "wweatherholtz"; :>> description = "The D0101 reverify contract (.engine/contracts/reverify.toml) includes 'cargo clippy --all-targets -- -D warnings', but .github/workflows/ci.yml ran only cargo-llvm-cov (tests+coverage) + cargo-audit + npm-audit + client vitest — NEVER clippy. So clippy lint drift accumulated invisibly: a newer local toolchain (clippy 1.96) flagged ~7 warnings in files nobody recently touched (audit/users/ws/auth/sharelinks + the opens field type + a hardening test), which turned 'keel reverify' RED at the clippy step and meant deliverableTestGate could not be re-stamped after the top-20 critique cleanup. A recurrable process gap (D0047): a gate that isn't enforced by CI drifts. FIX: (1) a new server-clippy CI job running the exact reverify clippy command (the permanent guard); (2) fixed the ~7 pre-existing lints (redundant cast, map_or→is_some_and, bool_comparison, too_many_arguments allow, items_after_test_module allows for the request extractors, OpenLocks type alias, repeat().take()→vec![;n]). Verified clippy -D warnings exits 0 + 99 tests green. Severity Low (hygiene/process; no runtime impact — the drift was all style/test lints). discoveredInField=false."; :>> discoveredInField = false; :>> relatedTask = "clippyGateInCi"; :>> severity = Severity::Low; }
    #Resolves dependency from clippyGateInCi to issueClippyNotInCi;

    // ---- Round-2 function audit (D0028, 2026-07-18): next 20 critical functions, 5 independent critics.
    // Each finding VERIFIED against the code before recording. These three are the verified real defects. ----
    part issueChunkPutNoDirFsync : Issue { :>> id = "c0f1a5cc-e021-4a10-9b20-a1b2c3d4e021"; :>> title = "ContentStore::put fsync'd the blob bytes but not the shard DIR after rename → an acked commit's chunk could vanish on power loss"; :>> createdAt = "2026-07-18"; :>> createdBy = "wweatherholtz"; :>> description = "chunkstore.rs put() did write-temp → sync_all(contents) → rename(tmp, p) but never fsync'd the containing shard directory after the rename. Its own R10-D1 invariant is explicit: a referenced chunk must survive power loss because the index (fsync'd on commit) points at it. sync_all makes the BYTES durable, but under POSIX the directory ENTRY created by the rename is not guaranteed to survive power loss without a parent-dir fsync. write_mirror (vault.rs) DOES perform exactly this dir-fsync and its comment claims parity with 'the chunk store' — which was false. Failure scenario: client puts chunk C (bytes fsync'd, renamed, dir-entry NOT fsync'd) → commits a file referencing C (index WAL fsync'd, durable) → server acks → power loss → on reboot the index durably cites C but its dir-entry was lost → verify_and_gc flags the dangling ref → reindex → classify_missing finds C gone → the file is lost → reindex aborts unless force. An acked commit's content unrecoverable — exactly what R10-D1 exists to prevent. Medium confidence on the practical window (ext4 data=ordered often carries the rename durably as a side effect; POSIX gives no guarantee, and the code elsewhere treats the dir-fsync as required). Found by the round-2 audit (chunkstore critic), verified against the code. FIX: fsync the shard dir (best-effort, File::open(dir).sync_all()) after the rename in put(), matching write_mirror so the two paths truly agree. Severity Medium. discoveredInField=false."; :>> discoveredInField = false; :>> relatedTask = "postR2FunctionAudit"; :>> severity = Severity::Medium; }
    part issueReconcilePathStaleSize : Issue { :>> id = "c0f1a5cc-e022-4a10-9b20-a1b2c3d4e022"; :>> title = "reconcilePath fed the coalesce-stale queued size into the symmetric size gate → a grow-then-shrink/delete was skipped until the full scan"; :>> createdAt = "2026-07-18"; :>> createdBy = "wweatherholtz"; :>> description = "The engine's path coalescing deliberately keeps the LARGER of two queued sizes (R6 CONC: so a file that grew past the RAM/size cap between events isn't judged on a stale small size). But reconcilePath passed that queued localSize straight into reconcileOne's size gate, which is SYMMETRIC (localSize > max → skip). Failure scenario: a synced file is edited up past the cap (event {size:5GB}) then deleted/shrunk (event {size:0}), both queued before pump drains (e.g. during a long initial reconcile). Coalescing keeps 5GB; reconcilePath(path, 5GB) hits the gate and returns — the deletion/shrink is NOT propagated this pass and the stale base is left in place, even though the file on disk is now 0 bytes/absent. BOUNDED + self-healing: the periodic whole-vault reconcileAll re-stats every file from disk and propagates it with a fresh size, so the effect is DELAYED propagation (up to FULL_SCAN_INTERVAL_MS), not lost data; narrow trigger window. Found by the round-2 audit (drivers critic), verified against the code. FIX: reconcilePath refreshes the gate input from the live O(1) stat (d.localSizeOf) rather than trusting the queued hint — correct in BOTH directions, still no read. Fail-first regression: reconcile.test 'refreshes the size gate from the LIVE stat'. Severity Medium. discoveredInField=false."; :>> discoveredInField = false; :>> relatedTask = "postR2FunctionAudit"; :>> severity = Severity::Medium; }
    part issueScanStampBeforeWork : Issue { :>> id = "c0f1a5cc-e023-4a10-9b20-a1b2c3d4e023"; :>> title = "doReconcileAll marked the config/full scan windows done BEFORE the awaited scan → a mid-scan failure skipped re-arming it"; :>> createdAt = "2026-07-18"; :>> createdBy = "wweatherholtz"; :>> description = "main.ts doReconcileAll advanced lastConfigScanAt/lastFullScanAt to now up front, before await reconcileAll/reconcileDelta/reconcileLocalConfig. If any of those threw, the timestamps already claimed the scan happened, so a later poll wouldn't re-arm it — masked only because the throw routes to offline → doConnect, whose success re-stamps both; i.e. correctness leaned on the recovery path re-doing it rather than this function being self-consistent. Found by the round-2 audit (drivers critic), verified against the code. FIX: stamp the two windows AFTER the awaited scan completes, so a mid-scan failure leaves the window still due (the idle-poll early-return is only reached when NOT forced, so it correctly stamps nothing). Severity Low-Medium. discoveredInField=false."; :>> discoveredInField = false; :>> relatedTask = "postR2FunctionAudit"; :>> severity = Severity::Medium; }
    #Resolves dependency from postR2FunctionAudit to issueChunkPutNoDirFsync;
    #Resolves dependency from postR2FunctionAudit to issueReconcilePathStaleSize;
    #Resolves dependency from postR2FunctionAudit to issueScanStampBeforeWork;

    // ---- Mutation testing (D0030, 2026-07-18): cargo-mutants on shares.rs (the authz keystone,
    // highest criticality). 53 mutants; the one SURVIVING (MISSED) mutant is a real test-gap class. ----
    part issueSharesPersistNotTested : Issue { :>> id = "c0f1a5cc-e024-4a10-9b20-a1b2c3d4e024"; :>> title = "ShareStore's persist-on-change deletions (revoke/purge_vault/purge_user) were asserted only in-memory → a save()-skip mutant survived (dropped grants would reload after a restart)"; :>> createdAt = "2026-07-18"; :>> createdBy = "claudeOpus"; :>> description = "cargo-mutants on shares.rs (authz keystone) left ONE surviving mutant: shares.rs:161 `!=`→`==` in purge_user (its `if len != before { save() }` guard). Under the mutant, when grants ARE removed the guard reads false → save() is SKIPPED → the account-deletion purge lives only in memory; a restart reloads the .shares.json with the dropped grants intact — the exact 'dangling grant silently reactivates, re-exposing content to a prior grantee' hazard purge_vault's own comment warns about. The analogous save()-skip mutants on revoke (:119) and purge_vault (:153) landed in the run's 6 inconclusive timeouts (the first run's --timeout 120 was only ~1.25x the 96s baseline, so parallel contention tipped them over). ROOT CAUSE is a systemic TEST-gap class, not a code defect (the code correctly calls save()): every unit test for the three retain-then-save methods (revoke_removes_access_immediately, purge_vault_drops_only_that_vaults_grants, purge_user_drops_grants_as_owner_and_grantee) asserted against the LIVE in-memory store and never reopened from disk, so the durable-write step was untested for all three — a real fault there would have shipped undetected. FIX: three fail-first reopen-persistence tests (purge_user_persists_across_reopen / purge_vault_persists_across_reopen / revoke_persists_across_reopen) that open a fresh ShareStore from the same path after the mutating op and assert the grant stays gone — killing the MISSED mutant and the analogous save()-skip mutants across the whole class. Confirmed by a clean re-run (--timeout 300). Severity Medium (test-efficacy gap on the access-control persistence path; caught pre-release by mutation testing). discoveredInField=false."; :>> discoveredInField = false; :>> relatedTask = "mutationTestingSharesPass"; :>> severity = Severity::Medium; }
    #Resolves dependency from mutationTestingSharesPass to issueSharesPersistNotTested;

    // ---- Mutation testing (D0030, 2026-07-18): the durability core (index_store + chunkstore). ----
    part issueChunkstoreIndexTestGaps : Issue { :>> id = "c0f1a5cc-e025-4a10-9b20-a1b2c3d4e025"; :>> title = "The content/index durability core had mutation-surfaced test gaps in its error/validation/recovery paths (chunkstore) + the latent schema-migration stamp (index_store)"; :>> createdAt = "2026-07-18"; :>> createdBy = "claudeOpus"; :>> description = "cargo-mutants on index_store.rs + chunkstore.rs: 73 caught / 7 survivors / 9 unviable. index_store was already solid (1/42 viable survived = 97.6%); chunkstore's untested error/validation/recovery paths gave 6/38 (84.2%). Same META-pattern as the shares.rs pass — CODE is correct, the TESTS were blind to negative/error/recovery paths: (1) chunkstore sweep_temp (crash-leftover .tmp reclamation) had NO test; (2) is_valid_hash's len==64 && all-hex gate — a mutant weakening the && let a malformed hash slip past the format check to fail later as a content mismatch (untested — no negative put case); (3) get() swallowing a non-NotFound read error as 'chunk absent' (untested error-propagation — could mask a real IO/permission fault as a missing chunk); (4) touch()'s R16 orphan-clock reset (untested — a de-referenced-long-ago chunk could look instantly reclaimable, racing a concurrent re-referencing commit); (5) index_store migrate's R12-CC1 schema_version stamp — a latent guard the single-version schema never exercised, so a future migration's stamp was unverified. FIX: 6 killing tests (chunkstore: open_sweeps_leftover_temp_files, put_rejects_a_malformed_hash_as_a_format_error, get_propagates_non_notfound_read_errors, touch_resets_the_orphan_age_so_an_old_chunk_is_spared; index_store: migrate_stamps_a_stale_schema_version_up_to_current). Confirming re-run: 80 caught / 0 missed = 100% over viable. Severity Low (test-efficacy gaps on mostly best-effort/latent paths; no live defect; caught pre-release). discoveredInField=false."; :>> discoveredInField = false; :>> relatedTask = "mutationTestingIndexChunkstore"; :>> severity = Severity::Low; }
    #Resolves dependency from mutationTestingIndexChunkstore to issueChunkstoreIndexTestGaps;

    // ---- Mutation testing (D0030, 2026-07-18): vault.rs (the largest / most durability-critical module). ----
    part issueVaultRequestPathTestGaps : Issue { :>> id = "c0f1a5cc-e026-4a10-9b20-a1b2c3d4e026"; :>> title = "vault.rs request path (commit/delete/safe_rel_path) had mutation-surfaced test gaps: integrity (right-size/wrong-hash), idempotency, version-bump, and path-safety were untested for their exact predicates"; :>> createdAt = "2026-07-18"; :>> createdBy = "claudeOpus"; :>> description = "cargo-mutants on vault.rs (the largest module): 95 caught / 33 survivors / 10 unviable = 74.2% over viable — the least mutation-covered module. 8 survivors were on the LIVE per-commit/delete request path (code correct; tests blind to the exact predicate): safe_rel_path's front guard `is_empty() || contains('\\') || starts_with('/')` had no test for an empty/absolute input (path-safety); commit's `req.size > MAX_FILE_BYTES` size gate was only tested with u64::MAX (both == and >= mutants survived — an over-limit request rerouted to a later mismatch error, or an at-limit request wrongly rejected); commit's integrity check `len != size || hash != claimed` — weakening the || would accept a right-SIZE/WRONG-HASH body (corruption laundered into a committed, served file); commit's idempotent short-circuit `hash == req.hash && chunks == req.chunks` — weakening the && would freeze a stale chunk list on a same-hash re-chunk; commit + delete `new_version = self.version + 1` — a `+1`->`*1` mutant stalls the version so peers never see the change/tombstone. FIX: 5 fail-first tests (safe_rel_path_rejects_empty_backslash_and_absolute, commit_size_gate_is_strict_greater_than, commit_rejects_correct_size_but_wrong_hash, commit_idempotency_requires_both_hash_and_chunks_to_match, commit_and_delete_each_bump_the_version). Confirming re-run: 102 caught / 26 missed (the 26 = 21 documented equivalent/impractical accepts + 5 reindex corrupt-rebuild gaps, issueVaultReindexRebuildTestGaps). Severity Medium (integrity + version-monotonicity + path-safety on the live write path; caught pre-release by mutation testing; no live defect). discoveredInField=false."; :>> discoveredInField = false; :>> relatedTask = "mutationTestingVault"; :>> severity = Severity::Medium; }
    #Resolves dependency from mutationTestingVault to issueVaultRequestPathTestGaps;

    // OPEN (triaged to an outstanding follow-on): the 5 reindex corrupt-rebuild survivors are REAL gaps
    // (not equivalent), deferred because they need corruption-injection test scaffolding — honest open work.
    part issueVaultReindexRebuildTestGaps : Issue { :>> id = "c0f1a5cc-e027-4a10-9b20-a1b2c3d4e027"; :>> title = "vault.rs reindex corrupt-rebuild branches (prefer-store on missing chunk, version-preservation, history-floor raise) are untested — 5 mutation survivors"; :>> createdAt = "2026-07-18"; :>> createdBy = "claudeOpus"; :>> description = "5 vault.rs mutation survivors live in reindex's CORRUPT-rebuild path, which the existing (rich) reindex tests don't reach because they exercise the HEALTHY reindex (which short-circuits via the prefer-store branch BEFORE these): reindex:387 `&&`->`||` (a healthy reindex with a MISSING chunk must rebuild from disk, not keep the broken verbatim entry); reindex:412 x3 (`old.hash == hash` version-preservation on a corrupt rebuild — unchanged keeps its version, changed bumps); reindex:426 `&&`->`||` (raise history_floor ONLY when was_corrupt AND no tombstones). These are REAL gaps (not equivalent mutants) but need a corruption-injection test helper that forces was_corrupt=true with a populated old_files map. Deferred to mutationTestingVaultReindex (outstanding) rather than rushing fragile tests — an OPEN, honest gap, tracked not faked. Severity Low (a corrupt reindex is an operator-triggered repair path, not the live sync surface; the healthy path is well-covered). discoveredInField=false."; :>> discoveredInField = false; :>> relatedTask = "mutationTestingVaultReindex"; :>> severity = Severity::Low; }
    #Resolves dependency from mutationTestingVaultReindex to issueVaultReindexRebuildTestGaps;

    // =====================================================================
    // CRITIQUE R+1 (2026-07-18): a fresh 4-lens adversarial code critique by INDEPENDENT critics
    // (DI/durability, security/authz, concurrency, client-correctness) against the post-hardening code.
    // Every finding VERIFIED against the source before recording; the critics CLEARED the core ACL, path
    // safety, decide()/merge3, chunker, and DoS bounds. 2 client fixed (critiqueRPlus1ClientFixes, done);
    // 6 server findings triaged to critiqueRPlus1ServerHardening (OPEN). Lower/mitigated items (server
    // chunk read-verify — already backstopped by the client's download re-hash, issueDownloadIntegrity;
    // idle-eviction double-instance — implausible >600s op; client teardown timer nits — harmless
    // self-guarded no-ops) were considered and deprioritized, not filed.
    // =====================================================================
    // ---- client (fixed in critiqueRPlus1ClientFixes) ----
    part issueMassDeleteRemoteUnguarded : Issue { :>> id = "c0f1a5cc-e028-4a10-9b20-a1b2c3d4e028"; :>> title = "reconcileAll's bulk-delete guard was ASYMMETRIC: mass delete-REMOTE was unguarded, so a vanished LOCAL vault wiped the server fleet-wide"; :>> createdAt = "2026-07-18"; :>> createdBy = "claudeOpus"; :>> description = "CLIENT-1 (HIGH, data loss). The bulk-delete protection (guardBulkDelete via runDeleteGuard + DeleteRateGuard) was computed from wouldDelete = basePaths.filter(!remote.has(p) && local.has(p)) — ONLY delete-LOCAL candidates — and checked ONLY in reconcileOne's delete-local branch. The delete-remote branch had just the per-file confirmedAbsent probe, no bulk guard. confirmedAbsent catches a placeholder/unreadable listing but NOT a genuine mass local loss (cloud de-hydration, a partial backup restore, cleared storage): every file is truly absent, so each becomes an unbounded d.api.deleteFile → the whole server vault is deleted and tombstoned fleet-wide, then delete-local'd on every peer. The DI-1 bulk-delete hardening only covered the mirror (server-lost-files) direction. FIX: compute wouldDeleteRemote (accepted base paths gone locally but present+unchanged on the server, r.hash===base.hash) and gate the delete-remote branch on a symmetric isSuspiciousBulkDelete(basePaths.length, wouldDeleteRemote, false) — ratio + BULK_DELETE_MIN floor, NO empty-local override (an empty local vault can be a legit last-file delete, unlike an empty server manifest). Fail-first tests: a 10-file vault that vanishes is guarded (server intact); a single-file delete still propagates. Severity High. discoveredInField=false (critique pass, pre-release)."; :>> discoveredInField = false; :>> relatedTask = "critiqueRPlus1ClientFixes"; :>> severity = Severity::High; }
    part issueMergePushReReadLoss : Issue { :>> id = "c0f1a5cc-e029-4a10-9b20-a1b2c3d4e029"; :>> title = "pushBytes re-read the file from disk after writing merged bytes, so a racing local save was committed in place of the merge — silently dropping the remote edit"; :>> createdAt = "2026-07-18"; :>> createdBy = "claudeOpus"; :>> description = "CLIENT-2 (Medium, silent merge loss). pushBytes did io.write(mergedBytes) then pushFile, which RE-READ the file from disk (io.read) to chunk+commit. A user save landing in the write->read gap made pushFile commit the RACED content (local edit but NOT the remote edit the 3-way merge folded in) under the same server version (CAS doesn't protect — server didn't advance), setting base to it. DI-5 fixed base CONSISTENCY (text/hash agree) but not this LOSS of the merge result. Scenario: base 'L0\\nR0'; peer→'L0\\nR1', user→'L1\\nR0'; merge3→'L1\\nR1'; pushBytes writes it; user saves 'L1\\nR0-edited' in the gap; pushFile commits that → the peer's R1 edit is gone fleet-wide. FIX: a shared commitBytes(ctx,path,bytes) core commits the IN-HAND bytes (no re-read); pushBytes writes to disk for local persistence then commits the merged bytes it holds, so a racing save is caught as a fresh local edit on the NEXT reconcile (local != base=merged → push/merge) instead of overwriting the merge. Fail-first test: pushBytes commits the exact bytes given, not the raced re-read. Severity Medium. discoveredInField=false."; :>> discoveredInField = false; :>> relatedTask = "critiqueRPlus1ClientFixes"; :>> severity = Severity::Medium; }
    #Resolves dependency from critiqueRPlus1ClientFixes to issueMassDeleteRemoteUnguarded;
    #Resolves dependency from critiqueRPlus1ClientFixes to issueMergePushReReadLoss;
    // ---- server (OPEN; triaged to critiqueRPlus1ServerHardening) ----
    part issueFoldBackfillAsciiOnly : Issue { :>> id = "c0f1a5cc-e02a-4a10-9b20-a1b2c3d4e02a"; :>> title = "index_store.migrate backfills the fold column with SQLite ASCII-only lower(), but the write path + colliding_key use Rust Unicode to_lowercase() → the case-collision guard misses legacy non-ASCII rows"; :>> createdAt = "2026-07-18"; :>> createdBy = "claudeOpus"; :>> description = "DI-1 (Medium). Healing a pre-fold DB backfills fold via `UPDATE files SET fold = lower(path)` (index_store.rs:100) — SQLite's bundled lower() is ASCII-ONLY — while every other producer/consumer uses Rust to_lowercase() (full Unicode): the write path (:154) and colliding_key's probe (:298-299). The comment at :291-295 even documents SQLite lower() is ASCII-only, so the backfill introduces exactly the write-path/guard drift :147-148 warns is 'a silent collision-guard hole'. Failure: an upgraded pre-fold DB holds 'CAFÉ.md'; migrate sets its fold='cafÉ.md' (É untouched). A later commit of 'café.md' probes fold='café.md' → no match → collision NOT detected → two keys folding to one file → on a case-insensitive client FS they collapse (PROTO-4/DI-R5 phantom-delete + overwrite churn). Narrow (needs an upgraded pre-fold DB with a non-ASCII-uppercase path never re-committed). FIX: backfill per-row in Rust with to_lowercase() (re-derive fold in migrate using the same fold as everywhere else). The existing migrate_heals test uses only ASCII 'A.md' so it can't catch this — add a non-ASCII case. Severity Medium. discoveredInField=false."; :>> discoveredInField = false; :>> relatedTask = "critiqueRPlus1ServerHardening"; :>> severity = Severity::Medium; }
    part issueShareLinkRemanence : Issue { :>> id = "c0f1a5cc-e02b-4a10-9b20-a1b2c3d4e02b"; :>> title = "Share-LINKS survive vault/account deletion (only grants are purged), so a no-expiry link re-grants access across a delete+recreate boundary — the R17 remanence hole reopened for the link layer"; :>> createdAt = "2026-07-18"; :>> createdBy = "claudeOpus"; :>> description = "SEC-1 (Medium). purge_vault/purge_user_data (state.rs:257-287) and users_delete (admin.rs) meticulously drop share GRANTS (shares.purge_vault/purge_user, R17 — so a recreated same-name vault can't reactivate a grant) but NEVER touch .share-links.json; ShareLinkStore::open has no expiry sweep and links can be created with ttl=0 (no expiry); share_link_redeem mints the grant with no re-check that the owner still exists/owns the vault. Exploit: Alice creates a no-expiry ReadWrite link for alice/notes, hands/leaks the token, deletes vault notes (grants revoked — she reasonably believes access died), later recreates a vault named notes; Bob redeems the still-valid link → g.grant('alice','notes',bob,ReadWrite) → access to the recreated vault. Same across account delete + admin recreation of the username. FIX: add purge_links_for_vault(owner,vault) + purge_links_for_user(user) to ShareLinkStore, call them from the purge paths (mirror the shares.purge_* calls); add an open-time expiry sweep (parity with the tokens R22 sweep). Severity Medium. discoveredInField=false."; :>> discoveredInField = false; :>> relatedTask = "critiqueRPlus1ServerHardening"; :>> severity = Severity::Medium; }
    part issueVaultDeleteOpenRace : Issue { :>> id = "c0f1a5cc-e02c-4a10-9b20-a1b2c3d4e02c"; :>> title = "Vault::open's create_dir_all resurrects a just-deleted vault when it races a concurrent open past vault_exists()"; :>> createdAt = "2026-07-18"; :>> createdBy = "claudeOpus"; :>> description = "CONC-1 (Medium). state.rs vault() does NOT re-check existence — it unconditionally calls Vault::open, whose create_dir_all(vault_dir) (vault.rs:165) re-creates the tree. scoped() (api.rs) checks vault_exists() THEN spawn_blocking(st.vault()). Interleaving: request B passes vault_exists()==true, then its Vault::open create_dir_all runs AFTER request A's purge_vault remove_dir_all → the directory reappears empty and B caches a fresh empty VaultHandle → a just-deleted vault silently returns as an empty vault that vault_exists() now reports present (the server's delete is effectively undone; client empty-manifest guards prevent local data loss, but the delete didn't stick). FIX: serialize delete against open — hold the per-key opens lock across the purge (so no Vault::open runs for the key during teardown), and/or a 'deleting' tombstone set vault() consults before create_dir_all. Severity Medium. discoveredInField=false."; :>> discoveredInField = false; :>> relatedTask = "critiqueRPlus1ServerHardening"; :>> severity = Severity::Medium; }
    part issuePurgeDirNotBestEffort : Issue { :>> id = "c0f1a5cc-e02d-4a10-9b20-a1b2c3d4e02d"; :>> title = "purge_vault/purge_user_data comment 'best-effort on the dir' but use remove_dir_all(&dir)? — a Windows file lock leaves a grants-purged half-state 500; users_delete also removes the user row before purging shares"; :>> createdAt = "2026-07-18"; :>> createdBy = "claudeOpus"; :>> description = "CONC-2 + SEC-3 (Low). state.rs:266 (purge_user_data) and :285 (purge_vault) both comment 'Best-effort on the dir' yet `std::fs::remove_dir_all(&dir)?` PROPAGATES the error. Any in-flight request for the vault holds a live SqliteIndex with .sync-index.db open; on Windows an open file is locked, so remove_dir_all Errs → grants already purged + ns handle evicted, but the dir/data remain and the call 500s (a retryable half-state, contradicting the comment; the deliberate 'no half-state' reasoning at :277-280 covers only the poisoned-lock case, not a dir-fail after the grant purge). Separately (SEC-3) admin.rs users_delete removes the user ROW (users.remove) BEFORE shares.purge_user, so a purge failure there leaves dangling GRANTEE grants a recreated same-name account re-inherits (access to others' shared vaults). FIX: make the dir removal genuinely best-effort (log, don't ?), and order users_delete's shares.purge_user (+ the link purge from issueShareLinkRemanence) BEFORE users.remove. Severity Low. discoveredInField=false."; :>> discoveredInField = false; :>> relatedTask = "critiqueRPlus1ServerHardening"; :>> severity = Severity::Low; }
    part issueMfaDisableNoThrottle : Issue { :>> id = "c0f1a5cc-e02e-4a10-9b20-a1b2c3d4e02e"; :>> title = "/api/mfa/disable has no brute-force throttle, defeating its 'a stolen session token alone can't strip the factor' guarantee (±1-step TOTP window = 3/10^6 per try, unbounded)"; :>> createdAt = "2026-07-18"; :>> createdBy = "claudeOpus"; :>> description = "SEC-2 (Low). The login path is per-account rate-limited (auth.rs:81 login_throttle), but mfa.rs:58 disable has NO throttle. totp_verify_second_factor mutates state only on SUCCESS (failed guesses are free) and verify_step accepts a ±1-step window (3 valid codes / 10^6). A holder of a valid/stolen session token can hammer disable at ~3/10^6 success/request, ~10^5-10^6 requests (minutes) to strip MFA — the doc comment (mfa.rs:4,56) explicitly promises a token alone can't do this. Lower severity: the attacker already holds a session token; MFA's residual value is post-revocation/re-login protection (and under REQUIRE_ADMIN_MFA, disabling an admin's MFA is self-defeating since require_admin needs totp_enabled). FIX: run disable (and confirm) through login_throttle.check/fail keyed on the user, matching the login second-factor path. Severity Low. discoveredInField=false."; :>> discoveredInField = false; :>> relatedTask = "critiqueRPlus1ServerHardening"; :>> severity = Severity::Low; }
    part issueVersionEpochRewind : Issue { :>> id = "c0f1a5cc-e02f-4a10-9b20-a1b2c3d4e02f"; :>> title = "The version counter lives only in the corruptible index and REWINDS on a quarantine/empty rebuild; history_floor is set BELOW already-synced client cursors, so the RC-1 conservative-reconcile never engages"; :>> createdAt = "2026-07-18"; :>> createdBy = "claudeOpus"; :>> description = "DI-3 (Medium). `version` lives only in the index meta table (index_store.rs:66-68 seeds 1 on a fresh/quarantined DB; vault.rs:185-189 quarantine→fresh). reindex rebuilds file versions from self.version (=1 after quarantine) up to max_version≈file count, then sets history_floor=max_version (vault.rs:411-429). For an active vault the pre-crash version M (total commits+deletes over its life) far exceeds the post-rebuild N≈file count, so M>>N is the COMMON outcome. A client synced at cursor M polls changes(since=M): gets version=N<M, empty upserts/deletes, history_floor=N. Per the floor semantics (only a client BELOW the floor reconciles conservatively) the client (cursor M>N) does NOT — a violated monotonicity invariant with no signal it can act on; the mechanism relied on for RC-1 is inert for the common rewind. Precise client-visible outcome depends on plugin reconcile (the client's version-rewind full-reconcile, issueVersionRewindPin, likely mitigates in practice — cross-check), but the server-side monotonicity break is certain. FIX: persist a monotonic high-water version OUTSIDE the corruptible index (a small fsync'd sidecar, bumped each commit) and seed the rebuilt index from it, so version never rewinds and the floor's below-floor semantics hold. Severity Medium. discoveredInField=false."; :>> discoveredInField = false; :>> relatedTask = "critiqueRPlus1ServerHardening"; :>> severity = Severity::Medium; }
    #Resolves dependency from critiqueRPlus1ServerHardening to issueFoldBackfillAsciiOnly;
    #Resolves dependency from critiqueRPlus1ServerHardening to issueShareLinkRemanence;
    #Resolves dependency from critiqueRPlus1ServerHardening to issueVaultDeleteOpenRace;
    #Resolves dependency from critiqueRPlus1ServerHardening to issuePurgeDirNotBestEffort;
    #Resolves dependency from critiqueRPlus1ServerHardening to issueMfaDisableNoThrottle;
    #Resolves dependency from critiqueRPlus1ServerHardening to issueVersionEpochRewind;

    // =====================================================================
    // DESIGN-PATTERN CONFORMANCE CRITIQUE (2026-07-19): 5 independent critics evaluated the 27
    // pattern-tagged CodeElements against their declared pattern (findings VERIFIED against the code).
    // The pure cores are exemplary (decide/mapPool/safe_rel_path/validateStatus/the serialized actor);
    // the gaps are (1) a real validation DEFECT, (2) bool-predicates that should be refined types,
    // (3) shells that still decide, (4) the sync FSMs orphaned + several IMPLICIT FSMs, (5) mislabeled
    // tags. Triaged to 3 OPEN follow-on actions (implement later, per the owner). "we'll implement in a bit."
    // =====================================================================
    part issueValidateFileMetaMtimeUnchecked : Issue { :>> id = "c0f1a5cc-e030-4a10-9b20-a1b2c3d4e030"; :>> title = "validateFileMeta asserts mtime:number in its return type but never validates it — a hostile server's non-numeric mtime passes and flows into base stat-stamping"; :>> createdAt = "2026-07-19"; :>> createdBy = "claudeOpus"; :>> description = "DEFECT (Medium), surfaced by the parse-don't-validate conformance critic + VERIFIED. protocol.ts:49-57 validateFileMeta validates path/hash/size/version (asStr/asNum) + chunks (string[]) but has NO check for mtime, then returns `o as FileMeta` (line 56) — the FileMeta type (protocol.ts) asserts mtime:number. So a malformed/hostile server response with mtime:'evil' / NaN / missing passes validation and is cast to FileMeta; mtime flows into live base stat-stamping (reconcile localStat/stampStat paths). The exact parse-don't-validate hazard: the refined type promises a property the parser doesn't establish. Contrast validateStatus (protocol.ts:61-72), which CONSTRUCTS a fresh normalized value (the true exemplar). FIX: add asNum(m.mtime, 'mtime') and construct-don't-cast (build + return a fresh FileMeta). Severity Medium (untrusted-input validation hole; the client already re-hashes downloaded CONTENT so this is metadata-integrity, not content-loss). discoveredInField=false (critique)."; :>> discoveredInField = false; :>> relatedTask = "patternConformanceHardening"; :>> severity = Severity::Medium; }
    part issueBoolPredicatesNoRefinedType : Issue { :>> id = "c0f1a5cc-e031-4a10-9b20-a1b2c3d4e031"; :>> title = "Security bool-predicates (safe_name / isSafeVaultPath / isInsecureRemote) return bool not a refined type, forcing the checked property to be re-asserted at ~20 / 5 / 4 call sites (parse-don't-validate gap)"; :>> createdAt = "2026-07-19"; :>> createdBy = "claudeOpus"; :>> description = "parse-don't-validate conformance critic (verified). The weakness clusters in bool safety-predicates whose un-typed result forces defensive re-checking everywhere — exactly what the pattern eliminates: (1) safe_name (users.rs:28-37) is re-checked at ~20 call sites (admin.rs x10, state.rs x7, api.rs/vaults.rs/ws.rs/auth.rs) and DOUBLE-checked on the register write-path (auth.rs:136 then users.rs:133; state.rs:272 even comments 'the admin route already validated; defensive') — a name that reaches the FS as a path segment relies on every site remembering to call it; highest ROI. (2) isSafeVaultPath (pathsafe.ts:14-32) re-checked at 5 client I/O sites (main.ts write/read/exists/write/remove). (3) isInsecureRemote (connstr.ts:21-27) independently re-parses the raw URL via new URL() at 4 transport.ts sites, alongside (not consuming) normalizeServer's parse — shotgun parsing. FIX: a SafeName newtype (only ctor parses) taken by store keys/ns_dir/handlers; a branded SafeVaultPath taken by VaultIo read/write/remove (unchecked path → compile error); fold the insecure verdict into a refined ServerOrigin from normalizeServer. safe_rel_path (vault.rs, Option<PathBuf>, canonical round-trip, result trusted) is the reference parser to model on. Severity Medium (security-relevant reliance on human vigilance; no present bug). discoveredInField=false."; :>> discoveredInField = false; :>> relatedTask = "patternConformanceHardening"; :>> severity = Severity::Medium; }
    part issueFunctionalCoreShellsReDecide : Issue { :>> id = "c0f1a5cc-e032-4a10-9b20-a1b2c3d4e032"; :>> title = "The reconcile shells (reconcileOne/reconcileMergeOrConflict/reconcilePath) carry still-pure decision logic that should be lifted into explicit pure values (functional-core boundary too narrow)"; :>> createdAt = "2026-07-19"; :>> createdBy = "claudeOpus"; :>> description = "functional-core/imperative-shell conformance critic (verified). decide() is an EXEMPLARY pure total truth table (purity deliberately protected via requireRemote). But the three shells re-decide: (1) reconcileOne (reconcile.ts:780-947) delegates the 3-way call to decide() then adds a SECOND layer of largely-pure decision logic in the shell — config re-adjudication (848-858), delete gating on hasTombstone/guardDelete/guardRemoteDelete (897,910,921,929), size gate (792-798). Lift into a pure finalize(action, facts)→Effect (resolve confirmedAbsent/exists to booleans in the shell first); the switch then only executes Effects. (2) reconcileMergeOrConflict (700-760) uses the pure kernels (merge3/sameIgnoringEol/isMergeable) but interleaves outcome selection with I/O (partly inherent) — compute a pure MergePlan value, shell executes writes. (3) reconcilePath (617-657) inlines the delete-guard denominator/wouldDelete (626-641), duplicating runDeleteGuard (220-226, the B1 drift) — extract a shared perPassDeleteGuard(d, manifest) helper used by all three entry points. Net: widen the property-testable pure boundary. Severity Medium (design/testability; no correctness bug). discoveredInField=false."; :>> discoveredInField = false; :>> relatedTask = "patternConformanceHardening"; :>> severity = Severity::Medium; }
    part issueStateMachineOrphanedAndImplicit : Issue { :>> id = "c0f1a5cc-e033-4a10-9b20-a1b2c3d4e033"; :>> title = "The 2 tagged sync FSMs are correct but DEAD (only the test uses them); the live operational machine is a hybrid, and ~4 IMPLICIT FSMs (WS lifecycle, engine, reconcile-mode, config-adjudication) are boolean-soup that should be explicit"; :>> createdAt = "2026-07-19"; :>> createdBy = "claudeOpus"; :>> description = "actor/state-machine conformance critic (verified by grep + read). This answers 'why only 2 state machines?': (a) syncstate::transition + SyncMachine (syncstate.ts) are CORRECT total (State,Event)→State machines but ORPHANED — imported only by client/test/syncstate.test.ts; the operational machine migrated to syncengine.ts, whose header says the old FSM 'only ever drove the status LIGHT'. So the 2 tagged FSMs model nothing live. (b) The LIVE engine (SyncEngine, syncengine.ts) is a HYBRID: an explicit EngineState enum + 3 aux booleans (connected/retrying/running) + IMPERATIVE transitions in handle() — not a total transition table. (c) IMPLICIT FSMs that should be explicit, by value: D1 WS/transport lifecycle (main.ts spinUpWs/startWsLiveness/close-handler — realtimeConnected/opened/`ws!==ws`/poll-cadence/wsLivenessTimer encode no-socket/dialing/open/half-open-stale/closed-redial/closed-reconnect, with a documented history of race patches CONC-R2#4/#6/CONC-R3#1/R11#7 → strongest case for an explicit TransportState machine); D4 the engine hybrid; D2 doReconcileAll scan-mode (4 booleans → 4 modes); D3 config-path adjudication (array-membership-as-state). The (serialized-actor) SyncEngine.pump/handle ARE strong (real queue, run-to-completion, owned state) — the FSM issue is the transition MODELING, not the actor. Resolve via stateMachineConsolidation (delete-or-reunify the orphans; make the implicit machines explicit, model = decide()). Severity Medium (clarity/testability + a race-patch-prone lifecycle; no present bug). discoveredInField=false."; :>> discoveredInField = false; :>> relatedTask = "stateMachineConsolidation"; :>> severity = Severity::Medium; }
    part issuePatternTagsMislabeled : Issue { :>> id = "c0f1a5cc-e034-4a10-9b20-a1b2c3d4e034"; :>> title = "5 CodeElement design-pattern tags are mislabeled/overstated (+ a stale design-patterns.md exemplar claim) — the registry's own honesty"; :>> createdAt = "2026-07-19"; :>> createdBy = "claudeOpus"; :>> description = "Cross-cutting registry-accuracy finding from the conformance critics (verified). Five `pattern` tags don't match what the code does: ceContentStorePut is tagged singleWriter but is deliberately NOT single-writer (content-addressed immutable store; concurrent same-hash puts are safe by construction) → content-addressed-immutable; ceResolveConfigConflict is tagged command but reifies nothing (a direct async fn branching on a choice discriminant) → strategy; ceSharesAuthorized is tagged makeIllegalStatesUnrepresentable but is a runtime bool decision (the illegal state IS representable) → functionalCore/fail-closed-authz (only the Perm/Access two-enum split is a real make-illegal win); ceMergeEnabledPlugins tagged makeIllegalStatesUnrepresentable but the grow-only invariant is an algorithmic Set-union over string→string, not type-enforced → functionalCore+parseDontValidate; ceIsolatedPass tagged boundedPool but its bound is delegated to mapPool/FILE_CONCURRENCY → error-isolation-loop. Plus a DOC drift: .engine/docs/design-patterns.md:15 cites validateChanges/validateFileMeta as parseDontValidate exemplars, but both cast-not-construct and validateFileMeta has the mtime hole (issueValidateFileMetaMtimeUnchecked) — the true exemplars are safe_rel_path + validateStatus. Correcting these (with a DesignPattern enum extension where needed) keeps the descriptive-tag registry trustworthy. Severity Low (accuracy; the tags are descriptive). discoveredInField=false."; :>> discoveredInField = false; :>> relatedTask = "patternRegistryReview"; :>> severity = Severity::Low; }
    part issueUntaggedElementsPatternReview : Issue { :>> id = "c0f1a5cc-e035-4a10-9b20-a1b2c3d4e035"; :>> title = "The 142 untagged CodeElements (pattern=none) were never reviewed for a pattern they SHOULD follow — likely under-counting FSMs and other proven shapes"; :>> createdAt = "2026-07-19"; :>> createdBy = "wweatherholtz"; :>> description = "Owner-raised (2026-07-19): only 27 of 169 CodeElements carry a design pattern and only 2 are state machines, which under-counts given how much of the code is 'functions that operate over pieces of data and decide what state is represented' — FSMs fit that shape strongly. The `pattern` tag was applied opportunistically during the audit, so most elements read `none` without a deliberate check for whether a proven pattern APPLIES. ACTION: pass over the 142 untagged elements (pattern=none / no attr) and tag where a pattern SHOULD apply, recognizing the recurring SHAPE — state+events→decision ⇒ FSM; untrusted-input→trusted-downstream ⇒ parseDontValidate; concurrent-mutation ⇒ singleWriter; pure-decision-over-inputs ⇒ functionalCore — NOT just accepting `none`. A pattern earns a tag when the code REPEATEDLY solves the problem the pattern names (that is why they are 'patterns' — strong, proven answers to recurring shapes). Seeded by the implicit FSMs the conformance critique already surfaced (issueStateMachineOrphanedAndImplicit: the WS-lifecycle, engine, reconcile-mode, config-adjudication machines). The output raises the tagged-pattern coverage honestly + feeds stateMachineConsolidation. Severity Low (registry completeness / design insight). discoveredInField=false."; :>> discoveredInField = false; :>> relatedTask = "patternRegistryReview"; :>> severity = Severity::Low; }
    #Resolves dependency from patternConformanceHardening to issueValidateFileMetaMtimeUnchecked;
    #Resolves dependency from patternConformanceHardening to issueBoolPredicatesNoRefinedType;
    #Resolves dependency from patternConformanceHardening to issueFunctionalCoreShellsReDecide;
    #Resolves dependency from stateMachineConsolidation to issueStateMachineOrphanedAndImplicit;
    #Resolves dependency from patternRegistryReview to issuePatternTagsMislabeled;
    #Resolves dependency from patternRegistryReview to issueUntaggedElementsPatternReview;

    // =====================================================================
    // UNTAGGED PATTERN REVIEW executed 2026-07-19 (7 independent reviewers over the 142 untagged
    // CodeElements). Outcome: 56 already-conform tags APPLIED to the registry (tagged 27→83); the
    // audit had badly under-counted proven patterns (store writes=singleWriter, boundary parsers=
    // parseDontValidate, pure cores=functionalCore, the HTTP adapter, RAII guards, the serialized
    // actor, the UI templateMethod modals). Reviewers correctly declined to force-fit (login flow,
    // LoginThrottle, thin handlers, GC helpers = honest `none`). The SHOULD-ADOPT findings below are
    // the refactor work the review surfaced (recorded, implement later). The mislabel retags + the
    // doc fix remain under patternRegistryReview (some need a DesignPattern enum extension → a CR).
    // =====================================================================
    part issueVaultLifecycleImplicitFsm : Issue { :>> id = "c0f1a5cc-e036-4a10-9b20-a1b2c3d4e036"; :>> title = "Vault's corrupt + dangling_recovery bool pair is an IMPLICIT lifecycle FSM (Ok/Corrupt/DanglingRecovery) that can even represent an illegal state — should be an explicit enum VaultState"; :>> createdAt = "2026-07-19"; :>> createdBy = "claudeOpus"; :>> description = "Surfaced by the untagged-pattern review (server-durability reviewer, verified). Vault carries the lifecycle as TWO booleans — corrupt + dangling_recovery (vault.rs) — driven by open()→verify_and_gc()→reindex() and read by api::ensure_ready. The states are Ok / Corrupt[unreadable | empty-with-data] / DanglingRecovery[intact index, missing blob], plus an Unsupported→hard-refuse exit. The bool PAIR can represent the ILLEGAL combo (corrupt=false, dangling_recovery=true), and the transitions are imperative flag-sets across three methods. This is a genuine implicit state machine (distinct from the client sync-lifecycle FSMs in issueStateMachineOrphanedAndImplicit — this one is server durability). FIX: replace the pair with an `enum VaultState { Ok, Corrupt, DanglingRecovery }` (makeIllegalStatesUnrepresentable), with verify_and_gc/reindex as total guarded transitions and ensure_ready reading the enum exhaustively — modeled on decide()'s enumerated table. Folds into stateMachineConsolidation (which broadens to sync + vault lifecycle FSMs). Severity Medium (clarity + an illegal representable state; no present bug — the flags are set correctly today). discoveredInField=false."; :>> discoveredInField = false; :>> relatedTask = "stateMachineConsolidation"; :>> severity = Severity::Medium; }
    part issuePatternUntaggedShouldAdopt : Issue { :>> id = "c0f1a5cc-e037-4a10-9b20-a1b2c3d4e037"; :>> title = "Untagged-review should-adopt refactors: ChunkHash newtype, conflictCopyIfRaced discriminated union, parseSettings boundary, release_open_lock Drop guard, audit action/outcome newtypes"; :>> createdAt = "2026-07-19"; :>> createdBy = "claudeOpus"; :>> description = "The untagged-pattern review (7 reviewers, verified) found a handful of elements whose SHAPE fits a proven pattern but that implement it messily — refactor targets (each with a fail-first/behavior-preserving test when done): (1) chunkstore::is_valid_hash — a bool validator re-run in has/get/remove/touch/put; a `ChunkHash` newtype parsed ONCE at the boundary makes the raw &str hash unrepresentable downstream (parseDontValidate/newtype). (2) reconcile.ts::conflictCopyIfRaced — returns `string|null` but smuggles a MAGIC sentinel (' config-race', a leading-NUL non-path) through the path-valued channel; a discriminated union `{kind:'copy';path} | {kind:'config-race'} | null` precludes a caller conflating the marker with a real copy path (makeIllegalStatesUnrepresentable). (3) main.ts::loadSettings — hardens untrusted data.json at the boundary but ad-hoc (Object.assign + per-field Array.isArray); formalize a `parseSettings(raw): SelfSyncSettings` parser (parseDontValidate). (4) state.rs::release_open_lock — manually reaped on EVERY vault()/purge_vault return path (4+ sites, easy to forget); a Drop-based guard removes the release-on-all-exits hazard (raiiGuard) — note the reap is strong_count-based so the Drop needs the same check (low-confidence). (5) audit.rs — action/outcome 'closed catalogs' are &str consts, so the signature accepts arbitrary strings; newtypes/enums would enforce the catalog (newtype/makeIllegalStatesUnrepresentable, low). Severity Low (design/clarity; no present bugs). discoveredInField=false."; :>> discoveredInField = false; :>> relatedTask = "patternConformanceHardening"; :>> severity = Severity::Low; }
    #Resolves dependency from stateMachineConsolidation to issueVaultLifecycleImplicitFsm;
    #Resolves dependency from patternConformanceHardening to issuePatternUntaggedShouldAdopt;

    // ===== Release-discipline blind spot (surfaced 2026-07-19 when the owner questioned why 99 commits
    // sat unreleased despite the D0012 release-verify guard). D0047: logged as a tracked Issue + slated for
    // a permanent automated control (releaseCurrencyGuard; the guard itself is a process CHANGE pending a
    // Change-Request Decision + acceptance). =====
    part issueStatusLightFlicker : Issue { :>> id = "c0f1a5cc-e039-4a10-9b20-a1b2c3d4e039"; :>> title = "Status light flits 'Fully synced' <-> 'Syncing... checking for changes' ~1x/sec — a transient reconcile (a check) is painted as a STATE (UX/human-factors defect)"; :>> createdAt = "2026-07-28"; :>> createdBy = "wweatherholtz"; :>> description = "Owner-reported on a real device: the status light oscillates between 'Fully synced' and 'Syncing... checking for changes' about once a second. Root cause: a routine poll / config re-hash / path event flips the engine phase idle->syncing(syncPending=0)->idle in well under a second, and statusDisplay (main.ts:965) paints syncing-with-0-pending as 'Syncing... checking for changes' — so a transient CHECK is rendered as a STATE ('checking for changes is a state transition, not a state'). FIX: a debounced DISPLAY fsm (statuslight.ts) distinct from the engine FSM — the visible 'Syncing...' state requires syncPending>0 AND persistence past a short debounce, so a 0-pending or sub-second reconcile never paints and the light holds its steady state; 'checking for changes' is removed from statusDisplay; a render-dedupe skips identical repaints. Pure reducer + unit tests; behaviour otherwise unchanged. Severity Low (cosmetic/human-factors; no data effect). discoveredInField=true (owner, real device — the first field-discovered issue vs the critique-found set)."; :>> discoveredInField = true; :>> relatedTask = "statusLightFlickerFsm"; :>> severity = Severity::Low; }
    part issueReleaseCurrencyBlindSpot : Issue { :>> id = "c0f1a5cc-e038-4a10-9b20-a1b2c3d4e038"; :>> title = "check-release/verify-released (D0012) only assert the MANIFEST's version is released — unreleased SHIPPABLE commits piling up on main (manifest left at an already-released version) are invisible"; :>> createdAt = "2026-07-19"; :>> createdBy = "wweatherholtz"; :>> description = "The owner asked why 99 commits had accumulated on main since 1.6.0 with no release, despite D0012 adding check-release.mjs + verify-released.yml specifically to make 'released' a checkable assertion. Root cause: those checks assert only that MANIFEST.json's version has a matching tag + published GitHub release — a condition SATISFIED the entire time, because the manifest sat at 1.6.0 (which WAS released) while main drifted 99 commits (48 of them touching shippable client/server/manifest paths; 52 engine/tracking/docs-only) past it. So D0012 catches 'bumped-but-never-tagged' (the 0.10.4 miss) but is BLIND to 'never-bumped-so-work-accrues-unreleased' — a distinct drift. This violated D0002 ('every coherent set of committed, green changes ships as a version increment') for ~a week across the mutation/critique/pattern sittings, undetected. FIX (releaseCurrencyGuard): a repo-local scripts/check-release-currency.mjs (mirroring D0012's out-of-keel-scope pattern) that counts main commits since the last release tag touching SHIPPABLE paths only (so tracking/engine/docs commits don't false-positive), WARNs at >=1 and FAILs past a threshold, wired into verify-released.yml. Severity Medium (a process-control gap that already caused a real week-long release lapse; no user-facing defect). discoveredInField=false."; :>> discoveredInField = false; :>> relatedTask = "releaseCurrencyGuard"; :>> severity = Severity::Medium; }
    #Resolves dependency from releaseCurrencyGuard to issueReleaseCurrencyBlindSpot;
    #Resolves dependency from statusLightFlickerFsm to issueStatusLightFlicker;

    // ===== Embedded-timestamp conflict noise (owner-reported field pain, 2026-07-29). D0077: triaged to
    // the embeddedTimestampMetadata sprint as its resolver. =====
    part issueTimestampConflictNoise : Issue { :>> id = "d7c18001-0000-4a10-9b20-a1b2c3d40081"; :>> title = "Sync raises conflicts/merges for timestamp-only frontmatter differences — the whole file is hashed, so any updated: bump reads as a content change"; :>> createdAt = "2026-07-29"; :>> createdBy = "wweatherholtz"; :>> description = "Owner-reported on real devices: 'wayy too many diff conflicts that are just time metadata with no file changes otherwise.' Root cause: change detection hashes the ENTIRE file byte-for-byte (reconcile.ts sha256hex), frontmatter included, with zero frontmatter awareness — so when a note's embedded modified/created timestamp differs across devices (a copy, a re-open, or an editor-event plugin re-stamp) while the body is identical, the hashes differ and decide() routes it to merge / conflict-copy. FIX (embeddedTimestampMetadata sprint): SelfSync owns the updated/created fields and compares by a NORMALIZED content hash that masks the managed timestamp keys (git-model content-addressing), so a timestamp-only difference is a non-event; a spurious local bump is reverted-not-pushed, and a genuine timestamp-only cross-device diff auto-resolves keeping the older updated / earliest created — no conflict copy. Severity Medium (no data loss, but a chronic false-conflict UX defect). discoveredInField=true (owner, real devices)."; :>> discoveredInField = true; :>> relatedTask = "embeddedTimestampMetadata"; :>> severity = Severity::Medium; }
    #Resolves dependency from embeddedTimestampMetadata to issueTimestampConflictNoise;

    // Deferred findings from the pre-release 3-lens adversarial critique of embeddedTimestampMetadata
    // (independent critics, 2026-07-29). The ship-blockers (F1 non-md corruption, F2 cross-device churn,
    // F3 created=now on the edit path, F4 CRLF, F5 quoted dates) were fixed before release; these four
    // lower-severity items are deferred to a v-next hardening pass. Triaged to embeddedTimestampHardening.
    part issueTimestampHardeningFollowups : Issue { :>> id = "d7c18002-0000-4a10-9b20-a1b2c3d40082"; :>> title = "Embedded-timestamp v-next hardening: honor manual managed-field edits (F9), scan-skip vs external mtime-preserving tools (F12), DST-correct offset labels (F14), >1MiB churn-killer gap (F15)"; :>> createdAt = "2026-07-29"; :>> createdBy = "claudeOpus"; :>> description = "Deferred (non-ship-blocking) findings from the embeddedTimestampMetadata pre-release critique: F9 (MEDIUM) the copy/re-stamp revert blind-restores base.text, so a user's manual correction of a managed created/updated is reverted every sync — should reconcile the managed fields (honor an earlier/legit value) instead; F12 (MED-LOW) driving FS mtime to the embedded updated weakens the scan-skip's 'a write bumps mtime' premise, so a body-only change by an external mtime-preserving tool (rsync -a) could be missed until a full scan — niche mixed-sync-tool setups; F14 (LOW) formatIsoOffset uses the CURRENT tz offset for a historically-stamped time, mislabeling by the DST delta (instant still correct, only the human offset is off); F15 (LOW/MED) a >1MiB managed note whose base text is dropped (MAX_BASE_TEXT_BYTES) skips the churn-killer revert and gets a spurious updated=now on a mere copy (bounded — converges after one push via persisted normHash). discoveredInField=false (critique-found). MOOTED 2026-08-01 by timestampIgnoreRedesign (1.9.0): all four findings targeted the 'SelfSync owns created/updated' code path — the copy/re-stamp revert (F9/F15), driving FS mtime to the embedded updated (F12), and formatIsoOffset (F14) — ALL of which the redesign DELETED (SelfSync now writes no note timestamps; identity masks timestamp-valued keys instead). With no stamping/revert/fs-mtime-drive code left, none of F9/F12/F14/F15 has a subject. Resolver repointed from the never-started embeddedTimestampHardening action to the completed redesign."; :>> discoveredInField = false; :>> relatedTask = "timestampIgnoreRedesign"; :>> severity = Severity::Medium; }
    #Resolves dependency from timestampIgnoreRedesign to issueTimestampHardeningFollowups;

    // Shipped-1.7.0 data-corruption found by the embeddedTimestampMetadata pre-release critique + VERIFIED
    // against the code; fixed in 1.7.1 (frontmatterParserSafety). D0047: the fix carries a permanent guard.
    part issueFrontmatterBlockScalarCorruption : Issue { :>> id = "d7c18003-0000-4a10-9b20-a1b2c3d40083"; :>> title = "1.7.0 frontmatter parser corrupts block-scalar notes (indented --- false-closes) + rewrites BOM/EOL/key-order on stamp"; :>> createdAt = "2026-07-29"; :>> createdBy = "claudeOpus"; :>> description = "Found by the pre-release 3-lens critique and VERIFIED against shipped 1.7.0: the line-based split() closed the block at the FIRST line trimming to '---', so an indented '---' inside a YAML block scalar (description: | ... '  ---') false-closed the frontmatter and DEMOTED real keys (title, tags) into the body — silent, permanent corruption, written to disk and pushed. Separately setManagedValue stripped a leading BOM, converted CRLF->LF, and reordered keys, while the enable-confirm falsely claimed 'won't touch your other frontmatter'. Reachable for any user who ENABLED embedded timestamps (default off, limited exposure) editing a note with a block-scalar-containing-'---'. FIX (1.7.1): col-0-only fence detection (block-scalar-safe) + surgical writes preserving BOM/EOL/key-order/all non-managed content, with block-scalar/BOM/CRLF/order/round-trip tests as the permanent guard. Severity High (silent data corruption in shipped code). discoveredInField=false (critique-found, before field amplification)."; :>> discoveredInField = false; :>> relatedTask = "frontmatterParserSafety"; :>> severity = Severity::High; }
    #Resolves dependency from frontmatterParserSafety to issueFrontmatterBlockScalarCorruption;

    // Owner-reported after 1.7.0: enabling the feature did nothing observable. Fixed in 1.8.0 (timestampBackfill).
    part issueTimestampEnableInert : Issue { :>> id = "d7c18004-0000-4a10-9b20-a1b2c3d40084"; :>> title = "Enabling embedded timestamps did nothing visible — feature was lazy (stamped only on next edit), so a settled vault saw no effect + no kickoff"; :>> createdAt = "2026-07-29"; :>> createdBy = "wweatherholtz"; :>> description = "Owner-reported after 1.7.0: 'embed created/updated timestamps doesn't make it clear when it's actually processing — it doesn't seem to be doing.' The feature stamped a note only on its next GENUINE EDIT; an already-synced/settled vault took the in-sync path and was never stamped, so flipping the toggle produced zero observable effect and there was no instantiation/kickoff. FIX (timestampBackfill, 1.8.0): a convergence pass on enable / policy-change / settled-launch that brings every in-scope .md note to compliance (seed from OS metadata, normalize non-canonical — instant-based, never bumps), paced + resumable via a per-vault marker/cursor, reversible via a conflict-copy for any not-cleanly-conformable note, gated by an informed COUNTED confirm with restore-signature detection; third-party alias keys masked in identity (no Linter re-stamp storm); Templates folder excluded. Severity Medium (usability — the feature appeared inert). discoveredInField=true (owner)."; :>> discoveredInField = true; :>> relatedTask = "timestampBackfill"; :>> severity = Severity::Medium; }
    #Resolves dependency from timestampBackfill to issueTimestampEnableInert;

    // Owner-reported regression from the 1.6.2 flicker fix; fixed in 1.8.1 (statusHangsOnSyncing).
    part issueStatusHangsOnSyncing : Issue { :>> id = "d7c18005-0000-4a10-9b20-a1b2c3d40085"; :>> title = "Status card hangs on 'Syncing...' — statusText() rendered the RAW engine phase, bypassing the light's 0-pending collapse"; :>> createdAt = "2026-07-29"; :>> createdBy = "wweatherholtz"; :>> description = "Owner-reported after the 1.6.2 flicker fix: the status card 'just hangs on Syncing' whether or not an edit is made, and shows Syncing at launch. A device probe proved the ribbon light FSM was CORRECT (shown=idle) while enginePhase=syncing (a 0-pending reconcile at rest) — so the visible 'Syncing...' came from the settings status card, which renders statusText() = the RAW engine.phase(), bypassing the effectiveLightPhase collapse (syncing+0pending -> idle) the light already applied. The two surfaces disagreed. FIX (1.8.1): extract the collapse into a pure syncstate.effectivePhase(phase, syncPending) and route BOTH effectiveLightPhase AND statusText through it, so every surface shows 'Fully synced' when nothing is pending. Also cleaned a raw NUL byte accidentally shipped in the 1.8.0 backfill sentinel (source now uses an escaped sentinel). Severity Low (cosmetic/human-factors; no data effect). discoveredInField=true (owner, real device)."; :>> discoveredInField = true; :>> relatedTask = "statusHangsOnSyncing"; :>> severity = Severity::Low; }
    #Resolves dependency from statusHangsOnSyncing to issueStatusHangsOnSyncing;

    // ===== 1.9.0 timestamp-ignore redesign (2026-07-30): field damage from the 1.7-1.8 "SelfSync owns the
    // field" approach on a real COPIED multi-device vault, + a SEPARATE CRLF root cause. All resolved by
    // timestampIgnoreRedesign (SelfSync stops WRITING timestamps; identity ignores volatile diffs). =====
    part issueTimestampFabricatedCreated : Issue { :>> id = "d7c18006-0000-4a10-9b20-a1b2c3d40086"; :>> title = "Embedded-timestamp backfill FABRICATED created dates — a copied vault's ctime=copy-time was seeded as created:now"; :>> createdAt = "2026-07-30"; :>> createdBy = "wweatherholtz"; :>> description = "Owner-reported on the real vault C:\\notes\\ASI - Work: 'how is it making new files that are created now, when they clearly weren't (their original creation date isn't being respected).' Root cause: the 1.8.0 backfill seeded a missing created from OS metadata (ctime/mtime); the vault is a COPY, and Windows resets file-creation time to copy-time, so seedValues read ctime≈now and stamped created:<today>. detectRestoreSignature (a 5s bucket) was too narrow to notice a slow multi-file copy and suppress the seed. ~22 survivors ended at a fabricated created:2026-07-08 (an earlier Win32 backfill) + others at today; one note has created AFTER updated (provably fabricated). FIX (timestampIgnoreRedesign, 1.9.0): SelfSync writes NO timestamps at all, so it can never fabricate one. Existing fabricated dates are irrecoverable for a real subset (no git; copy-contaminated birth time) and are REPORTED, never invented (the cleanup is delete-only). Severity High (silent wrong data written into user notes). discoveredInField=true."; :>> discoveredInField = true; :>> relatedTask = "timestampIgnoreRedesign"; :>> severity = Severity::High; }
    part issueTimestampBackfillConflictFlood : Issue { :>> id = "d7c18007-0000-4a10-9b20-a1b2c3d40087"; :>> title = "Embedded-timestamp backfill flooded the vault with timestamp-only conflict copies (planBackfillItem needsCopy true for every no-frontmatter note)"; :>> createdAt = "2026-07-30"; :>> createdBy = "wweatherholtz"; :>> description = "Owner-reported: 'tons of conflict files that show no difference either... on most of these conflict files the only differences I observe are in the timestamps, which we were explicitly supposed to ignore.' Root cause: planBackfillItem computed needsCopy = normalizedContent(original) !== normalizedContent(conformed); for a note with NO frontmatter, conform ADDS a ---...--- block, so the two normalized strings always differ -> needsCopy=true -> a reversible conflict copy for essentially every plain note. On the real vault this produced 33 live conflict copies (32 timestamp/EOL-only + 1 real). FIX (timestampIgnoreRedesign, 1.9.0): the whole backfill (and its needsCopy path) is DELETED — SelfSync never conforms/writes, so no copies are spawned; a timestamp-only cross-device diff is resolved by identity masking with no copy. The 32 existing spurious copies were cleaned up (delete-only, reversible external backup). Severity High (mass spurious conflict copies obscuring real ones). discoveredInField=true."; :>> discoveredInField = true; :>> relatedTask = "timestampIgnoreRedesign"; :>> severity = Severity::High; }
    part issueCrlfFalsePositiveChanges : Issue { :>> id = "d7c18008-0000-4a10-9b20-a1b2c3d40088"; :>> title = "CRLF/BOM-only differences are flagged as content changes — normalizedHash short-circuited to the RAW hash for a note without frontmatter (a SEPARATE root cause from timestamps)"; :>> createdAt = "2026-07-30"; :>> createdBy = "wweatherholtz"; :>> description = "Owner-reported: 'TONS of false positives that incorrectly identify changes when none really exists (CR/LF issues?).' An independent design-fit critic confirmed this is a DISTINCT root cause from the timestamp noise: normalizedHash (frontmatter.ts) returned the RAW byte hash for any note WITHOUT frontmatter (hasFrontmatter false -> sha256hex(bytes)), so EOL/BOM normalization never ran on plain notes and a CRLF↔LF re-save read as a content change; and even for notes with frontmatter the EOL normalization was gated behind the (feature-on) path. FIX (timestampIgnoreRedesign, 1.9.0): content identity ALWAYS normalizes EOL/BOM/trailing-newline for ALL text files, independent of the timestamp feature (the no-frontmatter short-circuit removed), and a cosmetic-only local change is recognized in-sync (not pushed) via the post-decide normHash override. Guard: the CRLF-only-not-pushed reconcile test + plain-note EOL identity tests. Severity Medium (chronic false-conflict/churn UX defect; no data loss). discoveredInField=true."; :>> discoveredInField = true; :>> relatedTask = "timestampIgnoreRedesign"; :>> severity = Severity::Medium; }
    #Resolves dependency from timestampIgnoreRedesign to issueTimestampFabricatedCreated;
    #Resolves dependency from timestampIgnoreRedesign to issueTimestampBackfillConflictFlood;
    #Resolves dependency from timestampIgnoreRedesign to issueCrlfFalsePositiveChanges;

    // ===== Field-reported 2026-07-30 (investigated, NOT yet fixed) — four follow-up defects. =====
    part issuePluginSyncStaleServerState : Issue { :>> id = "d7c18009-0000-4a10-9b20-a1b2c3d40089"; :>> title = "A plugin the user removed still shows as 'synced' — server plugin FILES are never pruned and community-plugins.json is grow-only, so a removal never propagates"; :>> createdAt = "2026-07-30"; :>> createdBy = "wweatherholtz"; :>> description = "Owner-reported: 'update-time-on-edit shows up in the synced community plugins' though not installed; 'there should be absolute parity here.' Root cause (verified): (A) the synced-plugins list is a UNION of local manifests + getServerPluginIds(); getServerPluginIds is derived by regex over EVERY remote file path (reconcile.ts onRemotePlugins), so it = every plugin with ANY file on the server. (B) removal never propagates: setPluginSync(id,false) only drops the id from pluginAllow (deletes nothing); then shouldSync=false -> the accepts predicate skips those paths ENTIRELY (no pull, no base, NO delete-remote), so the server folder lingers forever. (C) community-plugins.json is a deliberately grow-only union (mergeEnabledPluginsJson: enables propagate, disables do not, reconcile.ts:806-807), so the id is re-added every sync and never removed — why the vault still lists it enabled. FIX (pluginSyncRemovalPropagation): UI split (available-to-adopt vs synced) + a sanctioned removal channel (delete-remote for the plugin folder + a removal op the enabled-list merge honors) — a CHANGE to the catastrophe-proof-asymmetric merge, needs a Decision. Severity Medium. discoveredInField=true."; :>> discoveredInField = true; :>> relatedTask = "pluginSyncRemovalPropagation"; :>> severity = Severity::Medium; }
    part issuePluginSyncFolderIdNotName : Issue { :>> id = "d7c1800a-0000-4a10-9b20-a1b2c3d4008a"; :>> title = "Synced plugins display their folder id (update-time-on-edit) instead of the display name (Update time on edit) when not installed locally"; :>> createdAt = "2026-07-30"; :>> createdBy = "wweatherholtz"; :>> description = "Owner-reported: 'when plugins are synced, they indicate their file/folder name instead of display name, e.g. update-time-on-edit instead of Update time on edit; other names are more severe but that's the pattern.' Root cause (verified, settings.ts:495 + :449): the row name is manifests[id]?.name || id, and manifests = this.app.plugins.manifests = LOCAL installed manifests only. A server-only (not-installed-here) plugin has no local manifest, so name is undefined and it falls back to the folder id. The real name IS on the server (in the plugin's synced manifest.json) but onRemotePlugins (reconcile.ts) throws the content away, keeping only regex-extracted ids. FIX (pluginSyncDisplayName): carry the manifest 'name' from the server (lazy/cached for not-installed ids); display manifests[id]?.name || serverName(id) || id. Severity Low (cosmetic/legibility). discoveredInField=true."; :>> discoveredInField = true; :>> relatedTask = "pluginSyncDisplayName"; :>> severity = Severity::Low; }
    part issueVaultChangeSkipsTransition : Issue { :>> id = "d7c1800b-0000-4a10-9b20-a1b2c3d4008b"; :>> title = "A vault change via the setup wizard skips the merge/direction transition and reconciles against a STALE base — silent overwrite risk (data-integrity)"; :>> createdAt = "2026-07-30"; :>> createdBy = "wweatherholtz"; :>> description = "Owner-reported after a reconnect: 'i reconnected but didn't get the modal i expected (merge / keep device's / synced's)... joining a new vault needs some kind of transition logic, unless the re-logging in really did intelligently decide it wasn't needed.' Investigation (verified): a plain reconnect to the SAME vault correctly skips the modal (base intact -> normal incremental resume — WORKING AS DESIGNED, the modal is not broken). BUT a real latent GAP: SetupWizardModal.finish() (setupwizard.ts:255-279) writes st.vaultId directly WITHOUT setting pendingSwitch, WITHOUT clearing the base, and WITHOUT any direction modal, then reconnect() -> doConnect runs reconcileFull over the OLD vault's base. The base is a single global store cleared only by switchTo (reconcile.ts:1167). So changing vaults through the wizard (manually picking another vault, or the previously-synced vault no longer existing -> fallback to vaults[0]) makes decide() run against a FOREIGN base; the B===L->pull branch then SILENTLY OVERWRITES a local file whose new-vault copy differs — no conflict-copy, no prompt. Reachable from the user's exact scenario (token idle-expiry -> freshLogin -> openSetup -> wizard). FIX (vaultChangeTransitionGuard): route a wizard vault-change through switchToVault; defense-in-depth tag the base with owner/vaultId and force a switch/clear when it mismatches. Severity High (silent data overwrite on a vault change). discoveredInField=true."; :>> discoveredInField = true; :>> relatedTask = "vaultChangeTransitionGuard"; :>> severity = Severity::High; }
    part issueSessionIdleReloginFriction : Issue { :>> id = "d7c1800c-0000-4a10-9b20-a1b2c3d4008c"; :>> title = "Credentials 'stop working' until reconnect (a silent idle-logout) — token-only default + 30-min server idle timeout, correct but surprising and not clearly surfaced"; :>> createdAt = "2026-07-30"; :>> createdBy = "wweatherholtz"; :>> description = "Owner-reported: 'my credentials stopped working in selfsync but worked when I reconnected. would something recent have corrupted the login state?' Investigation (verified): NOT corruption. SelfSync defaults to TOKEN-ONLY (no stored password on disk, IA.3.5.10) and the server IDLE-EXPIRES a session after 30 min of no activity (DEFAULT_IDLE_TTL_SECS, AC.3.1.11; tokens otherwise persist across restarts, hashed, in .tokens.json). A device whose app was closed/asleep >30 min has its token idle-expire; with no stored password freshLogin can't silently renew, so it asks to reconnect — re-entering the password minted a fresh token. Working as designed, but the friction is real for a personal vault and the 'session expired' state is surfaced only by an opened setup modal, not a clear notice. FIX (sessionIdleReloginEase, UX-only): surface the reason clearly + document the knobs (Settings 'Store password on this device'; server SESSION_IDLE_TIMEOUT_SECS) + optionally a longer default idle window. Severity Low (UX; no defect, no data effect). discoveredInField=true."; :>> discoveredInField = true; :>> relatedTask = "sessionIdleReloginEase"; :>> severity = Severity::Low; }
    #Resolves dependency from pluginSyncRemovalPropagation to issuePluginSyncStaleServerState;
    #Resolves dependency from pluginSyncDisplayName to issuePluginSyncFolderIdNotName;
    #Resolves dependency from vaultChangeTransitionGuard to issueVaultChangeSkipsTransition;
    #Resolves dependency from sessionIdleReloginEase to issueSessionIdleReloginFriction;

    // ===== Field-reported 2026-07-30 (device log): the auth-retry storm. Resolved by the connection-FSM
    // typed-failure redesign (connectionFsmTypedFailure, 1.9.1). =====
    part issueAuthRetryStormNoStop : Issue { :>> id = "d7c1800d-0000-4a10-9b20-a1b2c3d4008d"; :>> title = "A hard auth failure (rejected sign-in / 401) is retried forever like a network drop — hammering login into a server-side lockout, and mislabeled 'offline'"; :>> createdAt = "2026-07-30"; :>> createdBy = "wweatherholtz"; :>> description = "Owner-reported with a device log: after a token rejection at reconnect, the client looped 'connect FAILED: unauthorized' every ~15-30s for 45+ min, never prompting re-auth. Root cause: SyncEngine.failToOffline collapsed EVERY effect failure into ONE 'offline' state + ONE recovery (scheduleReconnect, backoff capped 30s), and doConnect's catch distinguished only 404/session-expired via lastIssue string REGEXES; a 401-login or a 429 fell through to retry-forever. Two compounding harms: (1) the storm can trip the server's own 10-fails/5-min LoginThrottle (throttle.rs) → a self-inflicted 429 lockout that persists (every attempt keeps the window from rolling); (2) isAuthError = /HTTP 401/ never matched the server's plain-text 'unauthorized' body (errText overwrites the HTTP-nnn string), so the reactive re-login-once ALSO never fired for a real status() 401. The status card mislabeled a rejected sign-in / a timeout as 'offline'. FIX (connectionFsmTypedFailure, 1.9.1): a typed-failure connection FSM — a separate LinkState machine + a pure classifier reading TAGGED error fields (never a message regex) + a recovery policy — that STOPS retrying on a terminal class (awaits the user + a slow self-heal re-probe), honors the 429 Retry-After window, and surfaces the specific reason; isAuthError fixed to read the status field. Guard (D0047): the connstate tests (classify table + strand/loop invariants). Severity High (self-inflicted lockout + can't sync + confusing state). discoveredInField=true (owner, real device log)."; :>> discoveredInField = true; :>> relatedTask = "connectionFsmTypedFailure"; :>> severity = Severity::High; }
    #Resolves dependency from connectionFsmTypedFailure to issueAuthRetryStormNoStop;

    // ===== Owner-requested 2026-07-31: a newly-synced plugin needs a restart to activate. Resolved by
    // hotLoadSyncedPlugins (1.11.0), scoped to a provably-private vault (owner-accepted security tradeoff). =====
    part issueSyncedPluginRestart : Issue { :>> id = "d7c1800e-0000-4a10-9b20-a1b2c3d4008e"; :>> title = "A community plugin synced to a device that didn't have it requires a full Obsidian restart to activate — deliberate for untrusted (shared) code, but friction on a single-user private vault"; :>> createdAt = "2026-07-31"; :>> createdBy = "wweatherholtz"; :>> description = "Owner-reported: a plugin synced to a device (not previously there) shows 'not active yet — restart' and only loads on a full Obsidian restart. This is BY DESIGN (Round-6 SEC / R14 sec#1): sync-delivered plugin code is untrusted (a share peer / shared-vault owner could push malicious main.js), so SelfSync never auto-executes it — the restart is the trust barrier. But for a SINGLE-USER own+unshared vault the code is the user's OWN, so the restart is pure friction. FIX (hotLoadSyncedPlugins, 1.11.0): a NARROW, owner-ACCEPTED exception — on a PROVABLY-PRIVATE vault (own, not shared TO us, no readWrite grant/link — refreshVaultPrivacy, fail-safe) a newly-arrived plugin is hot-loaded live (app.plugins.loadManifests + enablePlugin), no restart. A shared/shareable vault, a running-plugin update, a hot-load failure, and CSS keep the restart barrier. The owner was shown the RCE tradeoff and chose the 'own, unshared only' scope. Severity Low (UX; the security-critical default — the restart barrier — is preserved for any untrusted case). discoveredInField=true (owner)."; :>> discoveredInField = true; :>> relatedTask = "hotLoadSyncedPlugins"; :>> severity = Severity::Low; }
    #Resolves dependency from hotLoadSyncedPlugins to issueSyncedPluginRestart;

    // ===== 2026-08-01 critique pass (4 independent antagonistic critics over shipped 1.9.0-1.11.0;
    // each finding re-verified against the code before recording). Three HIGH defects fixed in 1.11.1;
    // the Medium/Low findings backlogged. D0080: critique findings become severity-carrying Issues. =====
    part issueHotLoadPrivacyGateStale : Issue { :>> id = "f351b270-6d3a-4037-968e-904636df6bce"; :>> title = "Hot-load privacy gate (1.11.0) rides a STALE vaultIsPrivate — RCE-barrier bypass: a private->shared switch or an out-of-band grant lets a peer's synced main.js auto-execute with no restart"; :>> createdAt = "2026-08-01"; :>> createdBy = "claudeOpus"; :>> description = "Security critic finding, verified in code: vaultIsPrivate is never reset on a vault switch; flushConfigReload (which hot-loads) runs BEFORE the connect-time refreshVaultPrivacy (itself fire-and-forget void); and the delta/poll path that also hot-loads never refreshes it. So switching from a private vault to a shared/attacker vault, OR receiving an out-of-band readWrite grant on your own vault, leaves the gate true -> applyPluginCodeChange hot-loads a peer-controlled plugin (loadManifests+enablePlugin) with no restart — a bypass of the R14 sec#1 never-auto-execute barrier, within the in-scope peer/shared-vault threat model. FIX (hotLoadPrivacyGateFreshCheck, 1.11.1): re-derive privacy FRESH at the decision point. discoveredInField=false (critique-found)."; :>> discoveredInField = false; :>> relatedTask = "hotLoadPrivacyGateFreshCheck"; :>> severity = Severity::High; }
    #Resolves dependency from hotLoadPrivacyGateFreshCheck to issueHotLoadPrivacyGateStale;
    part issueReconcilePathTokenExpiryBlock : Issue { :>> id = "fdefcf4c-f6de-479a-befe-da2ef3fa9b39"; :>> title = "A routine mid-session token expiry on the poll/reconcile path mis-classifies as a PERMANENT auth block ('check your password') — the inverse of the auth-storm the FSM fixed"; :>> createdAt = "2026-08-01"; :>> createdBy = "claudeOpus"; :>> description = "FSM critic finding, verified in code: doConnect re-logs-in once on a 401, but the reconcile effects (doReconcileAll/doReconcilePath) call this.api.* directly with no such retry. So when a token expires DURING a connected session, a poll-path 401 propagates straight to classifyConnectError -> (hasStoredPassword) AuthRejected -> blocked{authRejected} showing 'Sign-in rejected — check your password' for a VALID password, self-healing only via the 600s reprobe (which runs doConnect) — and PERMANENTLY on a WS-less mobile client until then. FIX (reconcilePathReloginOnce, 1.11.1): withSyncRelogin wraps the reconcile effects for one silent re-login + retry when a password is stored. discoveredInField=false (critique-found)."; :>> discoveredInField = false; :>> relatedTask = "reconcilePathReloginOnce"; :>> severity = Severity::High; }
    #Resolves dependency from reconcilePathReloginOnce to issueReconcilePathTokenExpiryBlock;
    part issueVaultKeyServerBlind : Issue { :>> id = "16e029b6-2117-46a7-8ce8-77c2003b72ef"; :>> title = "Vault-identity key is SERVER-BLIND (owner/vault) — repointing at a different server with the same vault name silently overwrites local files (D0047 guard never trips)"; :>> createdAt = "2026-08-01"; :>> createdBy = "claudeOpus"; :>> description = "Vault-change critic finding, verified in code: historyFloorKey() = `${vaultOwner}/${vaultId}` omits the server URL, and the setup wizard's vaultChanged compares vaultId name only. Two servers trivially both host owner=''/vault='notes'. Repoint this device (own vault, same name) at a different server B and the D0047 guard's baseVaultKey === historyFloorKey() stays equal -> a plain reconcileFull runs against server B against a FOREIGN base -> for every path where B===L but R differs, decide() returns pull -> local file silently overwritten, no conflict copy. FIX (vaultKeyServerQualified, 1.11.1): server-qualified `host|owner/vault` key in both the guard + the wizard, with old-key grandfathering. discoveredInField=false (critique-found)."; :>> discoveredInField = false; :>> relatedTask = "vaultKeyServerQualified"; :>> severity = Severity::High; }
    #Resolves dependency from vaultKeyServerQualified to issueVaultKeyServerBlind;
    // Backlog (recorded, NOT fixed here) — clustered per critic area; each resolves to a stub action.
    part issueFsmCritiqueBacklog : Issue { :>> id = "fefd34b2-0f02-4893-9290-824935392946"; :>> title = "Connection-FSM Medium/Low follow-ups: LinkState not reset on disconnect (stale vault-gone prompt), serverDegraded reindex message clobbered, MFA/must-change-pw body-string classification, dead UserRetry edge / 429 re-arm / 503 retry-after"; :>> createdAt = "2026-08-01"; :>> createdBy = "claudeOpus"; :>> description = "FSM critic Medium/Low findings (verified), backlogged behind the 3 HIGH fixes: F2 disconnect/unload leave LinkState so getLastIssue/isVaultGone leak a stale blocked/vault-gone prompt after disconnect; F3 the actionable serverDegraded 'run reindex' message is overwritten by the generic outer catch and shows 'Reconnecting…'; F4 MFA/must-change-password classification matches un-pinned server body strings; F5 the UserRetry LinkState edge is dead, a repeated 429 re-arms retryAfter each cycle, and Retry-After is honored only for 429. discoveredInField=false (critique-found)."; :>> discoveredInField = false; :>> relatedTask = "critiqueBacklogFsm"; :>> severity = Severity::Medium; }
    #Resolves dependency from critiqueBacklogFsm to issueFsmCritiqueBacklog;
    part issueTimestampGateCritiqueBacklog : Issue { :>> id = "b23db4c3-7413-4e72-8b75-46b8247d384d"; :>> title = "Timestamp content-identity Medium/Low follow-ups: Date.parse value-shape gate over-masks bare-year/manual dates (contradicts the UI promise) + non-portable V8/JSCore; trailing-newline inconsistency; normHash never written"; :>> createdAt = "2026-08-01"; :>> createdBy = "claudeOpus"; :>> description = "Timestamp critic Medium/Low findings (verified), on the DEFAULT-ON feature so wide blast radius. T1 the isTimestampValue gate uses Date.parse, so a bare-year `created: 2020` (or a manually-curated date) is masked -> editing it silently doesn't propagate, contradicting the settings UI's 'a non-date value under the same key still syncs'. T2 Date.parse is engine-defined -> a non-canonical value hashes differently on desktop V8 vs mobile JSCore -> cross-platform churn. T4 trailing-newline normalization differs between normalizedContent (collapse 2+->1) and merge3's sameIgnoringEol (strip all) -> a final-newline toggle churns; lone-CR not normalized. T3 normHash is declared/serialized/read but never written (override rides on base.text recompute; >1MiB gap documented-accepted). discoveredInField=false (critique-found)."; :>> discoveredInField = false; :>> relatedTask = "critiqueBacklogTimestamp"; :>> severity = Severity::Medium; }
    #Resolves dependency from critiqueBacklogTimestamp to issueTimestampGateCritiqueBacklog;
    part issueVaultTransitionModalBacklog : Issue { :>> id = "862badb3-41bf-469f-82a1-515e65b2233f"; :>> title = "Vault-change Medium/Low follow-ups: redeem + owner-axis + guard-driven changes bypass the resolution modal (silent merge = cross-vault union); empty-base guard skip; fire-and-forget key stamp"; :>> createdAt = "2026-08-01"; :>> createdBy = "claudeOpus"; :>> description = "Vault-change critic Medium/Low findings (verified): V2 setupwizard finishRedeem + the direct-adopt path reconnect() with NO resolution modal (only the vaultId-name axis was closed), and the guard's remedy is a SILENT merge (a union across two vaults = contamination) rather than the Download/Upload/Cancel adjudication SwitchVaultModal offers — route guard-detected changes through the same modal. V3 the guard requires base.paths().length so a vault change with an empty base but local files skips it (pushes local into the new vault); baseVaultKey is stamped via a fire-and-forget save. discoveredInField=false (critique-found)."; :>> discoveredInField = false; :>> relatedTask = "critiqueBacklogVault"; :>> severity = Severity::Medium; }
    #Resolves dependency from critiqueBacklogVault to issueVaultTransitionModalBacklog;
    part issueSecurityHardeningBacklog : Issue { :>> id = "728d92a6-5e0e-4b65-bd6f-b1ed7bec05f6"; :>> title = "Security Medium/Low follow-ups: hot-load privacy gate trusts SERVER-reported share metadata (malicious-server threat — needs an owner decision); removePluginFromServer id not validated + re-push re-hot-loads"; :>> createdAt = "2026-08-01"; :>> createdBy = "claudeOpus"; :>> description = "Security critic Medium/Low findings (verified): S2 (threat-model decision) vaultIsPrivate is derived from share metadata the SERVER reports, and that same server ships the plugin bytes — a compromised/hostile server could lie 'not shared' -> hot-load. In scope only if the self-hosted server is treated as untrusted; needs an owner decision (accept-risk vs client-side attestation vs revert the private-vault hot-load exception). S3 (LOW) removePluginFromServer(id) builds a delete prefix from a server/peer-influenced id with no validation (reject `..`/`/`/empty); a removed plugin re-pushed by another active device re-arrives and, on a private vault, hot-loads again without re-approval. discoveredInField=false (critique-found)."; :>> discoveredInField = false; :>> relatedTask = "critiqueBacklogSecurity"; :>> severity = Severity::Medium; }
    #Resolves dependency from critiqueBacklogSecurity to issueSecurityHardeningBacklog;

    // Discovered 2026-08-02 while dispositioning the FSM backlog (F4): a FEATURE gap, not a critique defect.
    part issueMfaLoginUnsupported : Issue { :>> id = "5a8c473e-6c0d-440c-82e5-3607ec81d2b7"; :>> title = "MFA-enrolled accounts can't sign in via the plugin — login sends no TOTP code and the wizard/reconfigure has no field for one"; :>> createdAt = "2026-08-02"; :>> createdBy = "claudeOpus"; :>> description = "The server fully implements TOTP MFA (enroll/confirm, and login returns 401 'mfa required' without a code), but the plugin's transport.login() posts only {username,password} and the setup/reconfigure UI collects no code — so a user who enrolls MFA is locked out of the plugin. The connection FSM correctly classifies it (MfaRequired -> 'enter your authenticator code (Reconfigure)'), but Reconfigure can't actually collect the code, so the message is a dead-end. Surfaced while confirming the F4 classify branch matches the server's real phrasing. This is a FEATURE gap (MFA login support), not a defect in the shipped 1.9.1 classifier. discoveredInField=false (found during the critique-backlog pass)."; :>> discoveredInField = false; :>> relatedTask = "mfaLoginSupport"; :>> severity = Severity::Medium; }
    // D0038: MFA deprecated instead of building plugin TOTP — the mooting Decision now resolves this
    // (was: #Resolves from mfaLoginSupport, the not-pursued add-plugin-TOTP action, now removed).
    #Resolves dependency from d0038 to issueMfaLoginUnsupported;

    // Field-reported 2026-08-02 (owner, mobile, on 1.11.2).
    part issueStatusSwitchingLatched : Issue { :>> id = "6009ef6a-83ca-4211-9e6b-a50693e11330"; :>> title = "Status card latches 'Switching vault… applying your choice' on a persisted pendingSwitch even while connected + synced (no switch initiated); an authoritative switch that lingered set also re-clobbers local edits every connect"; :>> createdAt = "2026-08-02"; :>> createdBy = "wweatherholtz"; :>> description = "Owner-reported on a real device: the mobile status card showed 'Switching vault… applying your choice' persistently while the vault was actually connected and synced (green dot, recent Last synced), with no switch initiated. Root cause: statusDisplay() short-circuited on settings.pendingSwitch (a PERSISTED config value = the switch resolution) and this.resuming (a loose bool) BEFORE consulting the pure Phase projection — so a pendingSwitch that lingered set (its switchTo reconcile killed mid-flight on mobile before it could clear) latched the label. The D0047 guard was confirmed NOT the trigger (no 'base belonged to' line in the owner's debug log). Second-order (critique HIGH): a lingering AUTHORITATIVE resolution (download=take-remote / upload=take-local) re-runs on every connect and re-clobbers local edits made since. FIX (statusDisplayPureProjection, 1.11.3): statusDisplay is a PURE Phase projection (no setting/flag read); an already-applied guard clears a lingering switch whose base already belongs to the target (no re-clobber); the settings-card dot is made realtime-aware (no divergence). discoveredInField=true (owner, mobile)."; :>> discoveredInField = true; :>> relatedTask = "statusDisplayPureProjection"; :>> severity = Severity::High; }
    #Resolves dependency from statusDisplayPureProjection to issueStatusSwitchingLatched;

    // Field-reported 2026-08-02 (owner, mobile) — surfaced by the 1.11.3 debug log.
    part issueSwitchOutageFalseSynced : Issue { :>> id = "53288824-2bc7-4abc-8b85-1bd9318858ec"; :>> title = "A vault switch (upload/download) swallows a whole-server outage (DNS unresolvable) as per-file skips and settles to a FALSE 'Synced (polling)' — the status lies when the server is unreachable"; :>> createdAt = "2026-08-02"; :>> createdBy = "wweatherholtz"; :>> description = "Owner's 1.11.3 debug log on mobile: a persisted 'upload' switch ran during a DNS outage (Unable to resolve host 'notes2.willweatherholtz.com') and produced a flood of per-file 'UnknownHostException … skipped it, other files continue', after which the status card showed 'Synced (polling)' (yellow) even though the server was completely unreachable. Root cause: the normal reconcile loops (reconcileAll/reconcileLocalConfig) abort a pass on isConnectionError (→ engine offline+backoff), but switchTo's helpers switchDownload/switchUpload did NOT — every server-op catch called onFileError (skip+continue). So a connection-wide outage was isolated per-file, the switch 'completed' with everything skipped, and the engine settled to idle → a false 'synced'. FIX (switchAbortOnOutage, 1.11.4): switchDownload (applyPull) + switchUpload (pushFile, deleteFile) re-throw on isConnectionError, mirroring reconcileAll → the switch aborts → 'Reconnecting…' (honest). The underlying host-unresolvable condition is the owner's network/server to diagnose. discoveredInField=true (owner, mobile)."; :>> discoveredInField = true; :>> relatedTask = "switchAbortOnOutage"; :>> severity = Severity::High; }
    #Resolves dependency from switchAbortOnOutage to issueSwitchOutageFalseSynced;

    // Field-reported 2026-08-02 (owner, mobile) — the deeper layer surfaced by the 1.11.4 log.
    part issueConnectFalseSyncedDuringInitialReconcile : Issue { :>> id = "637d7422-517b-4012-b9b7-5387a0ed6732"; :>> title = "During a failing/empty initial connect reconcile the card reads 'Synced (polling)' — markReconciling pre-flips to 'syncing', which effectivePhase collapses to idle when 0 files transfer"; :>> createdAt = "2026-08-02"; :>> createdBy = "wweatherholtz"; :>> description = "After switchAbortOnOutage (1.11.4) the switch correctly aborted on the DNS outage (connect FAILED -> retrying in 3s), but the owner's log/UI still showed 'Synced (polling)' during the failing ~30s connect attempts — 'nothing to indicate work is being done'. Root cause (one FSM layer below the pure-projection fix): markReconciling() optimistically flipped connecting/disconnected -> reconciling (phase 'syncing') the instant the health check passed, before the initial reconcile ran; when that reconcile transferred nothing (DNS failing), syncPending stayed 0 and effectivePhase collapsed syncing-0-pending -> idle -> a FALSE 'Synced (polling)'. A normal poll avoided this by never pre-flipping (beginReconcile escalates only on real work). FIX (connectPhaseNoOptimisticFlip, 1.11.5): removed markReconciling; beginReconcile is the single door into 'reconciling', escalating from idle OR an in-flight connect, and onProgress(pending>0) triggers it — so a failing/empty connect stays 'Connecting…'/'Reconnecting…'. discoveredInField=true (owner, mobile)."; :>> discoveredInField = true; :>> relatedTask = "connectPhaseNoOptimisticFlip"; :>> severity = Severity::High; }
    #Resolves dependency from connectPhaseNoOptimisticFlip to issueConnectFalseSyncedDuringInitialReconcile;

    // Field-reported 2026-08-02 (owner, mobile) — surfaced by the 1.11.5 log.
    part issueSwitchNoProgressLooksHung : Issue { :>> id = "c2405aec-9b9f-463e-9ca5-b52d428eaba0"; :>> title = "A vault switch (upload/download) reports no progress, so it sits on a static 'Connecting…' and looks hung during a long transfer"; :>> createdAt = "2026-08-02"; :>> createdBy = "wweatherholtz"; :>> description = "After connectPhaseNoOptimisticFlip (1.11.5) the card honestly showed 'Connecting…' during the initial reconcile, but the owner reported it looked 'hung on connecting?' during a persisted 'upload' switch. Root cause: the normal reconcile (reconcileAll) reports onProgress (a decrementing pending count), but switchTo/switchUpload/switchDownload reported NONE — so syncPending stayed 0, there was no 'Syncing… N' detail and no state escalation, and a long/large switch sat on a static 'Connecting…'. FIX (switchReportsProgress, 1.11.6): switchDownload + switchUpload report onProgress like reconcileAll (full count up front, decrement to 0) — so an active switch shows 'Syncing… N pending' decreasing, a stalled one a stuck count, and an outage still aborts to 'Reconnecting…'. discoveredInField=true (owner, mobile). NOTE: the underlying block remains that notes2.willweatherholtz.com is unreachable (the owner's server/DNS)."; :>> discoveredInField = true; :>> relatedTask = "switchReportsProgress"; :>> severity = Severity::Medium; }
    #Resolves dependency from switchReportsProgress to issueSwitchNoProgressLooksHung;

    // Field-reported 2026-08-02 (owner, mobile) — 'is it rechecking? I don't see it reattempt'.
    part issueMobileResumeNoReattempt : Issue { :>> id = "c720d44e-f0d2-4ffc-9eca-2ac1352c1972"; :>> title = "On mobile, a connection that failed while backgrounded does not re-attempt on resume — the backoff timer is suspended and onResume's remote event is dropped while disconnected"; :>> createdAt = "2026-08-02"; :>> createdBy = "wweatherholtz"; :>> description = "Owner (mobile), server URL confirmed reachable: the plugin appeared to stop rechecking after a failed connect — 'is it rechecking though? I don't see it reattempt.' Root cause (mobile context-switching): the backoff reconnect timer uses window.setTimeout, which the OS SUSPENDS while the app is backgrounded, so a pending retry sits paused; and onResume enqueued a `remote` event, which the engine DROPS while disconnected (work is ignored until connected). So foregrounding after a failed connect did nothing to re-attempt. FIX (resumeReattemptsConnection, 1.11.7): onResume, when disconnected, cancels the stale paused timer and enqueues a fresh `connect` immediately (+ logs 'app resumed — re-checking the connection' for visibility); connected → re-assess; 'off' left alone. discoveredInField=true (owner, mobile)."; :>> discoveredInField = true; :>> relatedTask = "resumeReattemptsConnection"; :>> severity = Severity::High; }
    #Resolves dependency from resumeReattemptsConnection to issueMobileResumeNoReattempt;

    // Found 2026-08-02 by an STPA-UCA hunt on the delete/overwrite control actions (NOT the field) — the
    // first bug the deepened analysis DISCOVERED rather than confirmed.
    part issueSwitchUploadFalseAbsenceDelete : Issue { :>> id = "f6e60146-38f9-42f2-8b5c-03efe55e8c11"; :>> title = "An upload vault-switch tombstones a remote file that io.list() transiently FALSELY omits — fleet-wide delete-local of a still-present file (L-1)"; :>> createdAt = "2026-08-02"; :>> createdBy = "claudeOpus"; :>> description = "STPA-UCA hunt finding (delete-remote guideword): switchUpload's remote-drop loop issued delete-remote — a server tombstone that propagates delete-local to every peer — for any path missing from the switch's SINGLE io.list() snapshot, with NO probePresence re-probe and NO bulk-ratio guard. io.list() is fallible (an un-hydrated OneDrive/cloud placeholder, a directory that fails to enumerate, an OS/AV lock transiently under-reports a still-present file — the exact issueFalseAbsenceDelete hazard). On an 'upload' switch (make this vault authoritative) such a file is then never pushed AND deleteFile'd on the server; peers see the tombstone and remove their genuine local copy (L-1 data loss), while this device keeps the bytes with no base entry until the next full scan. This was the ONE delete path that trusted the raw listing: reconcileOne + reconcileDelta re-probe via probePresence and switchDownload's local-mirror carries the bulk-ratio guard — switchUpload had neither. FIX (switchUploadProbeGuard, 1.11.8): re-probe (probePresence) before tombstoning; present/indeterminate ⇒ keep. Severity High (fleet-wide delete of real content; recovery timing/luck-dependent via .trash + next full scan). discoveredInField=false (STPA-hunt-found)."; :>> discoveredInField = false; :>> relatedTask = "switchUploadProbeGuard"; :>> severity = Severity::High; }
    #Resolves dependency from switchUploadProbeGuard to issueSwitchUploadFalseAbsenceDelete;
    // Found 2026-08-02 by the same hunt (config-apply guideword) — a Medium L-3 gap needing an owner decision.
    part issueUntrustedCssApplied : Issue { :>> id = "90c02a08-7032-4b43-9c44-e57f413b8fd9"; :>> title = "Untrusted CSS (theme/snippet) synced from a shared vault is applied with only a restart notice — no trust warning, no private-vault gate, unlike plugin code (L-3)"; :>> createdAt = "2026-08-02"; :>> createdBy = "claudeOpus"; :>> description = "STPA-UCA hunt finding (caApplyConfig, L-3, Medium): flushConfigReload classifies synced themes/snippets/appearance CSS as 'will apply after restart' (a bare Notice) on the premise that CSS is 'never auto-applied' — but the plugin WRITES the CSS to disk during reconcile, and Obsidian hot-reloads an ENABLED snippet/theme on file change without a restart. On a readWrite-shared vault (snippets default ON) a peer can overwrite an enabled snippet's .css and Obsidian applies it live; CSS in Obsidian's un-CSP'd renderer enables exfil (background:url(...)) + phishing overlays (a class the code's own comment acknowledges). UCA-7 NAMES CSS but its realized mitigation SR-5 gates only plugin CODE (the restart trust-barrier + private-vault hot-load); CSS gets neither the trust warning nor the private-vault gate. Partly accepted-by-parity with Obsidian Sync (which also applies synced snippets) — so this NEEDS AN OWNER DECISION (gate/trust-warn untrusted shared-vault CSS vs accept-by-parity), not a unilateral fix. discoveredInField=false (STPA-hunt-found). Separately, the hunt re-confirmed the accepted S2 malicious-server oracle risk (issueSecurityHardeningBacklog) and sharpened it (the codebase elsewhere defends against a compromised server) — noted for the owner's re-weighing, already accept-risk'd."; :>> discoveredInField = false; :>> relatedTask = "cssTrustGate"; :>> severity = Severity::Medium; }
    #Resolves dependency from cssTrustGate to issueUntrustedCssApplied;

    // Found 2026-08-02 by an STPA-UCA hunt on the SERVER's delete/overwrite control actions (not the field).
    // The owner chose the CAS-guard fix over accept-authoritative via an explicit AskUserQuestion.
    part issueDeleteNoCasLostUpdate : Issue { :>> id = "3d5f9a71-8c02-4e6b-b1a4-0f2c7d9e4a83"; :>> title = "DELETE has no optimistic-concurrency (CAS) guard, unlike COMMIT — a stale reconcile delete silently supersedes a newer concurrent commit (L-1 lost update)"; :>> createdAt = "2026-08-02"; :>> createdBy = "claudeOpus"; :>> description = "STPA-UCA hunt finding (server delete control action, L-1). Vault::commit CAS-guards optimistic concurrency (expected_version: a second committer based on a stale version 409s + re-reconciles + merges), with a code comment naming the lost-update it prevents. Vault::delete had NO such guard: it took only a path and computed new_version unconditionally. So a device holding a STALE base could delete a file another device just edited (A commits edit v5->v6; B, still at v5, deletes -> server tombstones at v7), and the editor pulls the tombstone and silently loses its change FLEET-WIDE with no conflict marker — the exact class commit's CAS exists to stop. Weaponizable: a readWrite grantee can DELETE to discard the owner's concurrent edit. The critic flagged it as a possible 'delete-authoritative' trade-off that was NOWHERE recorded as a Decision, with the CAS rationale arguing against it — 'warrants an explicit decision.' OWNER DECISION (AskUserQuestion, 2026-08-02): CAS-guard delete (symmetric with commit) over accept-authoritative. FIX (deleteRemoteCasGuard): Vault::delete_checked(path, expected_version) mirrors commit's CAS (AlreadyExists->409); the reconcile delete-remote sends the based-on remote version; deliberate/authoritative deletes (user gesture / adjudication / switch) omit it and still always win. On a 409 the client re-reconciles and, because decide() keys on hashes, remote-advanced-since-base reads as edit-wins-pull -> the edit is RESURRECTED, never lost. Backward-compatible both ways (old client omits the field; old server ignores the unknown query param). discoveredInField=false (STPA-hunt-found)."; :>> discoveredInField = false; :>> relatedTask = "deleteRemoteCasGuard"; :>> severity = Severity::High; }
    #Resolves dependency from deleteRemoteCasGuard to issueDeleteNoCasLostUpdate;
    // Secondary LOW from the same server hunt — a mirror mismatch (not data loss); the chunk store stays authoritative.
    part issueMirrorWriteNotSelfHealed : Issue { :>> id = "7b1e0c4a-5d93-4f27-9a86-2e3c8b0d61f5"; :>> title = "A failed bind-mount mirror write is not repaired by a later idempotent commit retry (the same-content short-circuit returns before write_mirror)"; :>> createdAt = "2026-08-02"; :>> createdBy = "claudeOpus"; :>> description = "STPA-UCA server hunt, LOW. Vault::commit writes the authoritative bytes to the chunk store (durable) and then BEST-EFFORT mirrors them to the bind-mount file; a mirror-write failure is logged, not fatal, because get_chunk serves the durable content. But the idempotent re-commit short-circuit (identical path+hash+chunks -> return unchanged, no persist) returns BEFORE write_mirror, so a commit whose mirror write failed is NOT healed by a subsequent identical retry — the on-disk mirror stays stale until the next genuine content change or a reindex. NOT data loss (the chunk store is authoritative + is what sync serves); only affects a user editing the vault DIRECTLY on the host filesystem via the bind mount (a niche mode). Fix would re-attempt the mirror write on the idempotent path when the mirror is absent/stale. discoveredInField=false (STPA-hunt-found)."; :>> discoveredInField = false; :>> relatedTask = "mirrorWriteSelfHealBacklog"; :>> severity = Severity::Low; }
    #Resolves dependency from mirrorWriteSelfHealBacklog to issueMirrorWriteNotSelfHealed;

    // Raised 2026-08-02 by the owner ('does diagnose actually do much? always says everything is fine even
    // if it's not working'). An L-5 (misleading-UX) gap; the owner directed removal over a heavier fix.
    part issueDiagnoseFalseAllClear : Issue { :>> id = "2f8c1d64-9b3a-4e07-a5f2-6d09e83b71c4"; :>> title = "The 'Diagnose' button gives a FALSE 'all good' — it probes only the connection chain, blind to whether sync is actually converging (L-5 misleading UX)"; :>> createdAt = "2026-08-02"; :>> createdBy = "wweatherholtz"; :>> description = "Owner-reported. HttpTransport.diagnose walked the CONNECTION chain (reachable -> version -> auth -> vault present -> server-index-not-degraded) via fresh out-of-band HTTP probes and returned 'All good' when all five links were healthy. But it NEVER consulted the live sync engine (getState/linkState/getPhase/pending, per-file retry budget), so it was structurally blind to sync NON-convergence: a stalled/off engine, pending work not draining, a file looping on an error, or a wedged FSM. So exactly when sync is stuck-but-the-pipe-is-fine — the case the user clicks Diagnose for — it falsely says 'everything is fine' (an L-5 misleading feedback, feeding a wrong picture into the USER's process model; relates to H-9 reported!=actual). Worse: it was a SECOND, out-of-band source of truth that could CONTRADICT the honest status card (a pure FSM projection) built this sitting — the dual-source anti-pattern the status-FSM work exists to kill. Analysis showed the honest status card already surfaces every actionable cause diagnose gave, via connstate.blockedTip (version mismatch / sign-in rejected / session expired / MFA / vault-gone / access-removed / degraded) derived from REAL sync failures. RESOLUTION (owner-directed 'consider just removing'): REMOVE the Diagnose button + its chain (removeDiagnoseButton, 1.11.11) so the honest FSM-projected status line is the SINGLE source of truth (it cannot give a false all-clear because it is a pure projection). discoveredInField=true (owner). Severity Medium (misleading, not data loss)."; :>> discoveredInField = true; :>> relatedTask = "removeDiagnoseButton"; :>> severity = Severity::Medium; }
    #Resolves dependency from removeDiagnoseButton to issueDiagnoseFalseAllClear;

    // Owner-reported 2026-08-02: 'hanging on connecting status. I'd like some insight into why - surely
    // connecting has multiple phases?' An L-5 (missing/inadequate-feedback) gap on the connect loop.
    part issueConnectStatusOpaque : Issue { :>> id = "6b3e9f21-4c7a-4d80-b2e5-1f8a0c6d9e34"; :>> title = "'Connecting…' is one opaque label over several phases with no sub-phase or timing — a slow phase reads as hung with zero insight (L-5)"; :>> createdAt = "2026-08-02"; :>> createdBy = "wweatherholtz"; :>> description = "Owner-reported (field): the status hung on 'connecting' with no insight into why; the log showed 'connecting to ... as will' then a 36s gap then 'config sync on — syncing 38 files' and nothing between. doConnect (main.ts) runs THREE phases all labeled 'Connecting…' and logs NOTHING between them on the happy path: (1) establishSession — acquireToken (login/cached) -> api.status() first authed round-trip (30s timeout) -> version handshake -> refreshShareGrant; (2) resolveAndApplySwitch -> reconcileFull -> reconcileAll — which fetches the FULL remote manifest (changes(0)) THEN lists+hashes every local file (the 'config sync on' log is emitted by io.list, so the 36s of silence was establishSession + the manifest fetch, BEFORE the local scan even started); (3) finishConnect — WS + poll. By design (connectPhaseNoOptimisticFlip 1.11.5) the status stays 'Connecting…' through the whole initial reconcile and only flips to 'Syncing…' on real transfer work — good against a false 'Synced', but it makes a slow initial scan/fetch look hung. The user (a controller) can't tell a slow connect from a stuck one and has no timing to locate the stall — an L-5 inadequate-feedback gap on the connect control loop (parallels S-14, the no-progress bulk op). RESOLUTION (owner directed 'Status sub-phases + timed log'): connectPhaseVisibility (1.12.0) names each sub-phase (signing in / checking the server / checking your access / fetching changes / scanning local files / reconciling N) as the 'Connecting…' DETAIL (card/tooltip) AND logs each with cumulative elapsed, driven by a new reconcile onStage hook + a connect-gated setConnectStage. discoveredInField=true (owner). Severity Medium (misleading/opaque, not data loss)."; :>> discoveredInField = true; :>> relatedTask = "connectPhaseVisibility"; :>> severity = Severity::Medium; }
    #Resolves dependency from connectPhaseVisibility to issueConnectStatusOpaque;

    // Found 2026-08-02 by the client-side chunking/reassembly STPA-UCA hunt (an independent critic). The
    // owner chose to fix it (AskUserQuestion 'Fix it — careful spec + critique + TDD'). Closes SR-2's
    // previously-accepted streamed-pull residual.
    part issueStreamedPullMidEditLoss : Issue { :>> id = "8d4f1a63-2c90-4e57-b6a1-3f0e7c85d924"; :>> title = "A mid-stream local edit is silently, unrecoverably lost on a large-file (>=8 MiB) streamed pull — the buffered path is safe, the streamed path was not (L-1)"; :>> createdAt = "2026-08-02"; :>> createdBy = "claudeOpus"; :>> description = "Client chunking/reassembly STPA-UCA hunt finding (UCA-4 / S-3 / SR-2 family). applyPull's streamed branch (rmeta.size >= STREAM_MIN_BYTES, 8 MiB) ran the racing-edit check (conflictCopyIfRaced) BEFORE streaming, then streamFileToDisk reassembled to a temp file and atomic-renamed it over `path` in close() with NO re-check in the seam. So an edit saved to that file DURING the multi-second download was clobbered by the rename, and base was set to the remote hash → next reconcile sees local==base → in-sync → the edit is gone, unrecoverably. The BUFFERED path (all files < 8 MiB) is SAFE — it re-checks AFTER the fetch (reconcile.ts). Asymmetry: small notes protected, large files (e.g. a live-edited >8 MiB .canvas) not. This was EXACTLY SR-2's documented 'Residual (accepted): a sub-window TOCTOU on very large streamed pulls.' Prior attempts to close it regressed (a 'post-write re-read' that read the file AFTER the rename = remote bytes, laundering wrong bytes into base) — so the fix needed care. FIX (streamedPullRacingEditGuard 1.12.1): streamFileToDisk gains a beforeRename hook called after the incremental hash-verify + before close()'s rename; applyPull passes a seam guard that reuses conflictCopyIfRaced on the ORIGINAL on-disk file (which still holds the racing edit — never the post-rename result, so base is only ever rmeta.hash). An independent critic (SOUND-WITH-CHANGES) caught a follow-on hole: the orphan-cleanup would delete the SOLE surviving racing edit if close() throws AFTER the rename applied — so the fix does NOT delete the seam copy on failure (a redundant copy is cosmetic; a deleted edit is loss), plus a close()-must-never-throw-after-rename contract. Guards (fail-first): reconcile.test 'preserves a mid-stream local edit as a conflict copy', 'makes NO spurious copy when there is no racing edit', 'a >8 MiB config file ... ABORTS (adjudicate)', 'a close() failure AFTER the rename does NOT delete the sole surviving racing edit'. discoveredInField=false (STPA-hunt-found). Severity Medium (narrow window — >=8 MiB files hand-edited mid-download; unrecoverable but rare; notes unaffected)."; :>> discoveredInField = false; :>> relatedTask = "streamedPullRacingEditGuard"; :>> severity = Severity::Medium; }
    #Resolves dependency from streamedPullRacingEditGuard to issueStreamedPullMidEditLoss;

    // Owner-reported 2026-08-02 (field, via the new connect-phase timing): 'second time it's reconciling
    // ~1100 files, fully synced last time, changed nothing.' A reload-rehash-the-whole-vault perf issue.
    part issueScanSkipHintNotPersisted : Issue { :>> id = "9e5a2c74-3d81-4f60-b7a2-4c0f8d96e135"; :>> title = "Every plugin reload re-reads + re-hashes the WHOLE vault on the first connect — the size/mtime scan-skip hint was deliberately not persisted"; :>> createdAt = "2026-08-02"; :>> createdBy = "wweatherholtz"; :>> description = "Owner-reported via the 1.12.0 connect timing: on a fresh 'plugin loaded' the first connect reconciles ~1137 files though nothing changed and it was fully synced. Root cause: the (size,mtime) scan-skip hint (which lets a whole-vault reconcile skip the read+SHA-256 of an unchanged file) was DELIBERATELY in-memory-only — BaseStore.toJSON (base.ts) persisted only hash/text/normHash, dropping size/mtime ('never let a perf hint outlive its verifying session', R15 sync#3). So after every reload the base has no stamps, baseStatUnchanged can't match, and reconcileOne re-reads+re-hashes every file (nothing transfers — still fully synced — but it re-does the verification, the field cost). Also surfaced by the same log: the ~18s pre-reconcile is io.list() walking the whole .obsidian config tree (SEPARATE issue, not this one), and 'token rejected — re-logging in' every connect (session token not reused; separate). OWNER DECISION (AskUserQuestion 'Persist the scan-skip hints'): persist size+mtime in toJSON so a reload trusts the same rsync/Syncthing (size,mtime) heuristic the in-session skip already uses. TRADEOFF (independent critic verified SOUND — no data-loss path): a file changed OUT of Obsidian while off, preserving BOTH size AND mtime, isn't re-hashed on reload — the exact accepted rsync residual, now WIDER (the reload full-rehash backstop is removed, so the rare miss self-heals only on the next edit event / size|mtime change / remote divergence, not on the next restart). It is a DELAYED push, NEVER data loss (a lying stamp colliding with a remote change re-reads live in applyPull->conflictCopyIfRaced and writes a conflict copy — never a silent overwrite), and never hides a REMOTE change (detected via the manifest). FIX (persistScanSkipHint 1.12.2): toJSON emits size+mtime (constructor already loads them); guarded by base.test (round-trip) + reconcile T2/T5 (unchanged skips read + noop), T3 (stale stamp still re-reads a change), T4 (lying stamp + remote divergence -> conflict copy, the safety test), T6 (absent file not masked -> delete-remote fires), and a main.ts mtime-source-parity invariant (T7). discoveredInField=true (owner). Severity Medium (perf/UX; unrecoverable-loss ruled out by the critic)."; :>> discoveredInField = true; :>> relatedTask = "persistScanSkipHint"; :>> severity = Severity::Medium; }
    #Resolves dependency from persistScanSkipHint to issueScanSkipHintNotPersisted;

    // Owner-reported 2026-08-02 (field, via 1.12.0 connect log): 'token rejected — re-logging in' on
    // connect. Owner directed 'fix the token one first'. A too-aggressive idle-timeout DEFAULT.
    part issueTokenIdleReloginFriction : Issue { :>> id = "a7c4e582-6d13-4b90-9f27-3e0a8c145d76"; :>> title = "The plugin re-logs-in on every connect after a break — the server's session idle-timeout defaulted to 30 min"; :>> createdAt = "2026-08-02"; :>> createdBy = "wweatherholtz"; :>> description = "Owner-reported via the 1.12.0 connect timing ('token rejected — re-logging in' -> 'login OK', ~0.5s, on connect). Cause: the server's bearer tokens (tokens.rs, persisted to .tokens.json so they survive a RESTART — not the cause) carry BOTH a 30-day absolute cap AND an IDLE timeout (AC.3.1.11), which DEFAULTED to 30 min (SESSION_IDLE_TIMEOUT_SECS). An actively-syncing device slides last_used and never idle-expires, but a device whose app was CLOSED / not syncing for >30 min has its token idle-expire, so the next open 401s and the client (correctly) re-logs-in. For a personal single-user self-host where the client already stores the credential + auto-relogins, a 30-min idle timeout adds friction with little real security benefit (the re-login is automatic). OWNER DECISION (AskUserQuestion 'Default to the 30-day absolute cap (no idle expiry)'): make idle expiry DEFAULT-OFF. FIX (tokenIdleDefaultOff 1.12.3, SERVER — requires a server-image redeploy): DEFAULT_IDLE_TTL_SECS 30*60 -> 0 (idle expiry off; token lives its full 30-day absolute cap + revoke/password-change). The control REMAINS available: a compliance-seeking operator opts in via SESSION_IDLE_TIMEOUT_SECS=<positive>. COMPLIANCE reconciled honestly (not silently): NIST 800-171 3.1.11 disposition partial -> operator (opt-in), and 3.13.9's inactivity clause noted opt-in; docs/cmmc-posture.md + docs/deployment.md doc-synced. Guards: tokens.rs default_has_no_idle_expiry_only_the_absolute_cap (new default) + idle_expires_a_stale_token_but_keeps_an_active_one (the control when enabled). discoveredInField=true (owner). Severity Low (friction; auto-heals, no data/security loss). NOTE: two OTHER things from the same log remain separate — the ~18s .obsidian config-tree walk (owner directed 'then the other' — NEXT) and nothing else."; :>> discoveredInField = true; :>> relatedTask = "tokenIdleDefaultOff"; :>> severity = Severity::Low; }
    #Resolves dependency from tokenIdleDefaultOff to issueTokenIdleReloginFriction;

    // Owner-reported 2026-08-02 (field, via 1.12.0 connect timing): the ~18s pre-reconcile 'scanning local
    // files' phase. Owner directed 'then the other' (after the token fix). A slow config-tree walk.
    part issueConfigWalkSlow : Issue { :>> id = "b8d5f296-4e02-4c71-a3d6-5f1a9e074c28"; :>> title = "The .obsidian config-tree enumeration is fully sequential — a plugin-heavy tree costs many seconds on a latency-bound (mobile) adapter, every reconcile"; :>> createdAt = "2026-08-02"; :>> createdBy = "wweatherholtz"; :>> description = "Owner-reported via the 1.12.0 connect timing: the 'scanning local files' phase took ~18s (2.5s -> 20.5s in the log), before the reconcile even started. Root cause: ObsidianVaultIo.enumerateConfig walked the hidden .obsidian/ tree FULLY SEQUENTIALLY — one awaited adapter.list(dir) per directory + one awaited adapter.stat(file) per passing file, depth-first — so the wall-clock was (call COUNT x per-call latency). The notes come from Obsidian's in-memory getFiles() instantly; only this config walk does async fs work, and it runs on EVERY reconcile (incl. polls), not just connect. On mobile (Android — the owner's device) each adapter call round-trips a filesystem bridge, so a plugin-heavy .obsidian tree (many plugin dirs/files) = seconds. OWNER DIRECTED the fix ('then the other'). FIX (configWalkParallel 1.12.4): extract the walk into a pure, unit-tested configwalk.ts (walkConfigTree) that runs adapter.list/stat CONCURRENTLY under a GLOBAL concurrency cap (a counting semaphore — a per-call mapPool can't bound a recursive walk), collapsing the wall-clock toward (tree DEPTH x latency). Read-only + behavior-preserving: it finds exactly the same passing-file set (order-independent), a dir it can't list is SKIPPED (not treated as empty — reconcile's per-file probe still guards a false delete) + logged, and a slow walk logs its shape ('config scan: N folders + M files in Xs') so the effect is measurable. Guards: configwalk.test — finds every passing file across a nested tree; respects the passes filter; a list error skips only that subtree + continues; NEVER exceeds the global cap (peak<=limit) yet DID run in parallel (peak>1); empty tree. discoveredInField=true (owner). Severity Medium (perf; every-reconcile cost, worse on mobile)."; :>> discoveredInField = true; :>> relatedTask = "configWalkParallel"; :>> severity = Severity::Medium; }
    #Resolves dependency from configWalkParallel to issueConfigWalkSlow;

    // Owner-reported 2026-08-02 (field): 'says it's reconciling but it's not actually doing anything?' then
    // 'stuck on label' — the connect status showed a static 'reconciling 1137 local file(s)' that both
    // overstated (implied syncing 1137) and, when the examination was slow, looked frozen. An L-5 gap.
    part issueReconcileExamOpaque : Issue { :>> id = "c9e6f307-5f13-4d82-b4e7-6a2b0f185d39"; :>> title = "The connect examination shows a static 'reconciling N files' — overstates (implies syncing) AND looks stuck when the pass is slow, with no progress"; :>> createdAt = "2026-08-02"; :>> createdBy = "wweatherholtz"; :>> description = "Owner-reported (field): the connect status showed 'reconciling 1137 local file(s)' and appeared to do nothing ('says reconciling but not doing anything'), then 'stuck on label'. Two problems: (1) LABEL — my connect sub-phase (1.12.0) said 'reconciling N local file(s)', which reads as 'syncing N' when the pass actually EXAMINES all files to detect changes and transfers only what CHANGED (nothing changed -> 0 work -> completes to Fully synced). (2) NO PROGRESS — the examination showed a STATIC label, so a SLOW full pass (a first-run re-hash before the 1.12.2 scan-skip stamps have persisted; or a large mobile vault) looks frozen, and a genuine hang is indistinguishable from slow. The engine can't flip to 'Fully synced' until reconcileAll returns, so a slow/hung pass leaves the connect on the stale label. FIX (reconcileExamProgress 1.12.5): (a) honest label 'checking N files for changes' (examines, not syncs; real transfer work still shows as 'Syncing… N pending' via onProgress); (b) LIVE progress 'checked X/N files' (every 250 examined) so a slow pass shows MOVEMENT (not fake-stuck) and a genuine hang is PINPOINTED — the count freezes at the stuck file. NOTE: this is a UX + DIAGNOSTIC fix; if the underlying stall is a hard hang (not a one-time slow re-hash that completes + persists stamps), the frozen progress count locates it for a targeted follow-up. Guards: reconcile.test onStage sequence updated (fetching -> scanning -> 'checking N files for changes'). discoveredInField=true (owner). Severity Medium (misleading + looks-stuck; the connect blocks on the examination)."; :>> discoveredInField = true; :>> relatedTask = "reconcileExamProgress"; :>> severity = Severity::Medium; }
    #Resolves dependency from reconcileExamProgress to issueReconcileExamOpaque;
    // Owner-directed 2026-08-02: 'get rid of the "remove from server" button ... admin interface ... taking
    // up far too much space for a rare need.'
    part issuePluginRemoveButtonClutter : Issue { :>> id = "d0f7a418-6024-4e73-a5f8-7b3c1a296e4a"; :>> title = "The per-plugin 'Remove from server' button clutters the plugin list — a whole button per row for a rare, admin-appropriate need"; :>> createdAt = "2026-08-02"; :>> createdBy = "wweatherholtz"; :>> description = "Owner-directed: the settings plugin list rendered a 'Remove from server' button on EVERY server-present plugin row (settings.ts renderPluginRows) — a whole button per row for a rare need, taking far too much space. Removing a plugin's files from the server is an owner/admin task better done from the admin interface. FIX (removePluginServerButton 1.12.5): remove the per-row button; the plugin's removePluginFromServer method (still tested — plugin-wiring purge + traversal-reject tests) stays for the admin/other path, just not surfaced as per-row UI clutter. No test asserted the button (tsc clean, DOM tests green). discoveredInField=true (owner). Severity Low (UI declutter)."; :>> discoveredInField = true; :>> relatedTask = "removePluginServerButton"; :>> severity = Severity::Low; }
    #Resolves dependency from removePluginServerButton to issuePluginRemoveButtonClutter;

    // Found 2026-08-02 by the client-side WebSocket-push STPA-UCA hunt (independent critic). The only
    // non-null client finding; verified against the code.
    part issueWsSupersededOpenError : Issue { :>> id = "e1a80529-7135-4d94-b5f8-8c3d1b2a7e50"; :>> title = "The WS open/error handlers lack the superseded-socket identity guard that close has — a late error from an OLD socket degrades the CURRENT live socket"; :>> createdAt = "2026-08-02"; :>> createdBy = "claudeOpus"; :>> description = "Client WS-push STPA-UCA hunt finding (Medium). spinUpWs supersedes a socket by this.ws?.close() then pointing this.ws at the new one; the FSM design (transportstate.ts:7) requires ALL socket events to honor the this.ws!==ws identity check. The `close` handler and the liveness tick DO guard, but `open` (main.ts) and `error` did NOT. So a late `error` from a SUPERSEDED old socket (racing the abort supersession triggers) called applyTransport('errored') -> transportTransition(live,'errored') -> degraded -> the CURRENT live socket is forced to degraded: realtimeConnected reads false, the light shows yellow 'Synced (polling)' instead of green 'Fully synced', and the poll is pinned to POLL_ACTIVE_MS (4s) until the next full socket cycle (battery). SAFE direction (under-claims health; changes still flow via the poll -> no missed changes, no false-synced), so Medium not High; a clear bug (asymmetric guard contradicting the FSM's own supersession design). The dangerous direction (a stale `open` flipping to false-live) is unreachable (supersession close()s a still-connecting socket, which aborts without firing open) but the open guard is added for symmetry. FIX (wsSupersededGuard 1.12.6): add `if (this.unloading || !this.api || this.ws !== ws) return;` to both open + error handlers, matching close. Guard: plugin-wiring 'a SUPERSEDED WS socket's late open/error does NOT disturb the current live socket' (fail-first). discoveredInField=false (WS-hunt-found). Severity Medium (wrong status light + battery; no data risk)."; :>> discoveredInField = false; :>> relatedTask = "wsSupersededGuard"; :>> severity = Severity::Medium; }
    #Resolves dependency from wsSupersededGuard to issueWsSupersededOpenError;
    // Found 2026-08-02 by the SERVER-side WS-push hunt — a LOW latent-coupling / defense-in-depth gap (not
    // exploitable today). Backlogged (would need a server redeploy; not urgent).
    part issueWsSessionAliveMustChange : Issue { :>> id = "f2b91630-8246-4a05-c6a9-9d4e2c3b8f61"; :>> title = "The WS per-delivery liveness re-check (session_alive) omits the must_change dimension the connect-time gate enforces"; :>> createdAt = "2026-08-02"; :>> createdBy = "claudeOpus"; :>> description = "Server WS-push STPA-UCA hunt finding (Low, latent / defense-in-depth). The WS UPGRADE mirrors the HTTP must_change gate (a locked account can't open a subscription), but the per-notification/per-ping predicate session_alive (server/src/ws.rs) re-checks only token-resolves + share-ACL(Read) + vault-exists — NOT users.must_change(user). So an account that transitions to must_change WHILE a WS is open isn't torn down by that dimension alone. NOT a live defect: every path that sets must_change on an account with a live token ALSO revokes tokens (admin reset set_must_change+revoke_user; self-service change_password revoke_user; admin-create sets it on a token-less new account), and session_alive catches the paired revoke via token_ok==false -> teardown. So the socket does tear down, transitively through token revocation, not through the flag. FRAGILE INVARIANT (relies on callers pairing set_must_change with revoke_user), not a current leak. FIX (backlog, wsSessionAliveMustCheckBacklog): add must_change to session_alive so the liveness check is self-contained (defense-in-depth). Requires a server redeploy; low priority (not exploitable). ALSO from the same hunt, NOT tracked as separate Issues (accepted tradeoffs / negligible, not defects): the per-delivery re-auth (mutex + fs-stat) amplification on high fan-out (a deliberate prompt-revocation security-vs-scale tradeoff); a bounded cosmetic transient false-green over a not-yet-detected half-open socket (backstopped by the 60s idle poll + onResume); and a shared lastWsActivity field across socket generations (sub-ms window, negligible). discoveredInField=false (WS-hunt-found). Severity Low."; :>> discoveredInField = false; :>> relatedTask = "wsSessionAliveMustCheckBacklog"; :>> severity = Severity::Low; }
    #Resolves dependency from wsSessionAliveMustCheckBacklog to issueWsSessionAliveMustChange;

    // Owner-directed 2026-08-03: 'revisit the timestamp area UX. descriptions are way too verbose, and the
    // date field identification should be an array input, not a huge text field. we try and prevent errors.'
    part issueTimestampSettingsVerboseUx : Issue { :>> id = "17ea5b96-4f13-4d80-b6a2-5c1e0f286d40"; :>> title = "The timestamp settings are too verbose and the ignored-date-fields input is a huge free-text field (no error prevention)"; :>> createdAt = "2026-08-03"; :>> createdBy = "wweatherholtz"; :>> description = "Owner-directed UX cleanup of the 'Timestamp changes' settings (settings.ts renderIgnoreTimestamps): the descriptions were paragraph-length, and 'Ignored date fields' was a 5-row TEXTAREA (one-key-per-line free text) — a malformed / duplicate / unmatchable key just got silently accepted. FIX (timestampSettingsUx 1.12.7, client-only): (1) tightened all three descriptions (master toggle, date fields, excluded folders) to one short line; (2) replaced the textarea with a validated ADD-a-row LIST mirroring the excluded-folders + plugin-checklist pattern — each key is its own row with a Remove button, plus an 'Add a date field' row whose 'Add field' button runs a pure validateTimestampKey poka-yoke (rejects empty / a ':' that would break the YAML key / an unmatchable shape / a case-insensitive duplicate, each with a short Notice) so a bad entry is PREVENTED rather than accepted; (3) a 'Restore default date fields' safety shown only when the list has drifted (so a user can't get stranded with an emptied list — the old textarea's implicit empty->defaults is now explicit). No reconcile-semantics change (same s.ignoredTimestampKeys + saveSettings as the textarea). Guards: frontmatter.test validateTimestampKey (accepts the default shapes/wildcards/spaces, trims, rejects empty/colon/junk/case-dup); settings-ui.dom 'date fields are a validated add/remove LIST' + 'an INVALID or DUPLICATE date field is REJECTED'. discoveredInField=true (owner). Severity Low (UX / error-prevention)."; :>> discoveredInField = true; :>> relatedTask = "timestampSettingsUx"; :>> severity = Severity::Low; }
    #Resolves dependency from timestampSettingsUx to issueTimestampSettingsVerboseUx;

    // Owner-directed 2026-08-03 (follow-up + screenshot): little-X removes, a default-collapsible timestamp
    // section, move Reconfigure/Disconnect up, brief store-password, and 'the "X synced" collapse looks
    // really bad' — 'research canonical ways ... don't reinvent'.
    part issueSettingsUxPolish : Issue { :>> id = "28fb6ca7-5024-4f91-c7b3-16ad04f13bb5"; :>> title = "Settings UX rough edges: verbose store-password, huge Remove buttons, an orphaned/ugly collapse widget, buried Reconfigure/Disconnect"; :>> createdAt = "2026-08-03"; :>> createdBy = "wweatherholtz"; :>> description = "Owner-directed settings polish (with a mobile screenshot): (1) the per-row 'Remove' buttons on the date-field / excluded-folder lists were huge — replace with a little X; the lists are easily restorable so no scary warning; (2) the Timestamp-changes section should be COLLAPSIBLE (default collapsed — not seen most of the time); (3) the synced-plugin list's collapse rendered as an ORPHANED raw <details> disclosure triangle floating between cards ('looks really bad ... must be a better way'); the owner directed 'research canonical ways ... don't reinvent'; (4) move the Reconfigure/Disconnect item UP from Advanced into the top Connection area; (5) the store-password description was a wall of text — make it brief per human factors. FIX (settingsUxPolish 1.12.8, client-only): little-X via Obsidian's canonical addExtraButton().setIcon('x') (confirmed the canonical icon-action idiom); a collapsible() helper built from Obsidian's OWN documented components — Setting().setHeading() (the canonical section-heading, per the API docs) + a native lucide chevron via setIcon() + a body toggle — NOT a custom disclosure widget (researched: Obsidian has no native collapsible-group API, SettingGroup v1.11.0 has no collapse; setHeading + native chevron is the community idiom); used for BOTH the plugin list (fixing the orphaned triangle) and the default-collapsed Timestamp section; Reconfigure/Disconnect moved into fillStatus (top Connection group); store-password desc cut to one line. Guards: settings-ui.dom 'the Timestamp changes section is a collapsible (default collapsed) that toggles on header click' + the existing timestamp add/remove-list tests (the little-X extra-button is clickable); obsidian-stub gained ExtraButtonComponent + addExtraButton. discoveredInField=true (owner). Severity Low (UX)."; :>> discoveredInField = true; :>> relatedTask = "settingsUxPolish"; :>> severity = Severity::Low; }
    #Resolves dependency from settingsUxPolish to issueSettingsUxPolish;

    // Owner-reported 2026-08-03 (screenshot, on 1.12.8): 'dropdown looks the same, not like a heading' — the
    // 1.12.8 collapse header didn't render as a heading.
    part issueCollapseHeaderNotHeading : Issue { :>> id = "4abd8ec9-7246-4d13-e9d7-38cf26135df8"; :>> title = "The collapsible section header (1.12.8) rendered as a plain small row, not a heading — setHeading() was called without setName()"; :>> createdAt = "2026-08-03"; :>> createdBy = "wweatherholtz"; :>> description = "Follow-up to settingsUxPolish (1.12.8). The collapsible() helper called new Setting(c).setHeading() but built the label from a MANUAL createSpan instead of setName(title), so Obsidian's heading styling (which targets the .setting-item-name text) never applied — the 'N synced' / 'Timestamp changes' collapse headers rendered as small dim rows, not headings (owner screenshot: 'dropdown looks the same, not like a heading'). FIX (collapseHeaderFix 1.12.9, client-only): use the canonical new Setting(c).setName(title).setHeading() (styles the name as a heading), insert the native lucide chevron BEFORE the title (section-collapse convention), + a styles.css safety (.selfsync-collapse-header .setting-item-name { font-weight: 600 }) so it reads as a heading even on themes that render .setting-item-heading subtly. Guard: settings-ui.dom 'the Timestamp changes section is a collapsible ...' still green (header found by text + toggles). discoveredInField=true (owner). Severity Low (UX)."; :>> discoveredInField = true; :>> relatedTask = "collapseHeaderFix"; :>> severity = Severity::Low; }
    #Resolves dependency from collapseHeaderFix to issueCollapseHeaderNotHeading;
    part issueCollapseStillNotHeadingMobile : Issue { :>> id = "7de0fb1c-a579-4e46-0af0-61fb48368a0b"; :>> title = "The 1.12.9 setName().setHeading() collapse header STILL rendered as a small dim row (not a heading) on mobile — an inline setting-item-heading is styled far more subtly than the SettingGroup section headings"; :>> createdAt = "2026-08-03"; :>> createdBy = "wweatherholtz"; :>> description = "Follow-up to collapseHeaderFix (1.12.9). The owner hard-restarted Obsidian (confirming 1.12.9 was actually running, ruling out a stale-plugin/mobile-restart cause) and reported the '7 synced' collapse STILL looked the same — a small dim row, not a section heading like 'Synced community plugins'/'Advanced'. Root cause: 1.12.8/1.12.9 built the header from Setting().setHeading() — an inline heading ROW (.setting-item-heading) — but the prominent section headings the owner compares against are SettingGroup headings, which mobile themes style much more prominently; no setName()/font-weight tweak could match them. FIX (collapseHeaderGroupFix 1.12.10, client-only): render the collapsible() header as a real new SettingGroup(c).setHeading(title) — the SAME component as the other section headings — and toggle the group's public listEl as the body (heading reached via listEl.previousElementSibling; chevron prepended). Guard: settings-ui.dom collapse test updated to the SettingGroup heading + listEl toggle (green). discoveredInField=true (owner). Severity Low (UX)."; :>> discoveredInField = true; :>> relatedTask = "collapseHeaderGroupFix"; :>> severity = Severity::Low; }
    #Resolves dependency from collapseHeaderGroupFix to issueCollapseStillNotHeadingMobile;
    part issuePluginWiringTimerLeak : Issue { :>> id = "8ef1c2b0-5d3a-4f61-b0c2-91fe4d2a7b30"; :>> title = "plugin-wiring.test.ts intermittently failed 'D0047 guard is SERVER-qualified' — a leaked reconnect/poll window-timer from a prior test fired mid-assertion and re-stamped baseVaultKey (test-isolation flake)"; :>> createdAt = "2026-08-03"; :>> createdBy = "claudeOpus"; :>> description = "Recurring flake (seen ~1 in 3 full-suite runs across the 1.12.6 and 1.13.0 sittings): the full client vitest reported '1 failed' in 'D0047 guard is SERVER-qualified' (plugin-wiring), always green in isolation and on re-run. Root cause: bootPlugin() schedules REAL Node window.setTimeout/setInterval (a reconnect backoff or a poll interval); if a test's plugin.onunload() misses one, that timer persists across tests (real timers aren't tied to the per-test window object) and fires during a LATER test, driving a stray reconnect that re-stamps settings.baseVaultKey mid-assertion. FIX (pluginWiringTimerLeakFix): TRACK every window timer a test schedules and force-clear all live ones in an afterEach — guaranteeing timer isolation regardless of whether every onunload path cleared its own timers (D0047: a correction becomes a permanent guard, here a test-harness guard). Verified by 3 consecutive full-suite runs green. Severity Low (test reliability, not product)."; :>> discoveredInField = false; :>> relatedTask = "pluginWiringTimerLeakFix"; :>> severity = Severity::Low; }
    #Resolves dependency from pluginWiringTimerLeakFix to issuePluginWiringTimerLeak;
    part issueCollapseChevronDetached : Issue { :>> id = "9f0a2d31-6e4b-4c72-a1d3-b2e5f60c8a41"; :>> title = "The 1.12.10 SettingGroup collapse placed its chevron by guessing the heading DOM (listEl.previousElementSibling) — wrong on mobile Obsidian, so the chevron rendered detached inside the list card and the label didn't toggle"; :>> createdAt = "2026-08-03"; :>> createdBy = "wweatherholtz"; :>> description = "Follow-up to collapseHeaderGroupFix (1.12.10). Making the collapse header a real SettingGroup heading fixed its APPEARANCE, but the chevron + click were placed by guessing the heading element via group.listEl.previousElementSibling. That guess is wrong on mobile Obsidian's SettingGroup DOM: the chevron got inserted into the list container (rendered at the top-left of the card, divorced from the '7 synced' label) and the click bound to the wrong element, so tapping the label did nothing (owner screenshot: 'the X synced label isn't actually associated with the dropdown'). FIX (collapseChevronFix 1.14.1, client-only): add the chevron via addExtraButton — the DOCUMENTED way to put a control in a SettingGroup heading — so it lands IN the heading next to the label with no DOM guessing; the whole heading row toggles, derived from the button via the stable .setting-item class; degrades gracefully (the chevron button itself toggles even if the row-click derivation fails). obsidian-stub updated to model SettingGroup.addExtraButton in the heading. Guard: settings-ui.dom collapse test green. discoveredInField=true (owner). Severity Low (UX)."; :>> discoveredInField = true; :>> relatedTask = "collapseChevronFix"; :>> severity = Severity::Low; }
    #Resolves dependency from collapseChevronFix to issueCollapseChevronDetached;
    part issueConnectionRowButtonOverflow : Issue { :>> id = "b1c2d3e4-6f70-4a81-b2c3-d4e5f6a7b8c9"; :>> title = "1.15.0 Connection Server row: the long server URL sat inline with the Setup/Disconnect buttons and pushed Disconnect off the card on mobile"; :>> createdAt = "2026-08-04"; :>> createdBy = "wweatherholtz"; :>> description = "Owner-reported on 1.15.0 (mobile screenshot): the Server fact row rendered the value (a long https:// URL) as an inline control-area span alongside the Setup + Disconnect buttons; on a narrow screen the URL consumed the width and pushed 'Disconnect' past the card's right edge. Short values (username, vault name) fit, so only the long-URL Server row overflowed. FIX (connectionRowOverflowFix 1.15.1, client-only): factRow renders each fact's value as the row DESCRIPTION (full-width, wraps) instead of an inline value competing with the buttons — the control row then holds only the action buttons; robust for any long value. Retired the unused .selfsync-value CSS. Guard: settings-ui.dom green. discoveredInField=true (owner). Severity Low (UX)."; :>> discoveredInField = true; :>> relatedTask = "connectionRowOverflowFix"; :>> severity = Severity::Low; }
    #Resolves dependency from connectionRowOverflowFix to issueConnectionRowButtonOverflow;
    part issuePluginDirectionInert : Issue { :>> id = "c2d3e4f5-7081-4b92-c3d4-e5f6a7b8c9d0"; :>> title = "The per-plugin config-sync direction dropdown ('Use server's'/'Use this device's') was INERT for an already-synced plugin — it only governed a no-base first contact, so flipping it did nothing, silently (an honest-status / L-5 gap)"; :>> createdAt = "2026-08-04"; :>> createdBy = "wweatherholtz"; :>> description = "Owner-identified: the per-plugin first-contact direction dropdown implied a live 'which copy wins' switch, but configAutoResolveChoice only consults the direction when a divergence has NO common base (reason=='conflict-copy'). An already-synced plugin HAS a shared base, so its ongoing changes reconcile via merge/edit-wins and the direction is never used — flipping the dropdown changed nothing, with no feedback. That is exactly the misleading-UX the nHonestStatus Need (STPA L-5) is about. FIX (pluginPushPull 1.16.0, client-only, owner chose option #1): replace the dropdown (for an installed+synced plugin on a read-write vault) with explicit PUSH (make the server + other devices match this device's copy) / PULL (replace this device's copy with the server's) actions — confirmed authoritative overwrites scoped to .obsidian/plugins/<id>/, over the union of local+server files (pluginFilePaths), reusing the tested resolveConfigConflict. Independent critique run: hardened the self-folder guard to the shared case-insensitive+legacy isSelfPluginId (forcePlugin bypasses shouldSync) and made partial-failure reported not swallowed. Guards: pluginFilePaths + isSelfPluginId pure tests + settings-ui.dom Push/Pull wiring; full client vitest 589. discoveredInField=true (owner). Severity Low (UX/behavior)."; :>> discoveredInField = true; :>> relatedTask = "pluginPushPull"; :>> severity = Severity::Low; }
    #Resolves dependency from pluginPushPull to issuePluginDirectionInert;
    part issueDeletionProvenanceUnnotified : Issue { :>> id = "d3e4f5a6-8192-4ca3-d4e5-f6a7b8c9d0e1"; :>> title = "Source-driven config-change notifications (1.18.0) don't cover a peer's config/plugin DELETION — the Deletion wire type carries no provenance"; :>> createdAt = "2026-08-05"; :>> createdBy = "claudeOpus"; :>> description = "Surfaced by the independent security critique of changeProvenanceNotify (1.18.0, finding 6). The new source-driven reload notice attributes and notifies on ADD/EDIT config changes (each carries author/device provenance via FileMeta), but a peer DELETING a synced config file, CSS snippet, or plugin folder is applied on this device with NO notice: io.remove never marks pendingReload, and the Deletion protocol record ({path, version}) has no author/device fields to attribute it anyway. Partly pre-existing (deletions were never notified — there was no source-notification before this feature), so NOT a regression; it's a coverage boundary of the new capability. A follow-up (deletionProvenanceNotify) would add provenance to the server's Deletion record + a delete-path notice keyed on the same shouldNotifyConfigChange rule. discoveredInField=false (critique-found). Severity Low (a missed notice on a rarer event; no data risk — the deletion itself still reconciles correctly)."; :>> discoveredInField = false; :>> relatedTask = "deletionProvenanceNotify"; :>> severity = Severity::Low; }
    #Resolves dependency from deletionProvenanceNotify to issueDeletionProvenanceUnnotified;
    part issueUpsertProvenanceNotMapped : Issue { :>> id = "2e975afe-e745-43c6-8146-b53a68deec6c"; :>> title = "validateChanges discarded validateFileMeta's camelCase mapping (forEach), so an upsert's deviceId/deviceName never reached the notify path — masked because notify keys mainly on author"; :>> createdAt = "2026-08-14"; :>> createdBy = "claudeOpus"; :>> description = "Found while implementing deletionProvenanceNotify. validateChanges did `c.upserts.forEach(validateFileMeta)` — forEach DISCARDS the returned mapped object, so the ChangesResponse kept the RAW wire upserts (snake_case device_id/device_name). recordIncomingConfig then read meta.deviceId (camelCase) = undefined, so an incoming upsert's DEVICE provenance was always undefined. Masked because shouldNotifyConfigChange keys mainly on `author` (same key on wire + TS), which DID flow through — so the 1.18.0 notify feature worked on author but the userDevice-mode own-other-device gating silently degraded to always-notify (deviceId unknown). FIX (part of deletionProvenanceNotify): validateChanges now `c.upserts = c.upserts.map(validateFileMeta)` (+ maps deletes), so deviceId/deviceName reach consumers. Behavior change: userDevice mode is now device-accurate (was over-notifying). discoveredInField=false. Severity Low (author-based notify always worked; only the secondary device gating degraded)."; :>> discoveredInField = false; :>> relatedTask = "deletionProvenanceNotify"; :>> severity = Severity::Low; }
    #Resolves dependency from deletionProvenanceNotify to issueUpsertProvenanceNotMapped;
    part issueOptionalResponseFieldGates : Issue { :>> id = "0f199d1a-53c1-41be-b2e0-7bf424aa0fb4"; :>> title = "The wire-compat gate treats an OPTIONAL response field the client added (that an older server lacks) as BREAKING — a newer client hard-blocks sync against an older / mid-redeploy server"; :>> createdAt = "2026-08-15"; :>> createdBy = "wweatherholtz"; :>> description = "OWNER FIELD REPORT (2026-08-15): after updating BOTH server and client to 1.29.0, the client refused to sync — 'the server dropped Deletion.author/device_id/device_name, which this plugin reads. Update whichever is older.' Those are the OPTIONAL provenance fields the 1.29 client itself added (read undefined-safe). ROOT CAUSE: diffSignature's RESPONSE branch flagged ANY field in the client's embedded signature that the server lacks as breaking, REGARDLESS of `required`. So a NEWER client (which added optional response fields) hard-blocks sync against an OLDER server — or, transiently, a server MID-REDEPLOY (the log showed a block at 12:37 then a clean sync at 12:38 once the new image was live). This BROKE backward compatibility (a 1.29 client cannot sync with any pre-1.29 server) and made the deletion-provenance rollout require a lock-step update. Secondary: the message 'Update whichever is older' never says WHICH side. FIX (client-only): an optional (required:false) response field the server lacks is NON-breaking (the client degrades to undefined) — only a REQUIRED one gates; a guard test allowlists every optional response field as undefined-safe so a future one forces review; and a directional hint tells the user which side is likely older (server-lacks → server, hedged for the just-updated case; server-demands → plugin). discoveredInField=true. Severity High (blocks ALL sync against an older/mid-redeploy server; a backward-compat regression from 1.29.0)."; :>> discoveredInField = true; :>> relatedTask = "optionalResponseFieldNonGating"; :>> severity = Severity::High; }
    #Resolves dependency from optionalResponseFieldNonGating to issueOptionalResponseFieldGates;
    part issueDeclinedPluginNoticeSpam : Issue { :>> id = "a9694924-d938-4253-b3e4-683b0251ba5c"; :>> title = "The 'N community plugins on the server aren't in your sync selection' notice re-logs on nearly every poll/reconnect (de-duped on the volatile file list, not the plugin set)"; :>> createdAt = "2026-08-15"; :>> createdBy = "wweatherholtz"; :>> description = "OWNER REQUEST (2026-08-15): 'I don't want tons of messages when there are many pending server-side plugins available. just one indicating there are pending plugins will do.' noteDeclined de-duped on `paths.sort().join('|')` — the raw declined FILE list, which differs between the full pass (all declined files) and each delta pass (only the changed declined subset), so the sig changed almost every pass and it re-logged. FIX (client-only): fire onDeclined ONLY from the FULL pass (reconcileAll; the delta's partial view churned it); de-dup on the stable PLUGIN SET (sorted ids + a config-files flag); and simplify to a COUNT ('7 community plugins ... aren't synced to this device — enable them in Settings') instead of the full list. discoveredInField=true. Severity Low (log noise; no data impact)."; :>> discoveredInField = true; :>> relatedTask = "declinedPluginNoticeCoalesce"; :>> severity = Severity::Low; }
    #Resolves dependency from declinedPluginNoticeCoalesce to issueDeclinedPluginNoticeSpam;
    // ===== 3-lens independent critique of the shipped 1.29.x cluster (2026-08-15). =====
    part issueHeldResolverWholeScopeClear : Issue { :>> id = "0617f13c-4667-496f-96c7-d8bb4b8976f0"; :>> title = "A held-review resolver clears the WHOLE pending set (delete(scope)), so a deletion a reconcile ADDED while the resolver's task was queued silently vanishes from the review"; :>> createdAt = "2026-08-15"; :>> createdBy = "claudeOpus"; :>> description = "Concurrency-lens critique of the 1.29.x cluster (MEDIUM; worsened by the 1.29.1 serialization). acceptBulkDeletions/keepBulkDeletions + acceptBulkPushes/keepBulkPushes ran pendingBulk*.delete(scope) in their tail - clearing the ENTIRE scope, not the applied snapshot. Because the resolver's base mutation now DEFERS behind an in-flight reconcile (the engine task queue), that reconcile can setPendingBulk(authoritative) a NEW held path B before the tail runs, and the blanket delete(scope) then wipes B from the Conflicts review (B's toast already fired). B is NOT wrongly deleted (safe direction - never passed to io.remove), but it disappears from review until the next full scan (~15 min), a trust defect for a data-safety gate. FIX: clearHeldPaths subtracts ONLY the applied snapshot; a mid-resolve-added held path survives. discoveredInField=false. Severity Medium (review-surface data-integrity; no file loss)."; :>> discoveredInField = false; :>> relatedTask = "cluster129CritiqueHardening"; :>> severity = Severity::Medium; }
    #Resolves dependency from cluster129CritiqueHardening to issueHeldResolverWholeScopeClear;
    part issueProvenanceMigrationNonAtomic : Issue { :>> id = "fb1e0fa0-e87d-48f1-b9aa-cdf5f4c26f68"; :>> title = "The provenance-column migration ran three autocommit ALTERs gated by a SINGLE-column probe — a crash between them permanently bricks the commit/delete path"; :>> createdAt = "2026-08-15"; :>> createdBy = "claudeOpus"; :>> description = "Mixed-fleet/migration-lens critique of the 1.29.x cluster (MEDIUM, F1). migrate() added the three author_* columns to `files` (v2) / `deletions` (v3) as three separate autocommit conn.execute ALTERs, gated by one probe on author_user. A crash between them (a rolling-redeploy SIGKILL, OOM, or power loss on consumer hardware - the case synchronous=FULL exists for) leaves author_user present + the other two missing, the single-column probe PERMANENTLY satisfied, schema_version stamped to CURRENT, and every commit/delete INSERT (which references all columns) 500'ing forever with 'no such column' and NO self-heal. FIX: ensure_provenance_columns adds each column under its OWN pragma_table_info probe (idempotent), so a partially-migrated table self-heals on the next open (migrate runs every open). Covers both files + deletions. discoveredInField=false. Severity Medium (rare crash window, but a permanently bricked vault needing manual DB surgery)."; :>> discoveredInField = false; :>> relatedTask = "cluster129CritiqueHardening"; :>> severity = Severity::Medium; }
    #Resolves dependency from cluster129CritiqueHardening to issueProvenanceMigrationNonAtomic;
    part issueConfigDeletionMultiSourceUnderreport : Issue { :>> id = "c55c4b46-e716-4e64-99bc-5803404b56ff"; :>> title = "flushConfigDeletions names one source but drops a SECOND peer's deletions from the same pass (under-report)"; :>> createdAt = "2026-08-15"; :>> createdBy = "claudeOpus"; :>> description = "Data-safety-lens critique of the 1.29.x cluster (LOW-1). When two peers each delete synced config files in ONE reconcile pass, flushConfigDeletions named the first notifying source + counted only that source's removals, then cleared the pending map - so the second peer's deletion was neither counted nor announced and never re-fired. Notice-only (the files were already correctly removed). FIX: count per source and fire ONE notice covering ALL notifying sources ('N synced config files removed by alice (2), bob (1)'). discoveredInField=false. Severity Low (missed attribution on a rare multi-peer pass; no data impact)."; :>> discoveredInField = false; :>> relatedTask = "cluster129CritiqueHardening"; :>> severity = Severity::Low; }
    #Resolves dependency from cluster129CritiqueHardening to issueConfigDeletionMultiSourceUnderreport;
    part issueSchemaRollbackOpaque500 : Issue { :>> id = "bb6761b0-b62c-41c8-861a-a5c6bda6c472"; :>> title = "A v3->v2 server rollback is correctly refused but surfaces to the client as an opaque HTTP 500 on every route incl. /status — the clear 'newer schema' message lives only in the server log"; :>> createdAt = "2026-08-15"; :>> createdBy = "claudeOpus"; :>> description = "Mixed-fleet-lens critique of the 1.29.x cluster (LOW/MEDIUM, F2; DEFERRED). The v3 downgrade guard returns ErrorKind::Unsupported and Vault::open hard-refuses (correct - NOT quarantine, so no tombstone-destroying reindex + no data loss). But the caller maps it to AppError::Internal -> a generic 500. /status itself opens the vault, so it 500s too -> the client never gets a StatusResponse, the wire gate never runs, and the directional 'which side is older' hint can't fire in the one case (a rollback) an operator most needs it. The self-hoster sees a dead server with an undiagnosable client-side 'server error'; the clear message ('index written by a NEWER server ... upgrade the server binary') is only in the server log. FIX (deferred, server change): map ErrorKind::Unsupported to a DISTINCT AppError (e.g. a 503 carrying the message) that the client surfaces, so a rollback is self-diagnosing. discoveredInField=false. Severity Low (rare deliberate operator rollback; no data loss - only a log-dive to diagnose)."; :>> discoveredInField = false; :>> relatedTask = "schemaRollbackClearError"; :>> severity = Severity::Low; }
    #Resolves dependency from schemaRollbackClearError to issueSchemaRollbackOpaque500;
    // ===== Critique of the schema-rollback 503 fix (5effd75), 2026-08-16. =====
    part issueSchemaDowngradeMsgLengthCoupling : Issue { :>> id = "df798054-f6c7-48b6-aba5-8dfdafd0bad1"; :>> title = "The schema-downgrade 503 body (~276 chars) sat just under the client's 300-char plain-text cap with no test — a reword could silently re-hide the rollback as an opaque 'HTTP 503'"; :>> createdAt = "2026-08-16"; :>> createdBy = "claudeOpus"; :>> description = "Critique of 5effd75 (MEDIUM). The client (transport.ts errText) surfaces a server error body only when .length <= 300, else it shows the opaque 'HTTP 503' fallback. The schema-downgrade message was ~276 chars - 24 chars of headroom - and NOTHING tested the cross-language coupling (the Rust test even asserted the body was LONG). A future editor lengthening the message would keep all Rust tests green while silently reverting the rollback to an undiagnosable 503. FIX (server-only): shortened the body to ~190 chars, extracted it to a SCHEMA_DOWNGRADE_MSG const, and pinned its length (<= 260 chars) in the mapping test with a comment naming the client's 300-char errText cap both ways. discoveredInField=false. Severity Medium (would silently defeat the just-shipped self-diagnosing-rollback fix)."; :>> discoveredInField = false; :>> relatedTask = "schemaDowngradeMsgHardening"; :>> severity = Severity::Medium; }
    #Resolves dependency from schemaDowngradeMsgHardening to issueSchemaDowngradeMsgLengthCoupling;
    part issueAdminHealthMislabelsRollback : Issue { :>> id = "5232162f-fbf9-4711-97be-8d8f2c289e80"; :>> title = "The admin vault-health view reports a rolled-back (schema-too-new) vault as 'missing' — the operator's diagnostic surface mislabels an intact-but-needs-newer-server vault"; :>> createdAt = "2026-08-16"; :>> createdBy = "claudeOpus"; :>> description = "Critique of 5effd75 (LOW, DEFERRED; pre-existing - not introduced by that commit). admin.rs vault_health maps ANY st.vault() open Err - including the schema-downgrade ErrorKind::Unsupported - to 'missing'. So GET /api/admin/vaults, where an operator inspects fleet health, reports an intact but rolled-back vault as MISSING (it exists; it just needs a newer server). The sync-client 503 fix self-diagnoses for the USER but doesn't extend to the ADMIN view. A correct fix needs a NEW health status (e.g. 'incompatible'/'needs-newer-server') surfaced through the admin/settings UI - mapping it to the existing 'error' would wrongly advise 'run reindex', which the downgrade guard exists to prevent (reindex would destroy tombstones). Deferred (a small new-status feature across server + client rendering, not a trivial map change). discoveredInField=false. Severity Low (operator-diagnostic clarity; no data impact; the user-facing sync path already self-diagnoses)."; :>> discoveredInField = false; :>> relatedTask = "adminHealthRollbackStatus"; :>> severity = Severity::Low; }
    #Resolves dependency from adminHealthRollbackStatus to issueAdminHealthMislabelsRollback;
    part issueRollback503GenericWrapper : Issue { :>> id = "2623f29f-9891-4853-9ad2-b136004b35f8"; :>> title = "A 503 from /status (server can't open the vault — rollback / poisoned lock) was shown as the generic 'Can't reach the server (…). Retrying…', burying the server's clear operator message"; :>> createdAt = "2026-08-16"; :>> createdBy = "claudeOpus"; :>> description = "Critique of 5effd75 (LOW). The schema-rollback 503 body IS a clear operator message, but the client showed 'Can't reach the server (<body>). Retrying…' — factually off (the server DID respond) and it buries a clear instruction inside a transient 'can't reach' frame. Contrast the corrupt-index case, which throws a synthetic ServerDegraded with a clean, purpose-written lastIssue that doConnect preserves. FIX (client-only): establishSession detects a 503 from /status (keys on status===503, NOT fragile body-text matching) and throws a synthetic ServerDegraded carrying the body verbatim, so doConnect preserves it and the operator sees the real reason. Covers the rollback AND the poisoned-lock 503 (both carry a clear body). discoveredInField=false. Severity Low (message clarity; the info already surfaced, just wrapped)."; :>> discoveredInField = false; :>> relatedTask = "rollback503CleanMessage"; :>> severity = Severity::Low; }
    #Resolves dependency from rollback503CleanMessage to issueRollback503GenericWrapper;
    part issueSettingsScrollResetsOnToggle : Issue { :>> id = "e4f5a6b7-9203-4db4-e5f6-a7b8c9d0e1f2"; :>> title = "Toggling a setting (e.g. a community-plugin checkbox) resets the settings page scroll to the TOP"; :>> createdAt = "2026-08-05"; :>> createdBy = "wweatherholtz"; :>> description = "Owner-reported: 'most of the time when I click an option, a slide toggle on community plugins for example, it resets the settings page to the top.' Root cause: many settings handlers (the config-sync surface toggles, the community-plugin checklist) call this.display() to reflect the new state, and display() does containerEl.empty() + a full rebuild of the whole tab — which discards the scroll position, jumping the page to the top. The Status hero already avoids this (FSM ticks refresh JUST its row via fillStatus, per the display() comment), but the toggle handlers do a whole-tab rebuild. FIX (settingsScrollPreserve 1.21.1, client-only): preserve scroll ACROSS the rebuild in ONE place — display() captures the scrolling ancestor's scrollTop before empty() (via scrollEl(), walking up for the overflow:auto/scroll ancestor) and restores it after (sections rebuild at the same heights). Centralised in display() so EVERY re-render is covered structurally, not by per-handler vigilance (D0047: the control is the single choke point, not manual care). Not unit-testable in happy-dom (no layout → no real scroll), so verified by reasoning + on-device; the structural centralisation IS the durable guard. discoveredInField=true (owner). Severity Low (UX — no data risk)."; :>> discoveredInField = true; :>> relatedTask = "settingsScrollPreserve"; :>> severity = Severity::Low; }
    #Resolves dependency from settingsScrollPreserve to issueSettingsScrollResetsOnToggle;
    part issuePushPullDisabledStillClickable : Issue { :>> id = "f5a6b7c8-a304-4ec5-f6a7-b8c9d0e1f2a3"; :>> title = "The 1.21.2 'disabled' Push/Pull buttons were greyed but STILL CLICKABLE — setDisabled doesn't block clicks on an extra-button"; :>> createdAt = "2026-08-05"; :>> createdBy = "wweatherholtz"; :>> description = "Owner-reported on 1.21.2 (pushPullDisableInactionable): 'the push and pull buttons are grayed, but clickable. they should be disabled/unclickable.' Root cause: ExtraButtonComponent.setDisabled only adds an is-disabled CLASS to the button's div/anchor (it is NOT a native <button disabled>), so it greys the control but does NOT prevent the registered onClick from firing; the act() guard made the click a no-op, but the button still FELT interactive (hover / cursor / click feedback). This was the exact 'setDisabled doesn't block the click' caveat the earlier grey-out critique had flagged, resurfaced when the owner reversed the hint to a hard disable. FIX (pushPullDisableInert 1.21.3, client-only): when converged, ALSO set pointer-events:none on the button element, making it genuinely INERT (no click, no hover) — a real disabled control; the act() guard stays as defense-in-depth. GUARD (D0047): the settings-ui.dom test now asserts the converged button's style.pointerEvents === 'none' (not merely that a click no-ops), so a regression back to greyed-but-clickable is caught automatically. discoveredInField=true (owner). Severity Low (UX)."; :>> discoveredInField = true; :>> relatedTask = "pushPullDisableInert"; :>> severity = Severity::Low; }
    #Resolves dependency from pushPullDisableInert to issuePushPullDisabledStillClickable;
    part issueMountBaseIsolation : Issue { :>> id = "a6b7c8d9-b405-4fd6-a7b8-c9d0e1f2a3b4"; :>> title = "Composed-vaults mount correctness depends on each mount getting its OWN BaseStore + SyncState + cursor — the pure MountedIo/MountedApi adapters cannot enforce it, and a SHARED base would cause a phantom mass-delete"; :>> createdAt = "2026-08-07"; :>> createdBy = "claudeOpus"; :>> description = "Surfaced by the independent security critique of mountIoAdapters (composed-vaults Phase 2, finding C1 HIGH). The MountedIo/MountedApi adapters re-key a mount into mount-relative path space, but reconcileAll's path universe is (local ∪ remote ∪ base.paths()). If the Phase-3 mount engine wiring hands a mount the PRIMARY scope's BaseStore/SyncState (full-vault paths) instead of a fresh mount-scoped one, every primary path would read as local-absent + base-present under the mount's re-keyed io/api → a phantom mass delete-local/delete-remote (the delete-guard may or may not catch it). The pure adapters CANNOT defend this — base/state are injected by the caller — so it is a load-bearing WIRING invariant: the mount engine MUST allocate each mount its own persisted base + cursor + subscription, verified in the wiring increment's tests. Marked by a load-bearing invariant comment at the head of mountio.ts. discoveredInField=false (critique-found). Severity High (silent bulk data loss if the wiring gets it wrong — a design hazard for the not-yet-built engine, not a defect in shipped behavior). Resolver: the mountEngine action (Phase 3), which allocates + tests per-mount base/state isolation."; :>> discoveredInField = false; :>> relatedTask = "mountEngine"; :>> severity = Severity::High; }
    #Resolves dependency from mountEngine to issueMountBaseIsolation;
    part issueMountResetDetection : Issue { :>> id = "b7c8d9e0-c506-4a17-b8c9-d0e1f2a3b4c5"; :>> title = "A composed-vault SYNC mount does not run D0019 deletion-history-reset detection (reset hardcoded false, onKeptAbsent only logged), so it could resurrect a peer's deleted file into the shared source on a source history prune"; :>> createdAt = "2026-08-08"; :>> createdBy = "claudeOpus"; :>> description = "Surfaced by hardening Round 2 (data-integrity critique, finding F3). The primary sync computes a `reset` from the server's history_floor (D0019) and batches onKeptAbsent for user review; the mount sync loop (mountsync.ts) hardcodes reset:false. So on a SYNC mount, if the SOURCE vault prunes its deletion history past a file's tombstone, a local-present/base-present/remote-absent/no-tombstone file takes the restore (keep+push) path and RE-UPLOADS a file the source owner deleted, back into the shared source. R2 MITIGATED the SILENCE by wiring onKeptAbsent (a toast + log) so the keep/restore is now visible, not silent — and a PULL mount cannot resurrect at all (read-only). The residual (unfixed) is the AUTOMATIC re-upload on a sync mount under a source history reset. FULL FIX: port D0019 to the mount — persist a per-mount history floor + last-version (like the primary's historyFloors, keyed by mountKey), detect a reset from the mount's ChangesResponse.history_floor, and on a suspected reset route kept-absent files to a user-reviewed batch instead of auto-restoring. Low probability (needs a source-side history prune past the horizon + a sync mount holding the file) + now visible via onKeptAbsent, so tracked as a follow-up rather than a v1 blocker. discoveredInField=false (critique-found). Severity Medium (data resurrection into a shared resource on a sync mount; bounded + now-visible)."; :>> discoveredInField = false; :>> relatedTask = "mountResetDetection"; :>> severity = Severity::Medium; }
    #Resolves dependency from mountResetDetection to issueMountResetDetection;
    part issueMountCrossBoundaryMove : Issue { :>> id = "c8d9e0f1-d607-4b28-c9d0-e1f2a3b4c5d6"; :>> title = "Moving a file OUT of a SYNC-mount folder deletes it from the (possibly another user's) SOURCE vault, and moving one IN removes it from the primary — correct sync semantics but a surprising, unconfirmed cross-boundary data flow"; :>> createdAt = "2026-08-08"; :>> createdBy = "claudeOpus"; :>> description = "Surfaced by hardening Round 5 (security/holistic critique, finding MED-2). A composed mount and the primary are disjoint scopes. Dragging a note OUT of a sync-mount folder (e.g. Work/ASI/note.md → Notes/note.md): the primary sees a create of the new path (fine); the mount sees Work/ASI/note.md become locally-absent with base+remote present → delete-local → on a SYNC mount that propagates as a delete-REMOTE to the source vault, removing the file from another user's shared vault. Moving one IN is the mirror (removed from the primary server, pushed to the source). It is TECHNICALLY CORRECT sync (the file left/entered the synced folder), and a single-file delete is below BULK_DELETE_RATIO so the delete-guard doesn't catch it — but it crosses a trust boundary from an innocuous local reorganization, without a rename/move detection or a confirmation. Only affects SYNC mounts (opt-in + warned; a PULL mount never pushes/deletes the source). MITIGATION now: documented as expected behavior in the sync-mount warning path; FULL FIX (follow-up): lightweight rename/move detection across the mount boundary, or a confirmation before a mount-driven delete-remote of a non-tombstoned file. discoveredInField=false (critique-found). Severity Medium (cross-user data deletion from an ordinary local move on a sync mount; bounded to opt-in sync mounts, semantically-correct, not a breach)."; :>> discoveredInField = false; :>> relatedTask = "mountMoveSafety"; :>> severity = Severity::Medium; }
    #Resolves dependency from mountMoveSafety to issueMountCrossBoundaryMove;
    part issueMountDormantStaleBase : Issue { :>> id = "d9e0f1a2-e708-4b39-d0e1-f2a3b4c5d6e7"; :>> title = "A mount that goes dormant because the PRIMARY switched onto its source vault, then reactivates after switching back, restores a STALE base — the primary mutated the folder during dormancy, so the mount reconciles against a stale ancestor (spurious conflict copies / mis-merge)"; :>> createdAt = "2026-08-10"; :>> createdBy = "claudeOpus"; :>> description = "Surfaced by hardening Round 8 (persistence/durability critique, finding F4). A mount whose source == the current primary vault is auto-dormant (R5-LOW-3, activeMounts excludes it). Sequence: mount vault B → folder X; user switches PRIMARY to B → the mount goes dormant AND the primary now syncs folder X against B, mutating disk; user switches primary back to A → the mount reactivates and restores its OLD persisted base (unchanged during dormancy) → base says hash H, disk is H' (changed by the primary), source is H'' → the mount's three-way reconcile runs against a STALE ancestor, producing spurious conflict copies / a mis-merge. The primary has a foreign-base guard (settings.baseVaultKey / vaultKeyMismatch) that wipes+rebuilds its base on a vault change; mounts have no analogous base-freshness/vault-identity stamp on restore. IMPACT: recoverable — conflict copies preserve both versions (preserveLocalFirstContact + conflict semantics), NOT silent loss — and it requires a specific switch-to-source-then-back sequence. FULL FIX (follow-up): stamp a per-mount base-validity marker (source cursor + a disk fingerprint or a primary-base generation counter) and force a fresh first-contact (empty base) when the mount was dormant while its folder was managed by another scope. discoveredInField=false (critique-found). Severity Low (rare sequence; recoverable conflict copies, not loss)."; :>> discoveredInField = false; :>> relatedTask = "mountBaseFreshness"; :>> severity = Severity::Low; }
    #Resolves dependency from mountBaseFreshness to issueMountDormantStaleBase;
    part issueMountDeleteGuardCalibration : Issue { :>> id = "e0f1a2b3-f809-4c40-e1f2-a3b4c5d6e7f8"; :>> title = "The bulk-delete guard is whole-vault-calibrated; on a small composed-vault mount SUBTREE it both over-blocks normal source deletions (mount never converges) and under-protects tiny mounts — a calibration/safety-posture decision"; :>> createdAt = "2026-08-10"; :>> createdBy = "claudeOpus"; :>> description = "Surfaced by hardening Round 9 (reconcile-engine-reuse critique, finding A). The shared reconcile bulk-delete guard (runDeleteGuard: acceptedBasePaths as the universe + the filtered manifest, BULK_DELETE_MIN=6 / BULK_DELETE_RATIO=0.5 + the empty-manifest override) is calibrated for a WHOLE VAULT, where an empty/high-ratio-delete manifest is a strong index-loss/attack signal. For a MOUNT SUBTREE those are NORMAL user actions, producing THREE mismatches: (1) empty-manifest override — a user emptying the mounted source folder makes remote.size===0 trip the override → every delete-local refused (reportGuard) → the mount keeps the deleted files forever, never mirrors the emptying; (2) RATIO=0.5 — deleting ≥half of a ≥6-file mount (routine for a small folder) trips guardBulkDelete → refused / non-convergent; (3) tiny mounts (<6 files) get NO ratio guard AND the cumulative DeleteRateGuard early-returns, so a partial drain is unguarded. This is a genuine SAFETY-POSTURE tradeoff — how aggressively should a mount propagate deletions from its source? — NOT a clear-cut bug, so it is SURFACED for the maintainer's decision rather than unilaterally changed (deletes are recoverable via .trash on desktop; the R4-F4 source-readiness check already guards the degraded/index-loss source case; the R2-F2 onGuard wiring makes a refusal visible). OPTIONS for the fix: (a) drop the empty-manifest override for a mount scope (empty subtree ≠ index loss) — converges but removes that index-loss belt for the mount; (b) scope-scale MIN/RATIO or add an absolute deletes>=MIN floor; (c) keep the conservative refuse+notify (current) and rely on remove+re-add to recover. discoveredInField=false (critique-found). Severity Medium (non-convergence of legit deletions + an under-protected tiny-mount drain; recoverable, gated by the readiness check + .trash + onGuard). RESOLVED by D0041 (bulkDeleteConfirm): the whole-vault ratio/empty heuristic is replaced by a user-configurable per-scope confirmation, so a small mount no longer false-fires and a legit bulk delete either applies below-threshold or is held for a one-click confirm."; :>> discoveredInField = false; :>> relatedTask = "bulkDeleteConfirm"; :>> severity = Severity::Medium; }
    #Resolves dependency from bulkDeleteConfirm to issueMountDeleteGuardCalibration;

    // ---- Owner field feedback on composed mounts + plugin-sync settings UX (2026-08-11, backlogged) ----
    part issueMountPathValidationAndDefaults : Issue { :>> id = "39b9629e-be99-4bb9-a172-1fdbbc34541c"; :>> title = "Composed-mount path handling lacks sane defaults: source subfolder is unvalidated free text (though the folder set is knowable), and the local target folder is only created lazily so an empty/mistyped source never materializes it"; :>> createdAt = "2026-08-11"; :>> createdBy = "wweatherholtz"; :>> description = "Owner field feedback on composed vaults. VERIFIED against code: (1) the add-mount source subfolder is a plain free-text input with NO existence check (mountsettings.ts:107-108); validateMounts only guards blank/.obsidian/overlap (mounts.ts:114-134). The source vault IS a real dropdown, but the subfolder within it is unconstrained. (2) The client CAN know the valid folders — a source-scoped changes(0) listing returns the file paths (transport.ts:271, mountio.ts:64) from which folders are derivable — but the mount UI never calls it, so a typo just pulls an empty set (and can trip the empty-subtree bulk-delete guard, main.ts:2257). (3) The local mount-point folder is created only LAZILY on the first file write (main.ts:251-252); if the source subtree is empty or mistyped, no write happens and the folder is never created. WANT: autofill/validate the source subfolder from the derived folder list so the user selects a KNOWN-VALID path; eagerly ensure the local mount point exists on add; warn/block a mount whose source matches nothing. CONFIRMED REPRO (2026-08-11, owner): a mount of source vault syncme subfolder B into vault asi (local syncme/B) did nothing — the source cursor advanced to v12 but base=0 because the B folder is EMPTY (syncme/A has notes, B has none), so the path filter matched zero files and the local syncme/B folder was never created; the owner got no feedback that B was empty or that 0 files matched (the path-filter code itself is correct). discoveredInField=true (owner). Severity Medium (silent empty pull + never-created folder + possible guard trip; recoverable)."; :>> discoveredInField = true; :>> relatedTask = "composedMountPathUx"; :>> severity = Severity::Medium; }
    #Resolves dependency from composedMountPathUx to issueMountPathValidationAndDefaults;
    part issueMountRoToRwChange : Issue { :>> id = "3e169a47-11d7-42bc-8a98-dbef789bbb4e"; :>> title = "No in-place change of a composed mount from read-only (pull) to read-write (sync) — only add + remove exist, and remove+re-add drops the persisted base/cursor"; :>> createdAt = "2026-08-11"; :>> createdBy = "wweatherholtz"; :>> description = "Owner wants to flip a mount RO to RW. VERIFIED: the only mount ops are addMount + removeMount (main.ts:2332-2349); there is no updateMount/setDirection (grep confirms). The settings row offers only remove (settings.ts:506) + an Add-a-mount button; the edit modal is add-only (mountsettings.ts:66-148). So the only way to change direction today is remove-and-re-add, which DROPS the mount persisted base/cursor (main.ts:2349) — a full re-sync from scratch. WANT: an in-place edit/permission-change that flips direction while keeping the mount base/state. discoveredInField=true (owner). Severity Low (missing feature; a lossy workaround exists)."; :>> discoveredInField = true; :>> relatedTask = "composedMountPermissions"; :>> severity = Severity::Low; }
    #Resolves dependency from composedMountPermissions to issueMountRoToRwChange;
    part issueMountRoLocalEditBehavior : Issue { :>> id = "adb6d95a-e702-41e3-8810-2dd05007c6a8"; :>> title = "A local edit to a read-only composed file (source unchanged) is kept on disk and only reported — it lingers as an un-syncable divergence that re-notifies every poll and never converges"; :>> createdAt = "2026-08-11"; :>> createdBy = "wweatherholtz"; :>> description = "Owner asked what happens when RO is selected and the file is changed in the parent vault. VERIFIED: for a pull (read-only) mount, a local edit whose source is unchanged yields action push, which finalize turns into reportReadOnly (reconcile.ts:79-81) executed as onReadOnly only (reconcile.ts:1131-1133) — the edit is NOT pushed (RO honored), NOT reverted, NOT copied; it stays on disk as a silent local divergence, and every poll re-hits push->reportReadOnly (re-notify, never converge). A conflict copy is created only IF the source ALSO later diverges (planMerge readOnlyKeepCopy, reconcile.ts:118,953-961). This is a design characteristic, not a guarded bug. WANT: a defined, user-legible outcome for an edit on a RO mount (e.g. offer discard-my-edit or fork-to-a-writable-copy, or make the non-syncing state unmistakable) rather than a perpetual silent divergence. discoveredInField=true (owner). Severity Medium (the user may believe an edit synced when it silently will not)."; :>> discoveredInField = true; :>> relatedTask = "composedMountPermissions"; :>> severity = Severity::Medium; }
    #Resolves dependency from composedMountPermissions to issueMountRoLocalEditBehavior;
    part issuePluginListHierarchy : Issue { :>> id = "3c6290bd-0467-43fe-9d76-7c16b2b590cb"; :>> title = "The synced-plugin list is a separate sibling collapsible from the Synced community plugins group, not nested under it — the two should be one hierarchy"; :>> createdAt = "2026-08-11"; :>> createdBy = "wweatherholtz"; :>> description = "Owner: listing the actual synced plugins should not be a separate dropdown from Synced community plugins; there should be a hierarchy. VERIFIED: renderPluginChecklist creates the Synced community plugins group (settings.ts:722) and then renderPluginRows builds the N-synced plugin list via collapsible, which opens its OWN new SettingGroup on the same parent container (settings.ts:790, 596) — so the list is a FLAT SIBLING of the community-plugins group, not a child. WANT: nest the synced-plugin list under the community-plugins section so the toggle owns its list (one hierarchy). discoveredInField=true (owner). Severity Low (UX/IA)."; :>> discoveredInField = true; :>> relatedTask = "pluginSyncSettingsHierarchy"; :>> severity = Severity::Low; }
    #Resolves dependency from pluginSyncSettingsHierarchy to issuePluginListHierarchy;
    part issueGreyedNoteWrongSection : Issue { :>> id = "cb36817d-37c3-4b4d-a10a-c2ca4d1a991c"; :>> title = "The Greyed Push/Pull = already in sync note is in the community-plugins summary group, one section above the collapsible list that actually holds the Push/Pull buttons it explains"; :>> createdAt = "2026-08-11"; :>> createdBy = "wweatherholtz"; :>> description = "Owner: the greyed push/pull = already in sync note is in the wrong section, but it is split out correctly in the plugin view. VERIFIED: the note (settings.ts:764-766) is added to the Synced community plugins summary group g, whereas the per-row Push/Pull extra-buttons it describes live in the SEPARATE N-synced collapsible list (settings.ts:828-829, grey-out at 830-843) — one section removed. The per-plugin PushPreviewModal already states it inline next to the disabled action (pushpreviewmodal.ts:39-40,59), which is the correct split-out the owner referenced. WANT: move the note adjacent to the Push/Pull controls (it naturally rides along once the list is nested per issuePluginListHierarchy). discoveredInField=true (owner). Severity Low (UX; explanatory note detached from its control)."; :>> discoveredInField = true; :>> relatedTask = "pluginSyncSettingsHierarchy"; :>> severity = Severity::Low; }
    #Resolves dependency from pluginSyncSettingsHierarchy to issueGreyedNoteWrongSection;

    // ---- D0042 wire-compat independent-critique follow-ups (backlogged 2026-08-11) ----
    part issueEndpointsRouterDrift : Issue { :>> id = "e9a15102-18a9-4ce6-bd6b-361697445092"; :>> title = "The wire-signature ENDPOINTS list is hand-maintained and the drift gate is generated FROM it, so it can silently diverge from the real axum router"; :>> createdAt = "2026-08-11"; :>> createdBy = "claudeOpus"; :>> description = "D0042 pre-ship critique finding F4 (MED). ENDPOINTS (server/src/wire_signature.rs) is a hand-written const; the CI drift gate committed_artifact_matches_generated only checks the committed JSON equals canonical_signature(), which is built FROM that same const — a tautology w.r.t. the router. Nothing cross-references ENDPOINTS against lib.rs build()'s actual routes. Consequence: remove a route but leave it in ENDPOINTS -> the signature still advertises it -> the client's diff sees it present -> proceeds -> the sync op 404s into a generic retry loop (the exact failure D0042 targets). Field-level TYPES are schemars-derived (safe); only the endpoint list is hand-maintained. FIX: a test that probes each ENDPOINTS path against the built router and asserts not-404 (405 method-mismatch is fine). discoveredInField=false (critique-found). Severity Medium (a future hand-maintenance drift, not a current defect; the list is correct today)."; :>> discoveredInField = false; :>> relatedTask = "wireSignatureCoverageHardening"; :>> severity = Severity::Medium; }
    #Resolves dependency from wireSignatureCoverageHardening to issueEndpointsRouterDrift;
    part issueSharingResponseTypesUncovered : Issue { :>> id = "624ad715-98d1-4efe-9fd1-0278d43fa17d"; :>> title = "Client-consumed sharing/admin response shapes (SharedVault, VaultShares, ShareLinkInfo) are outside the 13-type signature map, so a breaking change to them is not caught"; :>> createdAt = "2026-08-11"; :>> createdBy = "claudeOpus"; :>> description = "D0042 pre-ship critique finding F5 (LOW-MED). The signature types map covers the 13 core protocol types but the client also consumes SharedVault (GET /api/shared, POST /api/share-redeem), VaultShares (GET /api/admin/vaults), and ShareLinkInfo (GET /api/share-links) — covered only at the endpoint level, not field-level, and these are as-cast in the client with NO validate guard (unlike the core types). A breaking rename/retype there (e.g. redeemed_by -> redeemedBy, expires_at number -> string) passes the signature diff untouched and is caught, if at all, only by absent/ad-hoc client parsing. Documented as v1 scope (wire_signature.rs scope note) but real. FIX: derive JsonSchema on these types + include them in the signature map (and add client-side validate for them). discoveredInField=false (critique-found). Severity Low-Medium (a breaking change to a secondary response shape is silently missed; the core sync/auth/status contract IS covered)."; :>> discoveredInField = false; :>> relatedTask = "wireSignatureCoverageHardening"; :>> severity = Severity::Medium; }
    #Resolves dependency from wireSignatureCoverageHardening to issueSharingResponseTypesUncovered;

    // ---- Owner field bugs on composed-mount SYNC (2026-08-11) ----
    part issueMountRwPushBack : Issue { :>> id = "a45791f9-4ed6-4847-b1fb-89846e3e7f09"; :>> title = "A read-write (sync) composed mount does not push LOCAL edits back to the source in steady state — the mount poll is source-driven only"; :>> createdAt = "2026-08-11"; :>> createdBy = "wweatherholtz"; :>> description = "Owner field report, CONFIRMED by trace. pollMount (mountsync.ts:30-44) calls changes() on the SOURCE, then runs reconcileDelta (applies the source delta = pull) when the source changed, or noop+returns when it did not; only a FORCED FULL pass (reconcileAll, on first-mount/reconnect/Keep) scans LOCAL files. So a local create/edit/delete in a sync-mount folder whose source is unchanged is never scanned or pushed to the source — mounts react to source changes, never to local changes (unlike the primary, which is driven by local file events). Effect: a sync mount is one-directional in practice (pulls from source, never pushes local edits back) until a reconnect forces a full pass. NOT data loss (the local file is safe on disk) but the sync contract is broken. FIX: route a local file event under a mount point to a full (local-scanning) reconcile for that mount. discoveredInField=true (owner). Severity High (a sync mount silently fails to propagate the user's local edits to the shared source)."; :>> discoveredInField = true; :>> relatedTask = "mountSyncPushLocal"; :>> severity = Severity::High; }
    #Resolves dependency from mountSyncPushLocal to issueMountRwPushBack;
    part issueMountPollNotEventDriven : Issue { :>> id = "3d138e1b-b595-4777-9c19-28d769ae7529"; :>> title = "Composed mounts are ~60s poll-driven, not event-driven — they feel slow next to the WebSocket-instant primary vault"; :>> createdAt = "2026-08-11"; :>> createdBy = "wweatherholtz"; :>> description = "Owner field report. The primary vault syncs via a WebSocket (instant), but composed mounts have no source subscription — pollMount runs on the ~60s primary poll cadence (mountsync.ts header + main.ts:2087 note it as a deferred D0039 refinement), so a source change can lag up to a minute. FIX: give each active mount a live subscription (a WS channel on the source vault, or a per-vault multiplex of the primary WS) so source changes pull promptly, keeping the poll as a backstop. discoveredInField=true (owner). Severity Low-Medium (latency/UX; correctness is unaffected — the poll still converges)."; :>> discoveredInField = true; :>> relatedTask = "mountLiveSubscription"; :>> severity = Severity::Medium; }
    #Resolves dependency from mountLiveSubscription to issueMountPollNotEventDriven;

    // ---- mountSyncPushLocal independent-critique follow-ups (2026-08-11) ----
    part issueMountOutgoingDeleteImmediate : Issue { :>> id = "cb007579-a275-4cff-bcbf-9da9f6b0c95e"; :>> title = "The sync-mount push-back nudge makes a local delete propagate to a (possibly shared) source vault IMMEDIATELY, with no confirmation — needs an owner decision"; :>> createdAt = "2026-08-11"; :>> createdBy = "claudeOpus"; :>> description = "mountSyncPushLocal critique finding F1 (Medium, data-safety). The push-back nudge forces a full mount reconcile on a local file event, so a local delete under a SYNC-mount folder now propagates to the source PROMPTLY (before the fix it only propagated on the next reconnect). Deleting a folder locally deletes those files from the source server-side. This is CONSISTENT with D0041 (outgoing deletes are honored exactly, no bulk gate — owner decision) and receiving peers are still gated by THEIR incoming bulk-delete confirmation (D0041) before their local copies go — but the immediacy + the shared-source blast radius are new with this fix. Needs the owner to decide: accept as-is (record a Decision) OR add a confirmation for a mount outgoing delete-remote to a non-owned (shared) source over the bulk threshold. discoveredInField=false (critique-found). Severity Medium (a routine local reorganization promptly deletes from a shared vault; peers still gated on receive, and it is the owner's own action)."; :>> discoveredInField = false; :>> relatedTask = "mountOutgoingDeleteDecision"; :>> severity = Severity::Medium; }
    #Resolves dependency from mountOutgoingDeleteDecision to issueMountOutgoingDeleteImmediate;
    part issueMountNudgeCoverage : Issue { :>> id = "444bd559-d293-4d93-9efd-f028b8eb3991"; :>> title = "The mount push-back nudge (nudgeMountForLocalPath) has no direct test, and it recomputes activeMounts() on every primary file event"; :>> createdAt = "2026-08-11"; :>> createdBy = "claudeOpus"; :>> description = "mountSyncPushLocal critique F4 (test adequacy) + F7 (micro-perf). F4: the mountsync test proves the underlying forceFull capability but sets forceFull by hand — the actually-new code (nudgeMountForLocalPath's claimsLocal filter, the recentSelfWrites echo-skip added for F2, the read-only no-op, and the onLocalEvent/onLocalDelete/onLocalRename call sites) has zero direct coverage (no main.test.ts). Add a plugin-level test that a user edit under a mount forces a push, a mount pull-write echo does NOT, and a pull mount never writes the source. F7: the nudge calls activeMounts()/validMounts() (O(mounts^2) path math) on every primary file event (every save) — negligible now, but memoize the active set (invalidated on a settings.mounts change) if mount sets grow. discoveredInField=false (critique-found). Severity Low (test-coverage + a micro-optimization; the code paths were traced correct in the critique)."; :>> discoveredInField = false; :>> relatedTask = "mountNudgeHardening"; :>> severity = Severity::Low; }
    #Resolves dependency from mountNudgeHardening to issueMountNudgeCoverage;

    // ---- Owner-raised data hazard (2026-08-11): deleting the mount-point folder ----
    part issueMountFolderDeletedWipesSource : Issue { :>> id = "4972127d-ce9a-4056-afae-1dd8b4f1263d"; :>> title = "Deleting the local mount-point FOLDER on a sync mount propagates as a full source-subtree delete — a container deletion must not wipe the (shared) source"; :>> createdAt = "2026-08-11"; :>> createdBy = "wweatherholtz"; :>> description = "Owner-raised after D0043. With the mountSyncPushLocal push-back + D0043 (outgoing deletes exact), deleting the whole local mount-point folder fires a delete per child -> nudge -> forceFull -> delete-remote each -> the entire mounted subtree is deleted from the (possibly shared) SOURCE vault server-side. A container deletion reads as remove/reset-the-mount, NOT delete-all-these-shared-files-forever, so it must never wipe the source. OWNER DECISION (flag-and-choose; 'it was intentionally deleted, it should be intentionally reinstantiated'): detect the mount-point folder is gone while the mount had content (base non-empty) -> do NOT reconcile/propagate (critical safety) -> FLAG the mount (surfaced on status + settings) with explicit actions Reinstate (drop base + re-create folder + full re-pull from source) and Remove mount (detach, source preserved) — NO automatic action. Distinguish from a fresh never-materialized mount (base empty -> normal pull). discoveredInField=true (owner). Severity High (a routine folder deletion silently wipes a shared source subtree server-side)."; :>> discoveredInField = true; :>> relatedTask = "mountFolderDeleteGuard"; :>> severity = Severity::High; }
    #Resolves dependency from mountFolderDeleteGuard to issueMountFolderDeletedWipesSource;
    part issueMountDeleteGuardResiduals : Issue { :>> id = "eafdb558-d6c4-4c19-8ece-fd7e75443384"; :>> title = "Mass-local-deletion guard residuals: a paced sub-floor drain can slowly propagate, and a transient empty listing can spuriously flag localGone"; :>> createdAt = "2026-08-12"; :>> createdBy = "claudeOpus"; :>> description = "Bounded residuals from the mountFolderDeleteGuard re-critique (both LOW). Finding 2: the guard is not fully cumulative — a delete-remote prunes base, so a PACED sub-floor drain (< BULK_DELETE_MIN per full pass, never all-absent) can slowly propagate deletions without tripping; realistic one-shot mass deletes (select-all / folder / big chunk) ARE caught, so this is a slow, visible, unusual pacing. Full close = HOLD the outgoing delete-remote batch inside the reconcile (like the D0041 incoming hold) so base is not eroded. Finding 5: massLocalDeletion trusts io.list() at face value — a transient empty/partial listing (adapter hiccup, mid-write, unhydrated cloud placeholder) trips a spurious localGone needing a manual Reinstate (fail-safe: holds, never wipes — availability only); mitigate with an indeterminate-treat-as-present probe or a re-probe/debounce. discoveredInField=false (critique-found). Severity Low (both bounded; the realistic wipe vectors are closed, and finding 5 fails safe)."; :>> discoveredInField = false; :>> relatedTask = "mountDeleteGuardHardening"; :>> severity = Severity::Low; }
    #Resolves dependency from mountDeleteGuardHardening to issueMountDeleteGuardResiduals;
    part issueMountSharedDirectionToggle : Issue { :>> id = "51f10573-cd6e-4463-bbc1-7607ca128642"; :>> title = "The mount direction toggle (Pull<->Sync) is offered only for OWN-vault sources; a shared read-WRITE source can't be switched in the UI"; :>> createdAt = "2026-08-12"; :>> createdBy = "claudeOpus"; :>> description = "composedMountPermissions critique finding F5 (Low-Med). The settings row offers the in-place direction toggle only when m.source.owner is empty (own vault). A SHARED source that is legitimately read-write (grant perm=readWrite) mounted as Pull for safety then can't be switched to Sync via the UI — direction (whether to push) is conflated with permission (whether the grant allows writing). A shared read-only source being non-switchable is correct; a shared read-write one is over-restricted. FIX: compute canWrite for shared sources from listSharedVaults (cache on tab render) and offer the toggle when own OR shared-readWrite. discoveredInField=false (critique-found). Severity Low (over-restriction of a legitimate action; not incorrect behavior — the safe default just can't be relaxed in-row for shared RW)."; :>> discoveredInField = false; :>> relatedTask = "mountSharedDirectionToggle"; :>> severity = Severity::Low; }
    #Resolves dependency from mountSharedDirectionToggle to issueMountSharedDirectionToggle;

    // ===== Deferred findings from the 5-pass critique of the 1.27.0 composed-vaults/wire cluster (2026-08-13). =====
    // The ACTIONABLE findings were fixed in 1.27.1 (v1271CritiqueHardening); these are the residual design-calls /
    // hardening items the owner did not direct fixed this pass. Each is triaged to a backlog resolver action.
    part issueMountSharedSourceResurrection : Issue { :>> id = "c1455fdd-d178-448e-852c-861a938f614a"; :>> title = "A sync mount's D0019 keep-and-push resurrects a peer's tombstone-pruned deletion back onto the SHARED source vault"; :>> createdAt = "2026-08-13"; :>> createdBy = "claudeOpus"; :>> description = "5-pass critique (data-loss + state lenses). On a source history-floor advance (a tombstone prune) OR a mount that was offline while a peer deleted a file, reconcileAll sees the file local-present/base-present/remote-absent/no-tombstone and resolves to `restore` — re-pushing it. For a SYNC mount the source is another user's vault, so this RESURRECTS a file the peer legitimately deleted. It is the intended D0019 bias (preserve-over-lose: never delete without a tombstone) and IS surfaced (per-file Notice), and it is not local data-loss (the file comes back; the peer re-deletes). But for a shared source the right behavior is a design call: keep-local-only vs keep-and-push. Distinguishing 'the source lost it (restore)' from 'a peer deleted it + tombstone pruned (leave deleted)' is impossible without the tombstone. discoveredInField=false (critique-found). Severity Low (surfaced, preserve-bias, needs a tombstone-prune during a mount-offline window; a design call like mountMoveSafety/D0044)."; :>> discoveredInField = false; :>> relatedTask = "mountSharedSourceResurrectionPolicy"; :>> severity = Severity::Low; }
    #Resolves dependency from mountSharedSourceResurrectionPolicy to issueMountSharedSourceResurrection;
    part issueWirePermVariantBlindSpot : Issue { :>> id = "e6aaf404-bdc6-45a0-9740-789ffb9f5378"; :>> title = "Perm enum variant changes are invisible to the wire-signature hash/diff (a new variant fails loud at runtime in asPerm)"; :>> createdAt = "2026-08-13"; :>> createdBy = "claudeOpus"; :>> description = "5-pass critique (wire-compat lens). `Perm` is referenced only by NAME in the signature (SharedVault/GrantView/LinkInfo `perm` field type = 'Perm'); its variant set (read/readWrite) is discarded, so adding/renaming a variant changes NO field list and NO hash. A future server returning e.g. Perm::Admin ('admin') passes the compat gate, then asPerm (transport.ts) throws at runtime and the WHOLE listShared/myVaults/listShareLinks response is rejected → the share/switch UI fails to load. Fails loud (no corruption). With 1.27.1's non-gating share types this no longer blocks core sync, but the share UI still breaks. Cheap fix: capture Perm's enum values into the signature (a signature-format addition) so the client can detect + degrade gracefully. discoveredInField=false. Severity Low (loud-fail, share-UI-only after the non-gating fix)."; :>> discoveredInField = false; :>> relatedTask = "wirePermVariantCoverage"; :>> severity = Severity::Low; }
    #Resolves dependency from wirePermVariantCoverage to issueWirePermVariantBlindSpot;
    part issueMountReadOnlyRailDirectionKeyed : Issue { :>> id = "c05376df-cb09-45e0-88c9-64e12c9c95a2"; :>> title = "The client read-only mount rail keys on the user-editable `direction` field, not the observed grant"; :>> createdAt = "2026-08-13"; :>> createdBy = "claudeOpus"; :>> description = "5-pass critique (security lens, LOW / defense-in-depth). MountedApi's write hard-refuse keys on `direction === 'pull'`, not the real source grant. If a read-only-granted source is driven with direction:'sync' (a settings hand-edit, or a grant downgraded RW->R after the user flipped Pull->Sync — sharedWritable is loaded once per tab, never refreshed), the mount runs the read-WRITE reconcile path and attempts commit/putChunk/deleteFile. NOT a breach: the server re-authorizes every write (Access::Write) and 403s a read-only grantee, and the 403 is a retryable file error with no local or source data loss. Residual: the mount becomes a stuck-failing scope re-attempting pushes every poll and loses the read-only UX affordances. Stronger design: key readOnly on the observed grant (listSharedVaults) unioned with direction, so the rail can't be disarmed by one client-side field. discoveredInField=false. Severity Low (server-enforced; stuck-scope + lost UX, not data loss)."; :>> discoveredInField = false; :>> relatedTask = "mountReadOnlyRailFromGrant"; :>> severity = Severity::Low; }
    #Resolves dependency from mountReadOnlyRailFromGrant to issueMountReadOnlyRailDirectionKeyed;
    part issueMountHalfOpenSocketLiveness : Issue { :>> id = "25aaadac-32d4-4360-b2d4-ba92ccc79227"; :>> title = "A mount WebSocket that half-opens INDEPENDENTLY of the primary is never re-dialed (silent fallback to the poll)"; :>> createdAt = "2026-08-13"; :>> createdBy = "claudeOpus"; :>> description = "5-pass critique (concurrency lens, LOW). Mount sockets have no liveness timer of their own; recovery of a half-open mount socket depends on the PRIMARY WS also going stale (which triggers spinUpWs -> closeMountSockets -> a rebuild that reopens them). If a source vault's server-side subscription drops while the primary's stays healthy, the dead socket sits in mountSockets (has(key) true, scope stays live/diverged), so syncMountSubscriptions skips reopening it — the mount silently loses prompt sync and falls back to the ~60s poll until any reconnect. Degraded latency + a lingering dead socket, NOT data loss (the poll is the backstop). D0040 deliberately avoided per-mount timer machinery; a lighter fix is a periodic force-cycle or a mount-socket readyState check. discoveredInField=false. Severity Low (latency degradation, poll-backstopped, no data loss)."; :>> discoveredInField = false; :>> relatedTask = "mountSocketLiveness"; :>> severity = Severity::Low; }
    #Resolves dependency from mountSocketLiveness to issueMountHalfOpenSocketLiveness;

    // ===== F1/F2 shared-source-resurrection EXPANSION critique findings (deferred, 2026-08-14). =====
    part issueMountPushGuardThresholdCoupling : Issue { :>> id = "f14e5bad-7b9f-4c91-bf4a-eadea58ce099"; :>> title = "The F2 bulk-push-to-shared guard reuses the incoming bulk-DELETE strategy/threshold, so turning that off (or a below-threshold pruned batch) leaves peer-deletion resurrection unguarded"; :>> createdAt = "2026-08-14"; :>> createdBy = "claudeOpus"; :>> description = "Independent critique of the F2 fix (MEDIUM). computeBulkPushHold reuses bulkDeleteStrategy/bulkDeleteThreshold. Two consequences: (1) a user who sets the INCOMING bulk-delete confirmation to 'off' ALSO silently disables the OUTGOING push-resurrection guard — one knob, two very different data-safety behaviors, no separate control or warning; with 'off' a base-loss re-first-contact with PRUNED tombstones resurrects the peer's whole deletion set. (2) Even with the guard on, a pruned-deletion batch that stays BELOW the threshold is pushed (resurrected) — inherent to a mass-only threshold. The LIVE-tombstone case is always safe (finalize keeps it local unconditionally); this is the no-tombstone/pruned residue only. The default is count/10 so out-of-the-box everyone is protected against a mass; only an explicit 'off' or a small pruned set is exposed. Also folds the LOW transient-changes(0)-under-report finding: a single-file transient tombstone omission at keep-time could stamp a base and later removeLocal — narrow and outside the trusted-server model (D0007). Robust fix: a DEDICATED push-guard control (or a hard floor independent of the delete knob), since it protects a PEER's data. discoveredInField=false. Severity Medium (peer-data resurrection when the shared knob is off / sub-threshold)."; :>> discoveredInField = false; :>> relatedTask = "mountPushGuardDedicatedControl"; :>> severity = Severity::Medium; }
    #Resolves dependency from mountPushGuardDedicatedControl to issueMountPushGuardThresholdCoupling;
    part issueMountReconcilePathPushUnguarded : Issue { :>> id = "6308df54-99e2-46d2-9855-23142aec251f"; :>> title = "The F2 bulk-push guard is computed only in the full-scan path; the single-event reconcilePath push is unguarded"; :>> createdAt = "2026-08-14"; :>> createdBy = "claudeOpus"; :>> description = "Independent critique of the F2 fix (MEDIUM/LOW). guardBulkPush is computed only in reconcileAll and threaded into reconcileOne; reconcileDelta is safe (a local-only-new file is never in a server delta) but reconcilePath (the single vault-event route) calls reconcileOne WITHOUT guardBulkPush (defaults false), so a create/modify event on a pre-existing peer-deleted-but-still-local file after a base loss routes to an IMMEDIATE unguarded push -> resurrection, bypassing the F2 review. The full-scan (~15 min / reconnect) is the backstop that catches the mass; the exposure is any event flow that emits create events for pre-existing files (a folder move, external FS change, reindex) in the window before the full scan. Note: with the H1 fix a LIVE-tombstoned path is still kept-local even here IF reconcilePath computed hasTombstone — but reconcilePath only fetches tombstones when base is present, so a base-null path is unguarded on both axes. Fix: compute + thread guardBulkPush (and the base-null tombstone probe) into reconcilePath, or debounce-route mass local creates through a full pass. discoveredInField=false. Severity Low (full-scan backstopped; needs create events on pre-existing files in a narrow window)."; :>> discoveredInField = false; :>> relatedTask = "mountReconcilePathPushUnreachable"; :>> severity = Severity::Low; }
    #Resolves dependency from mountReconcilePathPushUnreachable to issueMountReconcilePathPushUnguarded; // resolved by a not-reachable ANALYSIS (reconcilePath is primary-only), not a code change
    part issueMountHeldResolverSerialization : Issue { :>> id = "3cf3f0ed-2a2e-473d-a924-29d56dc63f9b"; :>> title = "The held-push / held-delete review resolvers mutate a scope's base outside the serialized reconcile engine (can interleave with an in-flight pass)"; :>> createdAt = "2026-08-14"; :>> createdBy = "claudeOpus"; :>> description = "Independent critique of the F2 fix (LOW-MEDIUM, PRE-EXISTING pattern). keepBulkPushes/acceptBulkPushes (and the D0041 keepBulkDeletions/acceptBulkDeletions before them) call keepHeldPushes/applyHeldPushes DIRECTLY on the scope deps from a settings-UI button callback, NOT through the producer/serialized-engine queue that vault events and the ~4s poll use. So a background poll-driven reconcile for the same mount scope can interleave with the resolver at await points (both touch d.base for the same paths) — worst realistic case a concurrent pass pushes a path the user is simultaneously choosing to keep, or the resolver's changes(0) snapshot diverges from the concurrent pass's. Harm is bounded and needs coincident timing; and it is CONSISTENT with the accepted sibling D0041 delete-resolver behavior, not introduced by F2. Fix: route the held resolvers through the same serialization as events/polls (enqueue), or document + enforce a no-resolve-during-in-flight-pass guard. discoveredInField=false. Severity Low (bounded, coincident-timing, matches accepted D0041 pattern)."; :>> discoveredInField = false; :>> relatedTask = "mountHeldResolverSerialize"; :>> severity = Severity::Low; }
    #Resolves dependency from mountHeldResolverSerialize to issueMountHeldResolverSerialization;
    part issuePrimaryHeldResolverSerialization : Issue { :>> id = "11adf060-d488-4032-a6ed-a39d7217367e"; :>> title = "The PRIMARY-scope held-review resolvers still mutate this.base outside the engine queue (the primary analogue of the now-fixed mount race)"; :>> createdAt = "2026-08-14"; :>> createdBy = "claudeOpus"; :>> description = "Independent VERIFY of the mount-serialization fix (LOW-MEDIUM, PRE-EXISTING). The mount held-resolvers now serialize via runMountExclusive, but the PRIMARY branch of runScopeExclusive mutates this.base directly. The primary's reconcile PASSES serialize against each other via the engine queue, but acceptBulkDeletions('primary')/keepBulkDeletions('primary') are non-enqueued settings-UI button callbacks, so applyHeldDeletions/keepHeldDeletions can still interleave — at each io.remove await — with an in-flight poll-driven reconcileAll/reconcileDelta reading this.base per path (the same race class the mount fix closed). Pre-existing (the old code ran the primary resolver directly too); narrow (a manual accept/keep racing a ~60s poll) and bounded (per-file isolated, no cross-file invariant). The clean fix is a primary analogue: route the resolver through the engine queue (a new event kind) or a this.base mutex, so it can't interleave with a primary pass. Deferred — distinct mechanism from the mount fix. discoveredInField=false. Severity Low."; :>> discoveredInField = false; :>> relatedTask = "primaryHeldResolverSerialize"; :>> severity = Severity::Low; }
    #Resolves dependency from primaryHeldResolverSerialize to issuePrimaryHeldResolverSerialization;

    // ===== Field bug (owner-reported 2026-08-14): self-redeem trap + the username-case root cause it exposed. =====
    part issueSelfRedeemVaultOwnerTrap : Issue { :>> id = "54e0ff97-8310-407a-8fda-c35532e66256"; :>> title = "Redeeming a share link for a vault YOU OWN stamps vaultOwner with your own name → connect-time grant check reports 'revoked' and blocks ALL sync"; :>> createdAt = "2026-08-14"; :>> createdBy = "wweatherholtz"; :>> description = "OWNER FIELD REPORT (testing sharing to a new mobile device). A self-redeem (redeeming a share link for a vault the SAME account owns, e.g. to get your own vault onto a new device) makes the server return {owner:<you>, vault, perm} but mint NO grant (self-redeem no-op). The client (adoptRedeemed / startRedeem) stamped settings.vaultOwner with the returned owner = your OWN username. Then refreshShareGrant (runs every connect for any non-empty vaultOwner) calls GET /api/shared, which lists only vaults owned by OTHERS, doesn't find your own vault, and throws 'share access revoked' — blocking ALL sync (functional, not cosmetic; the whole connection is held before the first reconcile). Own vaults synced fine (they go via /api/vaults). FIXED: refreshShareGrant self-heals (vaultOwner === my account → owned, read-write); adoptRedeemed/startRedeem treat a self-redeemed ref as OWN; comparisons are CASE-INSENSITIVE (isOwnAccount). discoveredInField=true. Severity High (blocks sync entirely on a plausible test/onboarding flow)."; :>> discoveredInField = true; :>> relatedTask = "selfRedeemVaultOwnerFix"; :>> severity = Severity::High; }
    #Resolves dependency from selfRedeemVaultOwnerFix to issueSelfRedeemVaultOwnerTrap;
    part issueUsernameNotCanonicalized : Issue { :>> id = "0c2b5d5b-626c-4d03-84cf-6f0285c8ff72"; :>> title = "The client persists username as-typed while the server canonicalizes to lowercase — every case-sensitive owner/author comparison silently breaks for a capitalized username"; :>> createdAt = "2026-08-14"; :>> createdBy = "claudeOpus"; :>> description = "5-pass/self-redeem critique root cause. The server lowercases usernames on login + register (auth.rs to_ascii_lowercase), but the client stores what the user typed (setupwizard only .trim()s). So any client-side `x === settings.username` comparison against a server-authenticated (lowercase) value breaks for a capitalized username. The self-redeem fix addressed its own three sites with a case-insensitive isOwnAccount(); the SAME class remains at the plugin-autopilot 'is this plugin mine?' gate (main.ts ~909, `author === settings.username`) — a capitalized-username user's OWN plugins would be gated as a peer's (fail-safe: gates more, not an escalation) — and potentially other sites. The robust fix is to CANONICALIZE settings.username to lowercase at login (so the whole client agrees with the server), audited across all username comparisons, with attention to the RCE-adjacent autopilot gate. Deferred from the self-redeem fix release (touches a security-adjacent gate). discoveredInField=false. Severity Low (fail-safe today; correctness + UX)."; :>> discoveredInField = false; :>> relatedTask = "usernameCanonicalization"; :>> severity = Severity::Low; }
    #Resolves dependency from usernameCanonicalization to issueUsernameNotCanonicalized;
    part issueBootstrapSyncUserNotLowercased : Issue { :>> id = "2ec41a40-8326-43c9-9f12-f98bb3d9c1ba"; :>> title = "The bootstrap admin SYNC_USER env var is stored as-typed (not lowercased); SYNC_USER=Admin silently fails to seed the admin account"; :>> createdAt = "2026-08-14"; :>> createdBy = "claudeOpus"; :>> description = "Found by the username-canonicalization critique (out of scope for that client fix). config.rs (~78) reads `user: env('SYNC_USER','admin')` and stores it AS-TYPED, but every account path canonicalizes to lowercase and SafeName rejects uppercase. So if an operator sets SYNC_USER=Admin, safe_name(cfg.user) (state.rs) rejects it → the bootstrap admin account is NEVER seeded (can't log in at all), AND the `user == st.cfg.user` bootstrap-admin password-change protection (auth.rs) never matches, silently disabling it. SERVER-side latent footgun; the client username-canonicalization neither causes nor worsens it. FIX: a one-line `to_ascii_lowercase()` (+ trim) on the SYNC_USER read at config load; ships as a server-image redeploy. discoveredInField=false. Severity Low (only bites an operator who capitalizes SYNC_USER; default 'admin' is fine)."; :>> discoveredInField = false; :>> relatedTask = "bootstrapSyncUserLowercase"; :>> severity = Severity::Low; }
    #Resolves dependency from bootstrapSyncUserLowercase to issueBootstrapSyncUserNotLowercased;

    // ===== no-latent-debt dispositions (2026-09-07, project D0047). Each was previously named only
    // in a conversation summary; the rule makes prose-mention an invalid disposition. =====
    part issueVersionRecordDrift : Issue { :>> id = "d47e6a6e-447c-466b-bf62-0ac34a2ab07e"; :>> title = "client/package.json silently stopped tracking the plugin version after 1.22.0 while manifest.json advanced to 1.30.0 — bump-version.mjs swallowed a no-op replace"; :>> createdAt = "2026-09-07"; :>> createdBy = "claudeOpus"; :>> description = "Found incidentally while renaming the client package during the provenance decoupling (D0046). client/package.json recorded 1.22.0; manifest.json (the source of truth BRAT reads) recorded 1.30.0 — eight releases of undetected drift. ROOT CAUSE: scripts/bump-version.mjs updated package.json inside a bare try/catch around a String.replace whose NON-MATCH is a silent no-op, so a bump could report success while leaving that record behind; git history shows package.json tracked correctly through 1.22.0 (e61df7ea) then stopped. Compounding shape: manifest.json and versions.json were written BEFORE the package.json step, so a failure there left the other two already bumped. The pre-existing scripts/check-release.mjs checks manifest-vs-tag-vs-GitHub-release but never checks that the three version RECORDS agree, which is the hole this came through. FIXED in-pass with a fail-first-verified guard (see versionRecordDriftGuard). discoveredInField=false. Severity Low (a stale dev-facing version string; the shipped manifest was always correct, so no user was served a wrong version)."; :>> discoveredInField = false; :>> relatedTask = "versionRecordDriftGuard"; :>> severity = Severity::Low; }
    #Resolves dependency from versionRecordDriftGuard to issueVersionRecordDrift;
    part issueHooksNotInstalled : Issue { :>> id = "092b1e5b-753b-407a-b262-a0f2f8d15d06"; :>> title = "No git hook ran in this repo at all — a machine-global core.hooksPath pointed at a non-existent directory, silently disabling the pre-commit keel gate as well as the push, while CLAUDE.md asserted the push hook was running"; :>> createdAt = "2026-09-07"; :>> createdBy = "claudeOpus"; :>> description = "Found when a commit during the provenance decoupling did not auto-push. core.hooksPath was set machine-globally (file:C:/Users/will/.gitconfig) to ~/.githooks, which DOES NOT EXIST; git silently runs NO hooks when hooksPath names a missing directory. So the repo's own .githooks/pre-commit — the keel validate + keel guard commit gate — had never fired either, and .git/hooks held no non-sample hook. Separately there was no post-commit hook in the repo at all, yet CLAUDE.md 4 asserted 'the post-commit hook pushes every commit' — a doc claiming a control that did not exist, which is worse than a missing control because it stops anyone looking for it. The two commits made before the fix were gated manually instead (keel validate + guard run by hand, green both times) so nothing unvalidated landed, but that was vigilance, not a control. FIXED in-pass (see hooksInstall). RESIDUAL, out of this repo's scope and reported to the owner: the machine-global core.hooksPath is still broken, so every OTHER repo on this workstation remains hook-less. discoveredInField=false. Severity Medium (a silently-disabled commit gate — the class of failure that lets an invalid commit land unnoticed)."; :>> discoveredInField = false; :>> relatedTask = "hooksInstall"; :>> severity = Severity::Medium; }
    #Resolves dependency from hooksInstall to issueHooksNotInstalled;
    part issueForkedE2eHelpersUnattributed : Issue { :>> id = "e5846d9e-0f32-412d-96eb-e0d3c36168db"; :>> title = "Two real-Obsidian e2e helpers ARE derived from vrtmrz/obsidian-livesync (authored by vorotamoroz, confirmed) and carry no upstream MIT notice — the only remaining upstream code in the repo"; :>> createdAt = "2026-09-07"; :>> createdBy = "claudeOpus"; :>> description = "Found by a complete livesync-reference audit after an earlier truncated (head -40) sweep missed it. client/e2e-obsidian/helpers/obsidian.ts and helpers/obsidianFunctions.ts both self-declare 'Ported from origin/test_real_obsidian'; authorship was CONFIRMED against the leftover fork's test_real_obsidian branch — test_e2e/helpers/obsidian.ts and obsidianFunctions.ts were authored by vorotamoroz on 2026-05-11 and 2026-05-14, before this project existed (2026-07-04). Measured overlap, whitespace/comments normalized: obsidian.ts 55 of our 111 code lines identical to upstream's 137, including the whole waitForCDP(port, timeoutMs) signature and the CDP poll/attach sequence; obsidianFunctions.ts 8 of 15, including the global app plugin-registry type declaration. Punctuation-only lines inflate that somewhat, but the signatures and the type shape are substantive: this is derived work, and upstream is MIT, so its notice-retention obligation applies to these two files. This CORRECTS an earlier same-sitting claim that HEAD's tree held no upstream source — that check was filename- and dependency-based and missed a file whose own header declared the derivation. Scope limits worth keeping straight: NEITHER file is bundled into the built plugin (e2e tooling only), so nothing SHIPPED to users contains upstream code; both are distributed in repo source. Resolution needs an OWNER DECISION between (A) attribute — add upstream's MIT notice to the two files or a NOTICE naming them — and (B) re-implement both helpers independently and drop the ported-from claims, which is the complete decoupling the owner asked for. Also gates a README wording review: D0046's no-shared-code statement is true of the plugin and server but not of these two helpers. discoveredInField=false. Severity Medium (licence-compliance + a provenance claim that is currently overbroad; no user-facing or security impact)."; :>> discoveredInField = false; :>> relatedTask = "forkedE2eHelperProvenance"; :>> severity = Severity::Medium; }
    #Resolves dependency from forkedE2eHelperProvenance to issueForkedE2eHelpersUnattributed;
    part issueEngineVintageGateDrift : Issue { :>> id = "d55228ad-6912-46db-9483-f1d4ebafd7fe"; :>> title = "The .engine/ tree is a 6-week-stale vintage against the keel binary that gates commits - four guards fail under keel 0.3.1, and every recent keel-guard-ALL-PASS record was a stale sibling build verdict"; :>> createdAt = "2026-09-07"; :>> createdBy = "claudeOpus"; :>> description = "Surfaced the instant a real pre-commit gate ran for the first time. TWO compounding causes: no git hook was installed at all (issueHooksNotInstalled), and CLAUDE.md section 5 documented the validator as a local Windows release-build path that does NOT exist in this repo - so a 6-week-old sibling checkout's keel was run by hand instead of the keel 0.3.1 on PATH. Consequence: engine drift accumulated unseen, and the keel verdicts recorded in D0046 and the provenanceDecoupling DoD were that stale binary's - both records now carry an explicit GATE CORRECTION rather than being rewritten. Under 0.3.1: viewpoint-renderer 9 violations (declared renderers name commands 0.3.1 does not expose - and CLAUDE.md section 1 documents those same commands, so the doc surface is stale too); cli-surface-declared 1 (.engine/cli/commands.sysml absent, keel migrate resyncs); tool-reference 1 (engine-triage/SKILL.md references a non-existent .engine/tools/triage_reminder.py); sprint-closure 1 (tracked as issueMootedTaskUnstamped); plus 19 unread warnings. A keel migrate --dry-run reports 481 .engine/ files, 0 blockers, nothing outside .engine/. NOT run: a 481-file process/schema-definition change needs owner acceptance + a co-committed Decision (D0070 keystone). BLOCKS ALL COMMITS meanwhile. The recurrence guard is already structurally in place - the installed pre-commit hook invokes plain keel, so the real gate can no longer be sidestepped by reaching for a stale build - plus CLAUDE.md now says to check keel --version first. discoveredInField=false. Severity Medium (no user impact; a silently-drifted commit gate and overstated verification records)."; :>> discoveredInField = false; :>> relatedTask = "engineVintageResync"; :>> severity = Severity::Medium; }
    #Resolves dependency from engineVintageResync to issueEngineVintageGateDrift;
    part issueMootedTaskUnstamped : Issue { :>> id = "45ea9a7d-9f9b-4598-9cc8-6f8ac625b256"; :>> title = "The explicitly-mooted task embeddedTimestampHardening has no TestResult, so it is served as READY forever - and VerdictKind has no honest value for mooted"; :>> createdAt = "2026-09-07"; :>> createdBy = "claudeOpus"; :>> description = "The keel 0.3.1 sprint-closure guard fails it: an unstamped task whose sprint has passed is indistinguishable from open work, so it stays on the ready frontier permanently. The task IS genuinely moot rather than forgotten - its DoD text opens 'MOOTED 2026-08-01 by timestampIgnoreRedesign (1.9.0) - NOT to be executed' because the redesign DELETED every code path it was to harden, and issueTimestampHardeningFollowups was repointed to that redesign; it was kept deliberately for provenance. The real obstacle is a schema gap: VerdictKind is {pass, fail, inconclusive, error} with no moot or waived member, and stamping pass would fabricate an attestation for a test that never ran against a subject that no longer exists (D0016/D0051 forbid synthesizing who/what/when). Options: (A) outcome=inconclusive with judgment text stating it was mooted and not executed - narrowest honest fix, recommended; (B) delete the action + DoD and let the mooting Decision carry provenance; (C) add a moot VerdictKind member - frozen-schema change belonging upstream in the engine. Left for the owner because it is a judgment call about tracking-model semantics and (C) touches frozen schema. discoveredInField=false. Severity Low (backlog hygiene - one permanently-ready phantom item skewing the ready frontier; no code impact)."; :>> discoveredInField = false; :>> relatedTask = "mootedTaskStamp"; :>> severity = Severity::Low; }
    #Resolves dependency from mootedTaskStamp to issueMootedTaskUnstamped;
    part issueScanSkipMtimePreservedBlindspot : Issue { :>> id = "3f9a1c74-8d52-49be-b0a7-6c1e2f8d5b31"; :>> title = "The (size,mtime) scan-skip misses an out-of-band body change that preserves both - a knowingly accepted residual that exists only as code comments, with no typed disposition and no test pinning the boundary"; :>> createdAt = "2026-09-07"; :>> createdBy = "claudeOpus"; :>> description = "Surfaced by auditing whether the mooted embeddedTimestampHardening task had buried any live concern (it had - see issueMootedTaskUnstamped). Its F12 item was never specific to timestamp ownership, so it outlived the redesign that deleted the other three. The (size,mtime) scan-skip (reconcile.ts baseStatUnchanged) does not re-read a file whose size AND mtime both match the base stamp, so an out-of-band writer preserving both - rsync -a / cp -p restoring a same-length version, Syncthing restoring mtime, a backup restore - has its change missed until something bumps mtime. The tradeoff is deliberate and sound: it makes a whole-vault pass O(changed files) instead of O(vault bytes) (a measured battery drain on mobile), and the destructive path is structurally excluded because the skip requires rmeta PRESENT while delete-local is only ever yielded when the remote is ABSENT - so a scan-hit reaches only in-sync or pull. reconcile.ts, base.ts and settings.ts each call it an accepted rsync/Syncthing residual. The DEFECT is not the tradeoff but its RECORD: the acceptance exists only in code comments, so it is invisible to keel show dispositions, and no test pins the boundary - a future change could widen it (letting a scan-hit reach delete-local) without anything going red. Needs a boundary-pinning vitest plus a typed acceptRisk disposition (D0092). No data loss when it hits: the change is late, not lost. discoveredInField=false. Severity Low."; :>> discoveredInField = false; :>> relatedTask = "scanSkipBoundaryPin"; :>> severity = Severity::Low; }
    #Resolves dependency from scanSkipBoundaryPin to issueScanSkipMtimePreservedBlindspot;

    // ===== conflict-modal field report (2026-09-07) — all four resolved by conflictModalPerf. =====
    part issueConflictDiffQuadratic : Issue { :>> id = "6c5f165e-ea38-4a36-8031-ea7077e6cd02"; :>> title = "The conflict diff ran an unbounded O(n*m) LCS over a nested matrix, freezing the UI for seconds on a large note - 12k lines took 4.5s, on open AND after every resolve"; :>> createdAt = "2026-09-07"; :>> createdBy = "claudeOpus"; :>> description = "Owner field report: 'resolve conflicts is extremely slow'. unifiedLineDiff called lcsPairs (an O(n*m) DP allocating a NESTED (n+1)x(m+1) number matrix) on WHOLE notes with no size bound. merge3 has guarded the same function with MAX_MERGE_LINES=5000 since it was written; the diff view had no bound at all, and the 400-row display cap in renderDiff is applied AFTER the full diff is computed, so it saved nothing. Measured on a fast desktop for notes differing by ONE line: 200 lines 3ms, 500 7ms, 1k 32ms, 2k 89ms, 4k 447ms, 6k 1.06s, 8k 1.96s, 12k 4.5s - quadratic, on the UI thread, and run on modal open AND again after every single resolve. Mobile is several times slower again, and memory is the other half: 12k lines is 144M boxed cells. FIXED by stripping the common prefix/suffix before the DP (exact same output; a one-line edit collapses to 1x1) plus a 2,000,000-cell cap with a bounded whole-region fallback above it. Guarded by two perf assertions in merge.test.ts that FAILED first (3922ms and 404ms against a 250ms bound). discoveredInField=true."; :>> discoveredInField = true; :>> relatedTask = "conflictModalPerf"; :>> severity = Severity::Medium; }
    #Resolves dependency from conflictModalPerf to issueConflictDiffQuadratic;
    part issueStalePreviewFalsePositive : Issue { :>> id = "b24b532a-7af8-4b41-bdb8-f08559da0912"; :>> title = "'That file changed since you opened this' fired when nothing had changed - a read failure and any cosmetic rewrite both counted as a change, blocking the apply"; :>> createdAt = "2026-09-07"; :>> createdBy = "claudeOpus"; :>> description = "Owner field report: 'claims things have changed since i last opened the file which i haven't done'. The stale-preview guard in resolveNoteConflict compared (await readTextOrEmpty(original)) !== previewedOther. TWO independent false positives. (a) readTextOrEmpty SWALLOWS every read error and returns the empty string, so a transient Windows lock / AV scan / cloud placeholder read as 'the file was rewritten' - the user is told someone else edited their note when the file merely could not be opened for a moment. (b) The comparison was on RAW decoded text while the modal's own diff NORMALIZES EOL and (now) masks ignored timestamp keys - so a CRLF rewrite, or a `modified:`/`updated:` bump by another plugin, or an engine re-write during the 4s safety-net poll while the modal sat open, refused the apply over a difference the user was never shown. Because it is the 'Keep this device's' path that is guarded, the effect is that the user cannot keep their own version. FIXED by previewStillCurrent returning match/changed/unreadable and judging on normalizedContent - the same content identity the sync engine uses - with a distinct 'couldn't read it' notice. A genuine body change still refuses (guarded). discoveredInField=true."; :>> discoveredInField = true; :>> relatedTask = "conflictModalPerf"; :>> severity = Severity::High; }
    #Resolves dependency from conflictModalPerf to issueStalePreviewFalsePositive;
    part issueConflictDiffShowsIgnoredTimestamps : Issue { :>> id = "d111e7d8-97d2-4bfc-b23b-34bec6a59ae8"; :>> title = "The conflict diff showed frontmatter timestamp fields the user had told SelfSync to ignore, so the modal contradicted its own setting"; :>> createdAt = "2026-09-07"; :>> createdBy = "claudeOpus"; :>> description = "Owner field report: 'doesn't seem to ignore metadata timestamp fields like it should in the diff view'. Correct - renderDiff passed RAW text to unifiedLineDiff, and noteconflict.ts imported nothing from frontmatter.ts. The ignore machinery (normalizedContent + reconcile's private ignorePatternsFor) was used ONLY by the sync engine, so the engine treated a timestamp-only change as no change while the modal drew it as a red/green changed line and asked the user to adjudicate it. FIXED with a new plugin.ignorePatternsForPath that mirrors reconcile's gating (feature on, .md, not .obsidian/ config where a `created:` must stay significant, not an excluded folder), passed into renderDiff, which now diffs normalizedContent of both sides - the masked lines are neither a change nor shown as context - and the no-changes message says so. The same identity now backs the stale-preview guard and the cosmetic auto-dismiss, so all three agree. discoveredInField=true."; :>> discoveredInField = true; :>> relatedTask = "conflictModalPerf"; :>> severity = Severity::Medium; }
    #Resolves dependency from conflictModalPerf to issueConflictDiffShowsIgnoredTimestamps;
    part issueConflictModalSerialScan : Issue { :>> id = "5360e91f-a61d-45f1-8557-8cd20d6d86da"; :>> title = "The conflict modal read EVERY conflicting file pair serially before drawing anything, so opening it cost ~2N disk round-trips to display ONE conflict"; :>> createdAt = "2026-09-07"; :>> createdBy = "claudeOpus"; :>> description = "Owner field report: 'resolve conflicts is extremely slow' (the open, distinct from the diff freeze). run() executed the whole cosmetic auto-dismiss sweep BEFORE the first render: for every conflict, two STRICTLY SEQUENTIAL adapter.readBinary calls plus FOUR full UTF-8 decodes (isMergeable on each side, then sameIgnoringEol decoding both again) and two regex passes over the full text - all behind a 'Checking conflicts...' placeholder, and all repeated on every open. The modal only ever displays ONE conflict, so none of that work was needed to paint. FIXED by rendering first and sweeping in the background (redrawing only if something was dismissed), gating on the free extension check BEFORE any read so a binary attachment costs zero IO, decoding each side once with a strict fatal decode, and running the sweep at concurrency 8. Guarded by DOM tests that hang readBytesOrNull forever and still expect a painted conflict, and that assert a .png conflict performs zero reads. Related and fixed alongside: issueConflictResolveRepaintsPerFile (a settings repaint + whole-vault getFiles per resolved file) and issueConflictModalDoubleApply (unawaited render with no re-entry guard on an irreversible choice). discoveredInField=true."; :>> discoveredInField = true; :>> relatedTask = "conflictModalPerf"; :>> severity = Severity::Medium; }
    #Resolves dependency from conflictModalPerf to issueConflictModalSerialScan;
    part issueSettingsRepaintWalksEveryPluginFolder : Issue { :>> id = "dd2c06af-0da5-418e-938b-f269fbd54ac8"; :>> title = "Every settings re-render ran a recursive filesystem walk per synced plugin, so ONE conflict-resolve click cost a walk per plugin - seconds on Windows or a cloud-synced vault, regardless of note size"; :>> createdAt = "2026-09-07"; :>> createdBy = "claudeOpus"; :>> description = "THE defect that actually explains the owner's observation, found only after they pushed back: 'the diffs i was seeing were only on ~100 line files, but still took > 6 seconds or so'. At ~100 lines the LCS diff costs about 3ms (measured), so the quadratic-diff defect - real, and fixed - could NOT be the reported symptom; the AI's first explanation over-weighted it. The cost that fits scales with the number of SYNCED PLUGINS and the filesystem, not with note length. settings.ts renderPluginChecklist called plugin.pluginSyncClean(id) for EVERY synced plugin on EVERY render, UNCONDITIONALLY - even on the line right after the cached answer had already been applied - and pluginSyncClean runs walkConfigTree, a RECURSIVE adapter.list/stat walk over .obsidian/plugins/<id>. So any settings re-render cost one full filesystem walk per synced plugin. resolveNoteConflict ends by calling settingsRefresh, which IS a full settings display(), so a SINGLE 'Keep this device's' click paid for a walk per plugin; with ~10 synced plugins on Windows (antivirus on every stat) or a cloud-synced vault (placeholder hydration), that is seconds per click. It also compounded the modal OPEN: the old pre-render cosmetic sweep called resolveNoteConflict once per dismissed file, so N cosmetic conflicts meant N settings rebuilds, each doing that per-plugin walk plus a whole-vault vault.getFiles(). FIXED by walking ONLY when the answer is not cached; the cache is already invalidated where it matters (deleted per-plugin after a push/pull changes convergence, cleared wholesale on hide() so re-opening the tab re-checks), and staleness within one tab session errs safe - a button left live is a guarded no-op, never a wrong action. This is the fix for the single-click apply; the separate coalescing of settingsRefresh (issueConflictResolveRepaintsPerFile) only ever helped the BATCH case and would not have fixed one click. Guarded fail-first: with two synced plugins and three renders the guard saw 6 walks before the fix and 2 after. discoveredInField=true. Severity Medium (no data risk; a multi-second UI stall on an ordinary action)."; :>> discoveredInField = true; :>> relatedTask = "settingsPluginWalkCache"; :>> severity = Severity::Medium; }
    #Resolves dependency from settingsPluginWalkCache to issueSettingsRepaintWalksEveryPluginFolder;
    part issueConflictRenderSerialReads : Issue { :>> id = "e6343e11-ce19-4f6d-96f4-1f9c93207e74"; :>> title = "The conflict modal read the two conflicting files SEQUENTIALLY, doubling time-to-usable on slow storage for no reason"; :>> createdAt = "2026-09-07"; :>> createdBy = "claudeOpus"; :>> description = "Found by the new real perf harness (client/perf/conflicts.perf.ts), not by inspection. NoteConflictModal.render() awaited its two file reads one after the other - readTextOrEmpty(original) then readTextOrEmpty(copy) - and those two reads are the ONLY IO between opening the modal and it becoming usable. On a dev SSD (~0.05ms/read) the serialization is invisible, which is why it survived; on the storage where the conflict modal was actually reported slow - antivirus intercepting every open, or a cloud-synced vault hydrating placeholders, both 5-25ms per read - it doubled the wait for no benefit, since neither read depends on the other. FIXED by issuing them with Promise.all. Measured at an injected 10ms/read: time-to-usable 38.3 -> 18.7ms at one conflict and 45.1 -> 34.5ms at 300, and the end-to-end apply cycle 47.0 -> 30.9ms median. Guarded by the perf assertions, which pin both the absolute time and its FLATNESS in the conflict count. discoveredInField=false (found by instrumentation, though the environment it hurts is the one the owner reported from). Severity Low (a real but modest latency multiplier on an already-fixed path; no correctness impact)."; :>> discoveredInField = false; :>> relatedTask = "conflictPerfHarness"; :>> severity = Severity::Low; }
    #Resolves dependency from conflictPerfHarness to issueConflictRenderSerialReads;
    part issueConflictDiffInvisibleChars : Issue { :>> id = "9d2480d5-1550-4eb6-bfb8-6d9ebf395efa"; :>> title = "The conflict diff rendered visually-identical lines as a -/+ pair, so an irreversible either-side choice had nothing visible to choose between (trailing space, NBSP, zero-width, NFC/NFD)"; :>> createdAt = "2026-09-07"; :>> createdBy = "claudeOpus"; :>> description = "Owner field report while reviewing real conflicts: the diff showed 'a lot of pseudo changes', specifically a '- tagNames:' / '+ tagNames:' pair whose two lines were visually identical, with the reasonable question of whether encoding or CR/NL was to blame and the reasonable expectation that 'a good diff should be line-return agnostic'. Half right. Line endings were ALREADY handled - a probe confirms CRLF vs LF, a lone CR and trailing blank lines each yield zero changed lines - so EOL was never the cause. The actual causes are invisible characters: a trailing space or tab (Markdown's hard line break!), a tab-vs-spaces indent, a non-breaking space U+00A0 which renders exactly like a space, a zero-width space/joiner or BOM, or NFC-vs-NFD Unicode. The DEFECT was not that the diff detected these - they are real content - but that it rendered them INDISTINGUISHABLY, asking the user to make an irreversible either-side choice between two lines they had no way to tell apart. Fixed by revealing them with per-class markers on changed lines only, plus an explanatory line when every changed line is invisible-only, and explicitly NOT by ignoring them (ignoring a trailing double space would hide a Markdown line break and could discard the user's version). discoveredInField=true. Severity Medium (no data loss, but it made an irreversible decision unmakeable - the user could not see what they were choosing between)."; :>> discoveredInField = true; :>> relatedTask = "conflictDiffInvisibleReveal"; :>> severity = Severity::Medium; }
    #Resolves dependency from conflictDiffInvisibleReveal to issueConflictDiffInvisibleChars;
    part issueContentIdentityNotUnicodeNormalised : Issue { :>> id = "9d2480d5-1550-4eb6-bfb8-6d9ebf395eff"; :>> title = "Note content identity does not Unicode-normalise, so NFC vs NFD text that renders identically counts as a divergence - a latent phantom-conflict generator for cross-platform vaults"; :>> createdAt = "2026-09-07"; :>> createdBy = "claudeOpus"; :>> description = "Found while diagnosing issueConflictDiffInvisibleChars. Note CONTENT identity does not Unicode-normalise at ALL: grep shows normalize(\"NF...\") appears exactly once in client/src, at mounts.ts canonSeg, and that is for mount folder PATHS - never for content. normalizedContent (and therefore normalizedHash, the sync engine's content-identity hash) compares NFC and NFD forms of the same text as DIFFERENT. Consequence: text that is canonically equivalent and renders identically - the classic case being 'cafe' with a precomposed e-acute versus e plus a combining acute - is treated as a genuine divergence. macOS has historically produced decomposed (NFD) forms where Windows and Android produce NFC, and SelfSync explicitly targets desktop-plus-mobile cross-platform vaults, so a vault spanning a Mac and a PC can generate conflict copies for notes nobody edited, repeatedly, with a diff whose two sides look identical. NOT FIXED HERE, deliberately: changing content identity changes what the sync engine considers the same file, so it needs its own pass with care over the base-hash migration (every stored normHash would shift), whether to normalise on write or only on compare, and mobile performance of normalising large notes. The conflict UI now at least TELLS the user the two versions are visually identical (invisibleOnlyDifference NFC-folds before comparing), so the symptom is explicable rather than baffling. Needs: a decision on normalise-on-compare vs normalise-on-write, a migration plan for stored hashes, and a test with real NFD content from a Mac. discoveredInField=false (found by instrumentation; the field symptom it would cause is exactly the phantom-conflict class already reported). Severity Medium (latent phantom-conflict generator for any non-ASCII text in a cross-platform vault; no data loss - a conflict copy keeps both sides)."; :>> discoveredInField = false; :>> relatedTask = "contentIdentityUnicodeNormalise"; :>> severity = Severity::Medium; }
    #Resolves dependency from contentIdentityUnicodeNormalise to issueContentIdentityNotUnicodeNormalised;
    #Resolves dependency from contentIdentityNormalisation to issueContentIdentityNotUnicodeNormalised;
    part issueConflictDiffNotCopyable : Issue { :>> id = "2e7c5c46-fcc6-4325-9e16-fabb0a032d47"; :>> title = "The conflict diff could not be selected or copied, so a user wanting to repair the note by hand had no way to get the text out"; :>> createdAt = "2026-09-07"; :>> createdBy = "claudeOpus"; :>> description = "Owner ask: 'let the Resolve conflicts modal let me copy text so we can fix it explicitly.' The conflict diff's pre element set no user-select, so the text could not be selected in the modal, and there was no copy affordance - leaving a user who wants to repair the note by hand with no way to get the content out. The LOG modal's pre in main.ts has had user-select:text AND a 'Copy to clipboard' button since it was written, so the pattern already existed and the conflict modal simply never adopted it. Fixed with user-select:text on the diff plus a 'Copy both versions' button ordered FIRST among the actions, so reaching for the text never requires first committing to a side of an irreversible choice. The clipboard payload is a plain-text report: the path, the marked-up diff with its marker legend, then both versions VERBATIM - not the normalized and timestamp-masked forms the diff renders, since the point is to repair the actual file - and it is not truncated. If the clipboard is unavailable it says so and points at manual selection rather than failing silently. discoveredInField=true. Severity Low (no data risk; a missing affordance that blocked the user's own workaround)."; :>> discoveredInField = true; :>> relatedTask = "conflictCopyAndLoadSweep"; :>> severity = Severity::Low; }
    #Resolves dependency from conflictCopyAndLoadSweep to issueConflictDiffNotCopyable;
    part issueCosmeticConflictsNotSweptOnLoad : Issue { :>> id = "a36c58f5-195d-4737-8894-c5f7bad1fef3"; :>> title = "Nothing re-examined existing conflict copies - not on load, not in reconcile - so an already-CONVERGED conflict stayed in the count until someone opened the modal, behaving exactly like a stale flag"; :>> createdAt = "2026-09-07"; :>> createdBy = "claudeOpus"; :>> description = "Owner question: 'i'm not sure if refreshing the plugin autoresolves as much as it can and this is a genuine outstanding issue, or if it was just flagged as an issue and isn't being reanalyzed on a plugin update as it should. which is it?' Investigated; the answer is both-and-neither, and there IS a defect. NOT a stale flag: a note conflict is DERIVED from a conflict-copy FILE on disk, and listNoteConflicts recomputes it from vault.getFiles() on every call (D-conflict-model), so the count cannot drift from reality. THE DEFECT: refreshing the plugin auto-resolved nothing at all. The cosmetic sweep was invoked from exactly ONE place - NoteConflictModal.run() - and nothing else in the codebase ever re-examined an existing conflict copy: not onload, not reconcileAll, not reconcilePath. reconcile CREATES copies and treats an existing one as a plain file thereafter. So a conflict whose two sides had since CONVERGED - identical content, or differing only in line endings or in frontmatter timestamp keys the user chose to ignore - stayed in the count indefinitely, and then disappeared the instant someone opened the modal. That behaviour is indistinguishable from a stale flag being cleared, which is exactly why it was reported as one. FIXED by moving the sweep to the plugin (dismissCosmeticConflicts) and running it once per load from onLayoutReady, so a refresh really does auto-resolve everything it safely can; the modal delegates and passes its open flag so closing it cancels the background work. Safe by construction: a copy is only deleted when content identity says the sides are the same, and binary/invalid-UTF-8 pairs are excluded before any read. discoveredInField=true. Severity Medium (no data loss, but the conflict count overstated real outstanding work indefinitely, and the disappear-on-open behaviour actively undermined trust in the count)."; :>> discoveredInField = true; :>> relatedTask = "conflictCopyAndLoadSweep"; :>> severity = Severity::Medium; }
    #Resolves dependency from conflictCopyAndLoadSweep to issueCosmeticConflictsNotSweptOnLoad;
    part issueConflictDiffHidesIgnoredLineLoss : Issue { :>> id = "43fa155f-6fd1-43d9-bbf1-4badab1c2299"; :>> title = "The conflict diff DELETED ignored timestamp lines instead of masking their values, hiding that keeping the other version would destroy this device s created:/updated: lines"; :>> createdAt = "2026-09-07"; :>> createdBy = "claudeOpus"; :>> description = "Found when the owner used the new Copy button and pasted a real conflict back. The conflict diff rendered normalizedContent(), which DELETES an ignored timestamp line rather than neutralising it. That is right for a content-identity hash but wrong for a diff: when only one side HAS the line, removing it from both makes it invisible. In the reported file, `created: 2026-04-01T14:54` and `updated: 2026-06-08T09:40` existed only on the Windows copy, and the diff showed neither - so choosing 'Keep the other device's' would have deleted both lines with no indication whatsoever, on an irreversible either-side choice. Self-inflicted: shipped in 1.30.1 in response to the owner's own request to ignore timestamp fields in the diff, implemented by dropping the lines instead of masking their values, and it reintroduced exactly the hiding that the invisible-character work had argued against one layer up. FIXED with maskedForDisplay: the VALUE is masked, the LINE always survives, so an ignore-worthy value difference is still silent while a missing line is always visible. Applies to the clipboard report too, so copied text matches the screen. discoveredInField=true. Severity Medium (no automatic data loss, but it concealed the consequence of a manual irreversible choice - the user could have deleted their own creation date believing nothing was at stake)."; :>> discoveredInField = true; :>> relatedTask = "conflictDiffShowIgnoredLines"; :>> severity = Severity::Medium; }
    #Resolves dependency from conflictDiffShowIgnoredLines to issueConflictDiffHidesIgnoredLineLoss;
    part issueFrontmatterTrailingSpaceConflictLoop : Issue { :>> id = "bbca0a36-9a20-4a90-a6ba-af772fd8e33f"; :>> title = "Content identity does not trim trailing whitespace inside frontmatter, so two devices whose plugin versions serialise an empty YAML value differently regenerate the SAME conflict forever"; :>> createdAt = "2026-09-07"; :>> createdBy = "claudeOpus"; :>> description = "Diagnosed from the owner's pasted conflict; NOT fixed, and deliberately so. The six differing frontmatter lines differ ONLY by a trailing space: the other device writes `tagNames: `, `filesPaths: `, `bookmarksGroups: `, `excludes: `, `extends: `, `favoriteView: ` with a trailing space for the empty value, and this device writes them without. In YAML both forms are the same null value, so the two files are semantically identical on those lines. The shape of the file (fields / valuesList / fieldsOrder / mapWithTag) is a Metadata Menu fileClass, so the likely source is two different plugin or Obsidian versions serialising an empty value differently on the two devices. normalizedContent normalises EOL and BOM and masks ignored timestamp keys, but does NOT trim trailing whitespace, so content identity treats these as genuinely divergent - which means every time either device rewrites that file the conflict is regenerated. This is a permanent conflict LOOP, not a one-off, and it is the actual reason the owner keeps seeing conflicts on this note. WHY NOT FIXED HERE: the fix is to trim trailing whitespace on lines INSIDE the frontmatter fences in normalizedContent - safe in YAML, and body lines must stay untouched because in Markdown two trailing spaces are a hard line break. But normalizedContent feeds normalizedHash, so changing it shifts every stored normHash; a persisted hash computed under the old algorithm would no longer match a freshly computed one, which can make files look changed once and generate exactly the conflict copies being eliminated. That needs a migration decision (recompute-and-restamp on load, or grandfather stored hashes, or compare-both-ways during a transition), which is the same class of change as issueContentIdentityNotUnicodeNormalised and belongs with it. Interim behaviour is honest: the diff now reveals the trailing spaces as middle dots and states that the versions differ only in invisible characters. discoveredInField=true. Severity Medium (recurring phantom conflicts on any note a differently-versioned plugin rewrites; no data loss, but persistent noise and a standing risk of the user resolving in the wrong direction)."; :>> discoveredInField = true; :>> relatedTask = "frontmatterTrailingSpaceIdentity"; :>> severity = Severity::Medium; }
    #Resolves dependency from frontmatterTrailingSpaceIdentity to issueFrontmatterTrailingSpaceConflictLoop;
    #Resolves dependency from contentIdentityNormalisation to issueFrontmatterTrailingSpaceConflictLoop;
    part issueNormHashDeadPersistedField : Issue { :>> id = "601c0f49-b774-437f-beda-3ea44d9829f3"; :>> title = "BaseEntry.normHash is declared, persisted and load-guarded but NEVER computed - dead state whose presence made a hash migration look necessary when none was"; :>> createdAt = "2026-09-07"; :>> createdBy = "claudeOpus"; :>> description = "Found while investigating whether the owner-approved 'recompute and restamp' hash migration was needed. It was not, and the reason is this defect: BaseEntry.normHash is declared in the interface, written by BaseStore.toJSON, and type-guarded on load in mountengine.ts:59 - but NOTHING EVER COMPUTES OR STORES IT. reconcile.setBase, the single writer of base entries, stores { hash, text? } only. So normHash is always undefined at runtime and reconcile.baseNormHash always falls through to recomputing the hash from the stored base text on every comparison. Two consequences. (1) A real if modest PERF cost: every content-identity comparison re-hashes the base text instead of reading a cached value - the field exists precisely to avoid that. (2) A documentation-and-reasoning hazard that already cost real time: the field's presence, plus base.ts's comment describing it as 'the NORMALIZED content hash at the last sync', made both the AI and the tracked issue text assert that changing normalizedContent would shift stored hashes and require a migration. It would not, because nothing is stored. Resolution options: POPULATE it in setBase (recovers the intended perf win, but then a future identity change genuinely does need a migration, so it should land together with a version marker in the persisted data - dataSchemaVersion already exists), or REMOVE the field, the toJSON branch and the load guard as dead weight. Either way the base.ts comment must stop describing behaviour that does not happen. A regression test now pins the current state so the choice is made deliberately rather than by drift. discoveredInField=false. Severity Low (a missed optimisation plus misleading documentation; no correctness impact, and the recompute path is correct)."; :>> discoveredInField = false; :>> relatedTask = "normHashDecide"; :>> severity = Severity::Low; }
    #Resolves dependency from normHashDecide to issueNormHashDeadPersistedField;
    part issueNoLockfileFloatingToolchain : Issue { :>> id = "28411d61-42ca-4b05-9bb3-3f6a04f28989"; :>> title = "package-lock.json is gitignored and CI runs npm install, so the client toolchain floats - builds, test verdicts and release artifacts are not reproducible across machines or days"; :>> createdAt = "2026-09-07"; :>> createdBy = "claudeOpus"; :>> description = "Found while chasing the dead real-Obsidian e2e layer, and worth recording precisely because it was first SUSPECTED as the cause and then FALSIFIED. client/.gitignore lists package-lock.json (line 7), no lockfile has ever been committed (git log --all -- client/package-lock.json is empty), and every CI and release workflow runs `npm install` rather than `npm ci` (ci.yml lines 78 and 103, release.yml line 49). So the toolchain is resolved fresh on every machine and every run: package.json asks for @playwright/test ^1.61.1 and a fresh install this sitting produced 1.63.0. The e2e attach failure was NOT this - pinning 1.61.1 reproduced the identical connectOverCDP error, so that cause was Obsidian's Electron, fixed by the CDP shim in the new driver - but the exposure is real and independent: a plugin build, a test verdict, or a release artifact produced today cannot be reproduced byte-for-byte tomorrow, a transitive dependency can change under a green CI without any commit in this repo, and a bisection of a regression cannot separate 'our change' from 'a dependency moved'. The original reason for ignoring the lockfile is not recorded anywhere. RESOLUTION needs an owner decision because it changes repository policy: commit client/package-lock.json (and use `npm ci` in CI and release so the lockfile is authoritative rather than advisory), OR record a Decision stating why floating resolution is wanted and pin exact versions in package.json instead. discoveredInField=false. Severity Low (no user-facing effect; a reproducibility and bisection hazard for the project itself)."; :>> discoveredInField = false; :>> relatedTask = "lockfilePolicy"; :>> severity = Severity::Low; }
    #Resolves dependency from lockfilePolicy to issueNoLockfileFloatingToolchain;
    part issueUnattestedDispositionClosesFinding : Issue { :>> id = "d8fce60b-00d7-45a5-a7be-69d70e43929d"; :>> title = "keel open-issues treats a finding with a #Dispositions edge as closed even when the disposition Test has NO TestResult - an unattested acceptRisk hid an open issue from the owner"; :>> createdAt = "2026-09-07"; :>> createdBy = "claudeOpus"; :>> description = "Found while recording the scan-skip acceptRisk (issueScanSkipMtimePreservedBlindspot). A method=confirmation Test carrying disposition = DispositionKind::acceptRisk was authored WITHOUT a TestResult - deliberately, because an acceptRisk is a human judgment and CLAUDE.md 3c forbids inferring one - and linked to the finding with a #Dispositions edge. keel 0.3.1's open-issues lens then dropped the issue from the open list entirely (it appeared under neither open nor resolved), while the dispositions lens did not list it as a finding at all. VERIFIED by experiment: deleting the single #Dispositions edge line made the issue reappear as open; restoring it hid the issue again. So the lens treats the PRESENCE of a disposition edge as closure, without checking that the disposition Test has any recorded verdict. That is the wrong direction for an honesty tool: D0092 makes a disposition a TYPED RECORDED JUDGMENT - the judgment is the TestResult (who, when, at what commit), not the edge - so an unattested disposition should leave the finding open, exactly as an unstamped DoD leaves a task open. Consequence here: an open item awaiting the owner's word was invisible to the owner. LOCAL MITIGATION applied: the #Dispositions edge is withheld until the attestation is recorded, and the acceptance.sysml comment says so and carries the exact edge text to author at that moment; the issue is open again. UPSTREAM: this is a keel (sysmlv2-ai-toolkit) defect - the lens should require a pass/acceptRisk/dismiss TestResult on the disposition Test before treating the finding as dispositioned. Same family as the earlier observation that keel migrate's dry-run reported 0 blockers for a change that deleted a project decision's effect: computed state that claims more than the authored facts support. discoveredInField=false. Severity Low here (no data at risk; a hidden open item), but it is an honesty defect in the control plane and should be fixed at the source."; :>> discoveredInField = false; :>> relatedTask = "keelDispositionLensReport"; :>> severity = Severity::Low; }
    #Resolves dependency from keelDispositionLensReport to issueUnattestedDispositionClosesFinding;
}
