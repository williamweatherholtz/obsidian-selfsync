// =====================================================================
// ProjectBusiness — the Business-layer artifacts for the SelfSync self-hosted Obsidian
// sync product (backfilled 2026-07-04, D0004 adoption). Brief -> Personas -> Needs.
// The three top Needs are the project's founding goals; sub-needs decompose them. Needs
// are solution-free desired outcomes; the HOW lives in requirements + architecture decisions.
// =====================================================================
package ProjectBusiness {
    private import EngineElement::*;
    private import EngineNeeds::*;
    private import EngineRelationships::*;

    // ---- Brief ----
    part selfsyncBrief : Brief {
        :>> id = "e4cc9b4a-edf0-42c9-8ea3-fd6d08433da6";
        :>> title = "SelfSync — self-hosted Obsidian sync";
        :>> createdAt = "2026-07-02";
        :>> createdBy = "wweatherholtz";
        :>> problem = "obsidian-livesync is powerful but notoriously hard to adopt: its configuration UI is confusing (dozens of cryptically-named toggles, easy to misconfigure), it depends on CouchDB (painful to self-host and operate), and its strongest conflict/diff-merge quality is gated behind sponsorship. Users self-hosting their notes get stuck at setup, fight the backend, or lose the merge quality they need.";
        :>> opportunity = "A fresh, self-hosted Obsidian sync — a single-binary Rust server (no CouchDB) plus a lean plugin — can deliver official-Sync-class ease with a guided setup, efficient content-addressed storage, and un-paywalled three-way conflict merge, all on infrastructure the user owns.";
        :>> constraintsNote = "Obsidian plugin (TypeScript, esbuild) + a self-hostable server; must run on desktop AND mobile (isDesktopOnly:false); distributed via BRAT; trusted-server + TLS-in-transit security model (content E2EE is a deferred option).";
    }

    // ---- Personas ----
    part selfHoster : Persona {
        :>> id = "04fae38b-fd54-42a1-ab46-19eda13d3122";
        :>> title = "Self-hosting Obsidian user";
        :>> createdAt = "2026-07-02";
        :>> createdBy = "wweatherholtz";
        :>> description = "A privacy-minded Obsidian user who wants their notes synced across devices on infrastructure they own, without a subscription and without operating a database. Comfortable running a Docker container; not eager to babysit CouchDB or decode dozens of cryptic toggles. Keeps a desktop plus at least one other machine, and has customized Obsidian (a theme, CSS snippets, a handful of community plugins) that they expect to travel with them intact.";
        :>> goals = "Sync notes across my devices on my own server; set it up once, quickly, without decoding cryptic settings; own my data end to end; and have my plugins, themes, and settings follow me to every device without one device ever wiping another's setup.";
    }
    part mobileUser : Persona {
        :>> id = "0290ffeb-e394-4c63-9f51-37ca76e58030";
        :>> title = "Mobile Obsidian user";
        :>> createdAt = "2026-07-02";
        :>> createdBy = "wweatherholtz";
        :>> description = "Uses Obsidian on a phone/tablet as well as desktop, often on the go and on flaky networks. Works within mobile constraints (foreground execution, limited memory, no status bar) and needs a UI that reads clearly on a small screen. Can't run every desktop plugin on mobile and expects that to be harmless — never a broken sync or a plugin that vanishes from the desktop.";
        :>> goals = "Sync reliably between phone and desktop; see sync state at a glance on mobile; and know that a plugin I can't run on mobile will never break sync or vanish from my desktop.";
    }
    part migratingUser : Persona {
        :>> id = "0001823c-fc83-4c4f-93c3-d521c265041e";
        :>> title = "Migrating LiveSync user";
        :>> createdAt = "2026-07-02";
        :>> createdBy = "wweatherholtz";
        :>> description = "Currently on obsidian-livesync and frustrated by its setup friction, CouchDB operations, or paywalled merge. Has an existing vault plus a customization set (themes, plugins) and wants to move without losing conflict-safety or re-learning a maze of settings.";
        :>> goals = "Escape CouchDB and confusing settings; keep strong, free conflict resolution; migrate my existing vault and customizations without data loss; understand each setting's purpose at a glance.";
    }
    part collaborator : Persona {
        :>> id = "c0f1a5cc-a001-4a10-9b20-a1b2c3d40091";
        :>> title = "Vault collaborator";
        :>> createdAt = "2026-07-05";
        :>> createdBy = "wweatherholtz";
        :>> description = "Shares one or more vaults with family, teammates, or collaborators on the same self-hosted server. Needs to grant access at the right permission level and trust that sharing never exposes their other vaults or their credentials.";
        :>> goals = "Share a specific vault read-only or read-write with named people; revoke access cleanly; never leak my other vaults or my login by sharing; collaborate on a shared vault with the same conflict-safety as my own.";
    }
    part selfHostOperator : Persona {
        :>> id = "c0f1a5cc-a002-4a10-9b20-a1b2c3d40092";
        :>> title = "Self-host operator";
        :>> createdAt = "2026-07-05";
        :>> createdBy = "wweatherholtz";
        :>> description = "Runs and administers the SelfSync server for themselves and others — provisions the single binary/container, manages accounts and shares, and controls who can register. Wants operation to stay a single-binary affair with no database to babysit.";
        :>> goals = "Stand up the server as one container with its own storage; manage accounts and vault shares through an admin interface; control registration (closed, or open with single-use invites); keep the server durable and self-healing without a DBMS.";
    }

    // =====================================================================
    // GOAL 1 — a clear, guided configuration experience (the #1 pain of LiveSync)
    // =====================================================================
    requirement goal1ClearConfig : Need {
        :>> id = "547cee47-9833-4080-b9ae-915ca476a3d9";
        :>> title = "Configuration is clear and guided, not confusing";
        :>> source = NeedSource::customer;
        :>> statement = "A user can set up and understand sync without decoding cryptic settings — setup is guided and each setting has one obvious home.";
        :>> marketJustification = "LiveSync's confusing config is its most-cited adoption barrier.";
        :>> priority = Priority::must;
    }
    requirement n1GuidedSetup : Need {
        :>> id = "31ee9f0a-c05a-4af5-8c5c-48864181080f";
        :>> title = "Guided first-run setup";
        :>> source = NeedSource::customer;
        :>> statement = "A new user is walked through connecting to their server and choosing a vault, without hand-editing opaque fields.";
        :>> priority = Priority::must;
    }
    requirement n1OneHomePerSetting : Need {
        :>> id = "e87d90b5-fddc-4dea-8dc7-5c08ea6656db";
        :>> title = "One clear home per setting";
        :>> source = NeedSource::customer;
        :>> statement = "Every setting lives in one obvious place, grouped by concern, with no duplicated or contradictory controls.";
        :>> priority = Priority::should;
    }
    requirement n1SingleIndicator : Need {
        :>> id = "2c042178-faed-474b-baf9-40ed7061bc92";
        :>> title = "One clear sync-state indicator";
        :>> source = NeedSource::customer;
        :>> statement = "The user sees a single, unambiguous indication of sync state, not several redundant indicators.";
        :>> priority = Priority::should;
    }
    // Config/customization sync (settings, themes, community plugins) across devices. Added
    // 2026-07-05 (CR d0011): the feature shipped in code with NO Need/SR behind it — an ORPHAN
    // capability, which is exactly how the multi-device divergence/removal defects (0.10.4)
    // escaped. Rooting it makes requirement-rootedness + tier-satisfaction guard it going forward.
    requirement nConfigSync : Need {
        :>> id = "c0f1a5cc-1001-4a10-9b20-a1b2c3d40001";
        :>> title = "My Obsidian setup syncs across devices — safely";
        :>> source = NeedSource::customer;
        :>> statement = "A user's Obsidian setup (settings, themes, community plugins) syncs across their devices — changes made while connected are detected without a reconnect, a removal made on a device that held the data propagates (auto-remove), a device that lacks the data never causes a deletion and nothing is silently resurrected, and only a genuine same-file difference is resolved by the user.";
        :>> marketJustification = "LiveSync's hidden-file/customization sync is a frequent source of confusion and data loss; safe, adjudicated config sync is a differentiator.";
        :>> priority = Priority::must;
    }

    // =====================================================================
    // GOAL 2 — a simple, fast, self-hosted backend with NO CouchDB
    // =====================================================================
    requirement goal2SimpleBackend : Need {
        :>> id = "bf9ec044-fd46-488d-b774-7ab9b43ea0b8";
        :>> title = "Simple, fast self-hosted backend without CouchDB";
        :>> source = NeedSource::customer;
        :>> statement = "A user can self-host sync with a single easy-to-run server and get fast sync, without operating CouchDB or any external database.";
        :>> marketJustification = "The CouchDB dependency is LiveSync's biggest operational pain.";
        :>> priority = Priority::must;
    }
    requirement n2NoCouchDB : Need {
        :>> id = "1af61c65-1abe-4946-a9dc-2fce163710a0";
        :>> title = "Single self-contained server (no external DB)";
        :>> source = NeedSource::operator;
        :>> statement = "The server runs as one self-contained binary/container with its own storage — no CouchDB, no separate database to provision or maintain.";
        :>> priority = Priority::must;
    }
    requirement n2Dedup : Need {
        :>> id = "a0bbfe25-989d-480d-a546-f3a178399107";
        :>> title = "Efficient storage via deduplication";
        :>> source = NeedSource::customer;
        :>> statement = "Storage and transfer are efficient — unchanged and duplicated content is not re-stored or re-sent.";
        :>> priority = Priority::should;
    }
    requirement n2Performance : Need {
        :>> id = "3d958048-37c9-4d31-9b9f-7b3eeec58692";
        :>> title = "Fast sync for large vaults and large files";
        :>> source = NeedSource::customer;
        :>> statement = "Sync stays responsive for large vaults and large/binary files without blocking other operations.";
        :>> priority = Priority::should;
    }

    // =====================================================================
    // GOAL 3 — strong, un-paywalled conflict detection + diff/merge
    // =====================================================================
    requirement goal3ConflictMerge : Need {
        :>> id = "2fec350f-432d-4ffc-9ad9-0b0cd9d90df4";
        :>> title = "Strong conflict resolution, free for everyone";
        :>> source = NeedSource::customer;
        :>> statement = "Concurrent edits are resolved well and no user ever silently loses data — and this quality is not gated behind payment.";
        :>> marketJustification = "LiveSync gates its best merge behind sponsorship; free strong merge is a differentiator.";
        :>> priority = Priority::must;
    }
    requirement n3ThreeWayMerge : Need {
        :>> id = "63e79d46-17fa-463c-910f-303c514759c5";
        :>> title = "Automatic three-way merge of concurrent edits";
        :>> source = NeedSource::customer;
        :>> statement = "When the same note is edited on two devices, non-conflicting changes are merged automatically.";
        :>> priority = Priority::must;
    }
    requirement n3NeverClobber : Need {
        :>> id = "04fa65ee-2355-45c3-ac8b-9dfb8a164d0f";
        :>> title = "Never silently lose data on conflict";
        :>> source = NeedSource::customer;
        :>> statement = "When changes cannot be merged cleanly, both versions are preserved (conflict copy) rather than one overwriting the other.";
        :>> priority = Priority::must;
    }
    requirement n3Unpaywalled : Need {
        :>> id = "241271c3-445c-45b0-b363-2830872acc90";
        :>> title = "Conflict/merge quality is not paywalled";
        :>> source = NeedSource::competitive;
        :>> statement = "The full conflict-detection and diff/merge experience is available to every user at no cost.";
        :>> priority = Priority::should;
    }

    // =====================================================================
    // Cross-cutting Needs
    // =====================================================================
    requirement nxMobile : Need {
        :>> id = "f7efcf39-e851-44d9-86cc-7332ab6317f6";
        :>> title = "Works on desktop and mobile";
        :>> source = NeedSource::customer;
        :>> statement = "Sync and its UI work on both desktop and mobile Obsidian.";
        :>> priority = Priority::must;
    }
    requirement nxSecurity : Need {
        :>> id = "31b84035-868e-47bd-8f89-ce661318f62d";
        :>> title = "User data and credentials are protected";
        :>> source = NeedSource::safety;
        :>> statement = "Notes are transferred securely to the user's own server, and SelfSync's own credentials (server, login, token) are never themselves synced into the vault.";
        :>> priority = Priority::must;
    }

    // ---- Post-launch capability: multi-user vault sharing (2026-07-04) ----
    requirement nVaultSharing : Need {
        :>> id = "393acf9e-8282-4b0b-8d70-80d6c5e1f936";
        :>> title = "Share a vault with other users on the server";
        :>> source = NeedSource::customer;
        :>> statement = "A vault owner can grant other accounts on the same server read-only or read-write access to a vault, and administer accounts + shares through a management interface.";
        :>> priority = Priority::should;
    }

    // ---- Needs surfaced by the use-case functional decomposition (2026-07-05) ----
    requirement nReliableSync : Need {
        :>> id = "c0f1a5cc-e101-4a10-9b20-a1b2c3d40101";
        :>> title = "Sync keeps running reliably on its own";
        :>> source = NeedSource::customer;
        :>> statement = "Once set up, sync just keeps working — changes propagate promptly, the client recovers from dropped connections without user action, and it stays responsive across desktop and mobile.";
        :>> priority = Priority::must;
    }

    requirement nVaultManagement : Need {
        :>> id = "c0f1a5cc-e102-4a10-9b20-a1b2c3d40102";
        :>> title = "Onboard devices and manage which vault syncs";
        :>> source = NeedSource::customer;
        :>> statement = "A user can bring a new device onto a vault and can choose or change which remote vault a local vault syncs to — without re-entering credentials and without losing data.";
        :>> priority = Priority::should;
    }

    // ---- Needs surfaced by the embedded-timestamp / conflict-noise work (2026-07-29) ----
    // Owner-reported field pain: "wayy too many diff conflicts that are just time metadata".
    requirement nTimestampFidelity : Need {
        :>> id = "d7c10001-0000-4a10-9b20-a1b2c3d40001";
        :>> title = "My notes' modified/created times are accurate and portable";
        :>> source = NeedSource::customer;
        :>> statement = "Each note carries a trustworthy record of when it was actually created and last changed — one that survives copying or moving the file between machines and is reflected in the file's own timestamps — so time-based and 'recently edited' views can be relied on.";
        :>> priority = Priority::must;
    }
    requirement nNoMetadataConflicts : Need {
        :>> id = "d7c10002-0000-4a10-9b20-a1b2c3d40002";
        :>> title = "Timestamp-only differences never cause sync conflicts";
        :>> source = NeedSource::customer;
        :>> statement = "When two devices hold a note whose content is identical apart from a timestamp/metadata field, sync resolves it silently and correctly rather than surfacing a conflict — the user is never asked to adjudicate a difference that is not a real content change.";
        :>> priority = Priority::must;
    }

    // ---- Backfill (2026-08-03, owner-directed): Needs for capabilities that shipped organically with
    // no upstream "what/why" — accounts/auth, operator administration, one-link onboarding, honest
    // status (STPA L-5), vault health, and auditability. Rooting them makes requirement-rootedness +
    // tier-satisfaction guard them going forward (the same lesson as the nConfigSync orphan, D0011). ----
    requirement nAccountSecurity : Need {
        :>> id = "c0f1a5cc-e201-4a10-9b20-a1b2c3d40201";
        :>> title = "My account is protected by strong authentication I control";
        :>> source = NeedSource::safety;
        :>> statement = "A user's account is protected by a strong password; they can change their password and end other sessions at will; repeated wrong guesses are throttled; and neither the plaintext password nor a standing secret is ever exposed. Signing in never reveals which accounts exist. (D0038: TOTP MFA was deprecated — the plugin cannot answer a TOTP challenge — so a second factor is no longer part of this Need; the flag-gated code is retained for a web-admin-only re-enable.)";
        :>> priority = Priority::must;
    }
    requirement nAccountAdministration : Need {
        :>> id = "c0f1a5cc-e202-4a10-9b20-a1b2c3d40202";
        :>> title = "The operator controls who can have an account";
        :>> source = NeedSource::operator;
        :>> statement = "The operator decides who may register — closed by default, fully open, or by single-use invite — and can create, delete, promote, and reset accounts through an admin interface, without editing files or operating a database.";
        :>> priority = Priority::should;
    }
    requirement nOnboardNewUser : Need {
        :>> id = "c0f1a5cc-e203-4a10-9b20-a1b2c3d40203";
        :>> title = "Someone new can join with a single link";
        :>> source = NeedSource::customer;
        :>> statement = "A person with no account yet can be brought on board with one link: a vault share link lets them create an account (or sign in) and start syncing the shared vault, and an account-creation link lets them make an account even when open registration is closed — without the operator hand-provisioning them first.";
        :>> marketJustification = "One-link onboarding removes the account-provisioning friction that otherwise makes self-hosted sharing hard to adopt.";
        :>> priority = Priority::should;
    }
    requirement nHonestStatus : Need {
        :>> id = "c0f1a5cc-e204-4a10-9b20-a1b2c3d40204";
        :>> title = "The UI never misleads me about my data's sync state";
        :>> source = NeedSource::safety;
        :>> statement = "Every sync indicator is a truthful projection of the actual sync engine: it never shows 'synced' or 'OK' when the connection is down or sync is not converging, it never gets stuck on a stale state, and when something is wrong it names the actionable cause. The user can always trust what the UI tells them about whether their notes are safely synced.";
        :>> marketJustification = "Ambiguous, stuck, or falsely-green sync state erodes trust and is a top LiveSync confusion; an always-honest status is both a differentiator and a safety property (STPA L-5).";
        :>> priority = Priority::must;
    }
    requirement nVaultHealth : Need {
        :>> id = "c0f1a5cc-e205-4a10-9b20-a1b2c3d40205";
        :>> title = "I can keep vaults healthy and storage bounded";
        :>> source = NeedSource::operator;
        :>> statement = "A vault whose index is degraded self-heals on access; when it cannot, a one-click repair rebuilds it from what is on disk; and storage stays bounded — unreferenced data is swept and the operator can deliberately reclaim deletion history — all without a database to babysit.";
        :>> priority = Priority::should;
    }
    requirement nAuditability : Need {
        :>> id = "c0f1a5cc-e206-4a10-9b20-a1b2c3d40206";
        :>> title = "Security-relevant actions are recorded for accountability";
        :>> source = NeedSource::regulatory;
        :>> statement = "Every security-relevant action — sign-in success and failure, lockout, account/registration/invite/share/vault/admin changes, and authorization denials — is recorded as structured, reviewable audit data carrying who/what/when/outcome/source, so an operator can hold the deployment to a compliance posture.";
        :>> priority = Priority::should;
    }
    requirement nChangeAttribution : Need {
        :>> id = "c0f1a5cc-e207-4a10-9b20-a1b2c3d40207";
        :>> title = "Know when SOMEONE ELSE changed my synced settings";
        :>> source = NeedSource::customer;
        :>> statement = "When a synced Obsidian setting or plugin changes, I want to be told WHO made it — and notified only when it was NOT me: a change from another person (or, by choice, from another of my own devices) is surfaced for review, while my own edits stay silent. The trigger is the SOURCE of the change, never whether the vault is shared. Attribution is by authenticated account plus a stable device identity, so it can't be dodged or forged by renaming a device.";
        :>> priority = Priority::should;
    }
    requirement nPushPullPreview : Need {
        :>> id = "c0f1a5cc-e208-4a10-9b20-a1b2c3d40208";
        :>> title = "Push and Pull show WHAT will change and BETWEEN WHICH endpoints";
        :>> source = NeedSource::customer;
        :>> statement = "Before I authoritatively Push a plugin's settings to the server (and thereby my other devices) or Pull the server's copy over my own, I want to SEE what the overwrite will do — which files are overwritten, added, or removed (and, for text settings, the content differences) — and clearly FROM which endpoint TO which (this device <-> the server + other devices). An authoritative overwrite must be an INFORMED choice, not a blind one; a generic 'this overwrites the server's copy' warning that never says what or how much is not enough.";
        :>> priority = Priority::should;
    }
    requirement nPluginSyncAutopilot : Need {
        :>> id = "c0f1a5cc-e20b-4a10-9b20-a1b2c3d4020b";
        :>> title = "Set-and-forget plugin sync — new plugins sync automatically; only another PERSON's needs approval";
        :>> source = NeedSource::customer;
        :>> statement = "I want to define correct plugin-sync behavior ONCE and never open the SelfSync tab again: with 'auto-sync new plugins' on, a plugin I install on any of MY devices is automatically synced everywhere (uploaded here; auto-adopted + hot-loaded on my other devices). A plugin added by ANOTHER PERSON on a shared vault must never auto-adopt — it waits for my explicit approval, made clear by BOTH a toast AND a persistent 'awaiting approval' place in settings (popups vanish too fast). Default off (opt-in), since auto-propagating executable plugin code is security-sensitive. Gating is keyed on the authenticated committing account (not a spoofable device name).";
        :>> priority = Priority::should;
    }
    // ---- Client<->server protocol compatibility (D0042, 2026-08-11) — roots the version-handshake
    // capability that previously lived as an un-requiremented single integer + exact-match check. ----
    requirement nProtocolCompat : Need {
        :>> id = "1c698370-47a6-473c-b535-f6668b1bde59";
        :>> title = "Client and server never silently operate on an incompatible wire contract";
        :>> source = NeedSource::safety;
        :>> statement = "When a client and server are on versions whose sync wire contract is incompatible, sync REFUSES rather than silently misbehaving or corrupting data, and tells me the SPECIFIC incompatibility (which field/endpoint one side expects that the other does not) with actionable guidance — while a change that does NOT alter the wire contract (a bugfix) keeps syncing across a version skew with no friction. Compatibility is judged from what the two ends actually exchange, not from a version number a human might set wrong.";
        :>> marketJustification = "An opaque 'version mismatch' or, worse, a silent mis-write across incompatible versions erodes trust in a sync tool holding the user's notes; a precise, self-explaining compatibility gate that still tolerates bugfixes is both a safety property and an operability differentiator over a hand-bumped lockstep integer.";
        :>> priority = Priority::must;
    }

    // ---- SPIKES (pinned 2026-08-07, owner) — big features that need their own brainstorm before any build. ----
    requirement nPerUserConfigScope : Need {
        :>> id = "c0f1a5cc-e209-4a10-9b20-a1b2c3d40209";
        :>> title = "Per-user (personal) config scope on a shared vault — 'for me' vs 'for everyone'";
        :>> source = NeedSource::customer;
        :>> statement = "On a vault shared with OTHER people, I want to choose per config/plugin whether it is SHARED (everyone who uses the vault gets it — e.g. dataview, which the notes rely on) or PERSONAL (synced across MY devices only, never imposed on peers — e.g. my theme/appearance). Today a shared vault is ONE store everyone reads, so 'synced' necessarily means 'everyone'; a personal scope requires the server to store config per (vault, user) as a personal overlay on the shared vault. SPIKE: a real server feature — needs its own brainstorm/design before any build (owner confirmed they do share vaults, so this is genuinely in scope).";
        :>> priority = Priority::could;
    }
    requirement nComposeRecipe : Need {
        :>> id = "c0f1a5cc-e20c-4a10-9b20-a1b2c3d4020c";
        :>> title = "Replicate a composition via an opt-in, reviewed recipe — without a sharer pushing config or credentials";
        :>> source = NeedSource::customer;
        :>> statement = "When I share a vault, I want the person I share it with to be able to reproduce the WAY I assembled it (which folders come from which vaults) without hand-configuring every mount — but a composition is a per-device choice, colocated with credentials, and references sources the reader may not have access to, so a share must NEVER auto-push my mount config. Instead I can COPY my composition as a portable recipe (mount specs only — never a token, password, or server login) and send it; the reader PASTES it and REVIEWS each mount, applying only the ones they choose, into their OWN local folders, with direction fail-closed (Sync only where their own grant permits, otherwise read-only Pull), and a source they lack access to is shown with guidance rather than silently grabbed. Opt-in on both ends: the sharer chooses to export, the reader chooses to apply.";
        :>> priority = Priority::could;
    }
    requirement nComposedVaults : Need {
        :>> id = "c0f1a5cc-e20a-4a10-9b20-a1b2c3d4020a";
        :>> title = "Compose a shared DATA-ONLY part of one vault into another (directional nested vaults)";
        :>> source = NeedSource::customer;
        :>> statement = "I want a shared PART of a vault to appear inside another vault — DIRECTIONALLY (my personal vault pulls in my ASI notes, but my ASI vault does NOT pull in personal) and COMPOSED so the data lives side by side. DATA ONLY (notes/attachments), never config/plugins — because when two vaults compose, which vault owns a plugin's settings is indeterminate, so config is deliberately out of scope (owner's key insight that makes it tractable). No known Obsidian plugin does this today; SelfSync is well-positioned since it already maps a vault to a server vault, so a shared subfolder mapping to a shared server-vault is a natural extension. SPIKE: needs its own brainstorm/design before any build.";
        :>> priority = Priority::could;
    }

    // ---- lineage: top goals derive from the Brief; sub-needs from their goal ----
    #DependsOn dependency from nVaultSharing to selfsyncBrief;
    #DependsOn dependency from nReliableSync to goal2SimpleBackend;
    #DependsOn dependency from nVaultManagement to goal1ClearConfig;
    #DependsOn dependency from goal1ClearConfig to selfsyncBrief;
    #DependsOn dependency from goal2SimpleBackend to selfsyncBrief;
    #DependsOn dependency from goal3ConflictMerge to selfsyncBrief;
    #DependsOn dependency from n1GuidedSetup to goal1ClearConfig;
    #DependsOn dependency from n1OneHomePerSetting to goal1ClearConfig;
    #DependsOn dependency from n1SingleIndicator to goal1ClearConfig;
    #DependsOn dependency from nConfigSync to goal1ClearConfig;
    #DependsOn dependency from n2NoCouchDB to goal2SimpleBackend;
    #DependsOn dependency from n2Dedup to goal2SimpleBackend;
    #DependsOn dependency from n2Performance to goal2SimpleBackend;
    #DependsOn dependency from n3ThreeWayMerge to goal3ConflictMerge;
    #DependsOn dependency from n3NeverClobber to goal3ConflictMerge;
    #DependsOn dependency from n3Unpaywalled to goal3ConflictMerge;
    #DependsOn dependency from nTimestampFidelity to goal3ConflictMerge;
    #DependsOn dependency from nNoMetadataConflicts to goal3ConflictMerge;

    // ---- backfill lineage (2026-08-03) ----
    // Account auth + auditability decompose the security Need; administration + onboarding are
    // post-launch capabilities off the Brief (like nVaultSharing); honest status decomposes the
    // clear-config goal; vault health decomposes the simple-backend goal.
    #DependsOn dependency from nAccountSecurity to nxSecurity;
    #DependsOn dependency from nAuditability to nxSecurity;
    #DependsOn dependency from nAccountAdministration to selfsyncBrief;
    #DependsOn dependency from nOnboardNewUser to selfsyncBrief;
    #DependsOn dependency from nHonestStatus to goal1ClearConfig;
    #DependsOn dependency from nVaultHealth to goal2SimpleBackend;
    // Change attribution — knowing WHO changed a synced setting — is a collaboration/multi-device trust
    // capability, so it decomposes the sharing Need (2026-08-05).
    #DependsOn dependency from nChangeAttribution to nVaultSharing;
    // Push/Pull transparency — showing what an authoritative overwrite will do + between which endpoints —
    // is the honest-status (non-misleading-UX) principle applied to a destructive action (2026-08-05).
    #DependsOn dependency from nPushPullPreview to nHonestStatus;
    // Set-and-forget plugin sync + peer-approval gating decomposes the config-sync Need (2026-08-07).
    #DependsOn dependency from nPluginSyncAutopilot to nConfigSync;
    // Spikes (2026-08-07): per-user config scope decomposes the sharing Need; composed vaults is a novel
    // capability off the Brief. Both pinned for a later brainstorm.
    #DependsOn dependency from nPerUserConfigScope to nVaultSharing;
    #DependsOn dependency from nComposedVaults to selfsyncBrief;
    // The recipe capability (2026-08-17) is an opt-in replication path for a composition — it decomposes both
    // the composed-vaults Need (what is replicated) and the sharing Need (the without-pushing-config posture).
    #DependsOn dependency from nComposeRecipe to nComposedVaults;
    #DependsOn dependency from nComposeRecipe to nVaultSharing;
    // Also root the two pre-existing cross-cutting Needs that had no Brief lineage edge.
    #DependsOn dependency from nxMobile to selfsyncBrief;
    #DependsOn dependency from nxSecurity to selfsyncBrief;
    // Protocol compatibility (D0042) is the honest-status principle applied to the version handshake:
    // never silently proceed when the two ends can't safely speak the same wire contract; name the cause.
    #DependsOn dependency from nProtocolCompat to nHonestStatus;

    // ---- End-to-end content privacy (st009 / us012, 2026-11-10; D0096 reverses D0009) ----
    // The threat model and the "content only" boundary are the AI's proposal, not elicited: the owner
    // said "end to end encryption" and did not state a threat model or a threshold (us012 triage note).
    requirement nE2eeContentPrivacy : Need {
        :>> id = "99d12bae-b287-41d2-9408-cb61d7a43740";
        :>> title = "Note content is unreadable by the server";
        :>> source = NeedSource::customer;
        :>> statement = "When I choose it for a vault, the content of every synced file is encrypted on my devices before upload and decrypted only on my devices. A compromised, curious, or seized server, and anyone with its data volume, cannot read note content. The server still cannot read it when I share the vault with another account. If the server alters, swaps, drops, or reorders any part of a file, or serves one file's content under another path, my device detects it and does not overwrite my local copy. A device of mine that runs an older SelfSync build never writes ciphertext into my vault and never writes plaintext into the encrypted vault. A device that joined the encrypted vault never falls back to plaintext because the server says the vault is not encrypted. NOT PROTECTED, stated so that I can accept it knowingly: file paths, sizes, mtimes, version numbers, device names and author stay visible. Which chunks are equal within the vault stays visible, and the sequence of chunk lengths can fingerprint a known document. The server can serve an older version of a file. Anyone with the stored key record can guess my encryption password offline, so the password has a length floor. A plaintext copy that existed before I chose encryption lives on in earlier backups. My device itself, and when and how often I edit, are not protected. Losing the encryption password loses the data, and the setup says so before I choose it.";
        :>> marketJustification = "A self-hosted sync tool whose host can read every note cannot be run on rented or shared infrastructure. Obsidian Sync and LiveSync both offer content E2EE; without it SelfSync is only safe on hardware the user fully controls, which excludes the common VPS deployment.";
        :>> priority = Priority::must;
    }
    #DependsOn dependency from nE2eeContentPrivacy to nxSecurity;
    #DerivedFrom dependency from nE2eeContentPrivacy to us012;
}
