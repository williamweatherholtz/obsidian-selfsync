// Per-actor issues records for claudeOpus (issue210/srDcPerActorWriteTargets): new records
// route here so concurrent contributors never conflict at a shared append anchor.
package IssuesClaudeOpus {
    private import EngineElement::*;
    private import EngineWork::*;
    private import EngineVerification::*;
    private import EngineRelationships::*;

    #ProcessDefect part issueNestedCoversEdgesSkipped : Issue {
        :>> id = "15a1983f-a7ca-4717-a8f8-014cc2d3116f";
        :>> title = "keel-parser silently skips the 74 nested #Covers edges inside action def SelfSyncDelivery - sitting-coverage read 0 covered against 74 authored covering edges";
        :>> createdAt = "2026-09-07";
        :>> createdBy = "claudeOpus";
        :>> description = "Found 2026-09-07 while reading the parser-coverage warning after the engine resync onto keel 0.3.1. The guard reported 81 skipped statements: 7 successions (the engine's own baseline) plus 74 `dependency` statements it did not locate. Measured by comparing grep counts to the AST census (`keel show marker-census`): every marker matched except #Covers - 74 in the text, 0 AST edges. All 74 `#Covers dependency from <sittingReview> to <sprintTask>;` lines sat at indent 8 INSIDE `action def SelfSyncDelivery { ... }` in .tracking/delivery/delivery.sysml, whereas the 114 #Verify edges that DID count sit at package level. keel-parser skips a dependency statement nested inside an action body, and it does so silently: `keel check` on a probe file with the nested form reports 'checked clean' (as do probes with two statements on one line and with a trailing comment, which were the first hypotheses and are NOT the cause). CONSEQUENCE: the sitting-coverage lens (D0049/issue040 - which delivery sprints have a covering per-sitting human review) read 0 covered while the record contained 74 covering edges, and the sitting-coverage guard was blind in the direction that matters - it could not have caught a sprint that genuinely lacked a review, because to it none had one. The per-sitting review is the single human gate in this project's sprint discipline (D0049), so this was the control most worth being able to see. FIX (coversEdgesHoisted, same commit): the 74 edges hoisted verbatim to package level; Covers AST edges 0 -> 74; parser-coverage skipped 81 -> 7; sitting-coverage now counts covered sittings. GUARD (D0047): the parser-coverage ratchet in .engine/contracts/parser-coverage-baseline.toml, set at the stock 7 - any new nested edge raises the skipped count and fails the gate, so this class cannot recur silently. UPSTREAM (keel toolkit): a construct the parser does not read should be a parse error, not a clean check; carried with the reproduction. discoveredInField = false. Severity Medium: no data at risk, but a governance control reported a false zero for the whole life of the record.";
        :>> discoveredInField = false;
        :>> relatedTask = "coversEdgesHoisted";
        :>> severity = Severity::Medium;
    }
    #Resolves dependency from coversEdgesHoisted to issueNestedCoversEdgesSkipped;

    part issueHistoricalDoDsUnstamped : Issue {
        :>> id = "1ebd18c7-aa30-497f-bda7-bf2a059487ad";
        :>> title = "103 delivery DoDs (80 method=test) read DONE in prose but carry no TestResult - shipped work with unrecorded verdicts; blocks honest #Verify edges for sr11/sr16/sr19";
        :>> createdAt = "2026-09-07";
        :>> createdBy = "claudeOpus";
        :>> description = "Found 2026-09-07 while authoring #Verify edges from Tests to the 25 STPA SafetyRequirements. A census of .tracking/delivery/delivery.sysml shows 103 verification Tests (DoDs) with no TestResult of any kind: 80 method=test, 14 inspect, 3 demo, 1 analyze, 1 critique, 4 confirmation. Their action comments and procedure texts read DONE and name the releases they shipped in (m1ProtocolDoD .. round7RecoveryFixesDoD, autoReindexDoD, uiFunctionalAuditDoD, round1DeferredHardeningDoD and others), and .tracking/verification/acceptance.sysml adds 5 unstamped method=test acceptance Tests for the embedded-timestamp requirements that timestampIgnoreRedesign (1.9.0) retired. CONSEQUENCE: (a) three SafetyRequirements (sr11 refuse-reindex-over-incomplete-directory, sr16 operator-repair-any-vault, sr19 bound-uncommitted-storage) cannot honestly carry a #Verify edge although the verifying server tests exist and pass - the DoD that owns each was never stamped; (b) every computed lens that keys on recorded verdicts (assured, tier-satisfaction, sitting-coverage, whats-next) under-reports work that shipped, while the prose over-reports it - the exact drift CLAUDE.md 2.1 exists to prevent (prose is not truth; the verdict is). WHY IT HAPPENED: these DoDs predate the write-API (2026-06-15) becoming the primary path and the evidence-cited convention (2026-08-25); DONE was written into the comment and the result never appended. Not fabricated here: a pass without a receipt would be a testimony, not a record (D0232). RESOLVER: dodBackfillStamp - classify each as reproducible (stamp at HEAD with a real run receipt), mooted (record the superseding decision as basis), or owner-judgment (listed for the owner), with reconciled control totals (D0067). discoveredInField = false. Severity Medium: no data at risk, but the record's honesty is the deliverable of this engine.";
        :>> discoveredInField = false;
        :>> relatedTask = "dodBackfillStamp";
        :>> severity = Severity::Medium;
    }
    #Resolves dependency from dodBackfillStamp to issueHistoricalDoDsUnstamped;

    #ProcessDefect part issueE2eObsidianBelowMinAppVersion : Issue {
        :>> id = "f661d25a-2a19-4aed-8a73-ce262035986d";
        :>> title = "real-Obsidian e2e ran green on Obsidian 1.5.8, below the plugin's minAppVersion 1.11.0 - a green run outside the supported envelope proves nothing";
        :>> createdAt = "2026-09-07";
        :>> createdBy = "claudeOpus";
        :>> description = "Found 2026-09-07 while trying to automate l3GuiPass (the manual GUI pass) as a real-Obsidian Playwright demonstration. The machine's Obsidian is 1.5.8 (Electron 28 / Chrome 120); manifest.json declares minAppVersion 1.11.0, and client/src/settings.ts imports SettingGroup from the obsidian API, which 1.5.8 does not provide. The e2e-obsidian suite (smoke, configsync, convergence) nevertheless ran GREEN on 1.5.8 this sitting, because those specs only load the plugin and sync files - they never open the settings tab. So the layer that exists to prove the real glue works was proving it on an Obsidian no user of this plugin can run (Obsidian refuses to enable a plugin below minAppVersion), and the first spec to touch the settings UI would have failed for a reason unrelated to the plugin. Hazard class: a test environment silently outside the supported envelope - green means nothing, red means noise. FIX (e2eObsidianVersionGate): obsidianDriver reads the running version from the renderer user agent and every spec skips loudly, naming installed vs. minimum, when the install is below the floor. The operator-facing consequence is honest: on this machine the real-Obsidian layer now SKIPS until Obsidian is updated to >= 1.11.0 - which is also what l3GuiPass needs before it can be demonstrated. discoveredInField = false. Severity Medium (assurance defect, no data at risk).";
        :>> discoveredInField = false;
        :>> relatedTask = "e2eObsidianVersionGate";
        :>> severity = Severity::Medium;
    }
    #Resolves dependency from e2eObsidianVersionGate to issueE2eObsidianBelowMinAppVersion;

    part issueConflictDiffSidesUnlabeled : Issue {
        :>> id = "8b5562eb-44f8-4b69-aa3c-1de295f11619";
        :>> title = "Resolve-conflicts modal: which side is − and which is + was fine print; the keep-buttons carried no sign";
        :>> createdAt = "2026-09-07";
        :>> createdBy = "claudeOpus";
        :>> description = "Owner field report 2026-09-07 on the Resolve-conflicts modal: 'you say 'keep this device's' or keep the other's but you give no indication as to which one is − and which one is + in diff view. it should be concise and clear.' Cause: the only mapping from diff sign to side was an 11px, 70%-opacity legend line above the diff ('− the other version + this device's'), styled like fine print and worded differently from the buttons, while the two keep-buttons ('Keep the other device's' / 'Keep this device's') carried no sign at all - so a reader looking at red/green lines had to hunt for the mapping before an irreversible choice. Consequence: a user could keep the wrong side (data loss on the other device's edit) or stall on a conflict they could otherwise resolve in a second. Fix (conflictDiffSideLegend): the header names the mapping in words, the legend is two bold spans in the diff's own red/green with the signs, and the buttons carry the signs ('Keep − other device's' / 'Keep + this device's'). Guarded by a DOM test. discoveredInField = true. Severity Medium (a UX defect on the one irreversible control in the plugin).";
        :>> discoveredInField = true;
        :>> relatedTask = "conflictDiffSideLegend";
        :>> severity = Severity::Medium;
    }
    #Resolves dependency from conflictDiffSideLegend to issueConflictDiffSidesUnlabeled;

    part issueRejectedPushRetriedEveryPass : Issue {
        :>> id = "df1034a6-0d81-4b71-a39d-c9986a249f6a";
        :>> title = "Server-refused pushes (commit: HTTP 400) were re-sent on every pass with the reason thrown away - ~500 futile uploads per reconcile made the UI crawl";
        :>> createdAt = "2026-09-07";
        :>> createdBy = "claudeOpus";
        :>> description = "Owner field report 2026-09-07: 'it's much slower now' - opening the Resolve-conflicts modal, clicking anything. The debug log showed why: the connect pass was PUSHING several hundred files under the PARA roots (4 Archive/**, 3 Resources/**, 2 Areas/**, 99 Utilities/**) - notes, PDFs, images alike - and the server answered 'commit: HTTP 400' for every one; 'checked 750/1835 files' arrived at +118.8s and the pass was still running at +165s, on a vault whose no-op rescan the perf harness completes in ~150 ms. Two client defects made this what it was. (1) transport.commit threw a bare 'commit: HTTP 400', discarding the server's body - which is the client-actionable reason (the server returns validation failures verbatim) - so neither the user nor the code could see WHY. (2) reconcile treated a 400 like any transient per-file error: the next pass re-read, re-chunked, queried missing chunks, re-uploaded and re-committed the identical content, and was refused again - for every file, every pass, forever. The reconcile loop runs on the renderer's main thread with the modal and settings tab, hence 'clicking anything' is slow. FIX (rejectedPushHold): a typed CommitRejectedError carrying the server text; a (path -> refused hash) memo so an unchanged rejected file is HELD (one summary log line per burst) until it is edited or the plugin reloads; 409/404 stay retryable. ROOT CAUSE OF THE REFUSALS IS STILL OPEN and will be named by 1.30.9's log. Leading hypothesis from the evidence: every rejected path sits under a top-level folder whose CAPITALISATION may differ between this Windows vault and the server's index keys - the server's commit guard refuses 'a path differing only in case already exists' - i.e. a case-only folder rename on a case-insensitive filesystem, which decide() sees as a local-only-new file (push) plus a remote file that a presence re-probe says is still present (no delete), so the two never converge. If confirmed, the fix is case-aware path identity on case-insensitive filesystems (a follow-up issue with its own resolver). discoveredInField = true. Severity High: the sync loop was doing hundreds of futile uploads per pass and the UI was unusable while it ran.";
        :>> discoveredInField = true;
        :>> relatedTask = "rejectedPushHold";
        :>> severity = Severity::High;
    }
    #Resolves dependency from rejectedPushHold to issueRejectedPushRetriedEveryPass;

    part issueCasePathDivergence : Issue {
        :>> id = "0602d5d2-2339-4861-8665-38afba8c25bb";
        :>> title = "Case-only folder capitalisation difference between a Windows vault and the server made every file in those folders unpushable - and edits there silently did not sync";
        :>> createdAt = "2026-09-07";
        :>> createdBy = "claudeOpus";
        :>> description = "Confirmed 2026-09-07 from the owner's 1.30.9 log: every refused push read 'the server refused it - a path differing only in case already exists' - hundreds of files under 4 Archive/**, 3 Resources/**, 2 Areas/**, 99 Utilities/**. The server's index holds those folders in a different capitalisation than this Windows vault reports. Path identity in the client was exact-case everywhere (base keys, manifest keys, decide()), while the filesystem underneath is case-insensitive, so a case-only divergence produced: (a) the local spelling has no base/remote key -> decide() = local-only-new -> push -> the server's collision guard refuses it (correctly - it protects case-sensitive servers from two keys folding onto one file); (b) the server's spelling is 'absent' from the local listing, but the false-absence re-probe (adapter.exists, case-insensitive) says present -> no delete -> the pair never converges; (c) and the DATA hazard: an edit made under the local spelling changes a file the client can only push under a refused key - edits in those folders did not sync at all, silently, since whenever the capitalisation diverged. Performance was the visible symptom (~500 futile uploads per pass, 1.30.9 held them after the first pass); the silent non-sync of edits is the real defect. FIX (casePathAlias): on case-insensitive platforms the local spelling is aliased to the existing server/base key for sync identity, in the full pass, the config pass and the vault-event path; nothing is renamed; the server keeps its spelling; Linux/Android untouched. ROOT CAUSE of the divergence itself (which device re-capitalised the folders, and when) is not knowable from the record; the client must simply be correct under it. discoveredInField = true. Severity High: silent non-sync of edits in a whole folder tree.";
        :>> discoveredInField = true;
        :>> relatedTask = "casePathAlias";
        :>> severity = Severity::High;
    }
    #Resolves dependency from casePathAlias to issueCasePathDivergence;

    part issueBusyStateNotSurfaced : Issue {
        :>> id = "fac1e0a7-587e-4d6c-aaef-de20fa781936";
        :>> title = "A sync pass in progress made the conflict/config/switch modals unusable for minutes with no indication of the state or the reason - functions were unavailable invisibly";
        :>> createdAt = "2026-09-07";
        :>> createdBy = "claudeOpus";
        :>> description = "Owner 2026-09-07, after the Resolve-conflicts modal sat on its placeholder for the whole 152 s first aliased pass: 'this state should be tracked and indicated somewhere. better transparency, especially if it affects availability of functions. maybe just grey out some options until actually ready, along with an indication as to why? state tracking'. The plugin knew it was busy - the status light said 'Connecting... checked 750/1420 files' - but no surface whose FUNCTION that state degraded said so: the conflict modal, the config-differences modal and the vault switcher all rendered their committing buttons as if ready while their own file reads queued behind the pass (on a large vault, minutes), so the user read 'broken' where the truth was 'busy, here is why, here is when'. Transparency defect on the plugin's irreversible controls. FIX (busyStateGating): busyState() as a pure projection + onBusyChange() subscription; busygate.ts mounts a reason banner and disables the committing buttons in the three modals until the plugin reports settled; the action handlers also refuse with the reason. discoveredInField = true. Severity Medium (no data at risk; availability of functions was invisible).";
        :>> discoveredInField = true;
        :>> relatedTask = "busyStateGating";
        :>> severity = Severity::Medium;
    }
    #Resolves dependency from busyStateGating to issueBusyStateNotSurfaced;

    part issueConflictModalHangsOnBinary : Issue {
        :>> id = "e4a89857-a36d-47d0-8cf3-085cda19b435";
        :>> title = "Resolve-conflicts modal hung indefinitely on a ~200 MB .mp4 conflict - it read both versions as text and line-diffed them";
        :>> createdAt = "2026-09-08";
        :>> createdBy = "claudeOpus";
        :>> description = "Owner field report 2026-09-08: 'resolve totally hangs - i see no diff, just 2 files need review. Looks like it's an mp4 that multiple files edited at once (which almost surely didn't actually happen)'. The vault holds a conflict copy of a ~200 MB .mp4 (the same recording the size gate logs as 'over this device's 200 MB sync limit'). NoteConflictModal.render read BOTH versions with readTextOrEmpty - TextDecoder over 200 MB on the renderer's main thread, twice - then handed the two giant strings to unifiedLineDiff and revealInvisible: a multi-second-to-indefinite freeze with nothing on screen but the header, i.e. 'totally hangs'. The 1.30.5 cosmetic-conflict sweep already gated on isTextExt/strictDecode; the modal's own render path never did, so the one surface a user reaches for on a binary conflict was the one that could not survive it. FIX (conflictModalBinaryView): decide from fileStat (no read) - binary extension or text > 4 MB -> the no-diff view (sizes + dates per side, same keep choices, nothing read, no stale-preview guard because nothing was previewed). WHY THE MP4 HAD A CONFLICT COPY AT ALL (not fixed here, likely benign): the file is the meeting recording that was still being written into the vault while a pull ran, and conflictCopyIfRaced preserves a local file whose bytes changed during a pull as a copy - or the recording crossed the 200 MB limit between devices; either produces exactly one copy and no data loss. discoveredInField = true. Severity High: the resolve surface hung indefinitely on a real conflict.";
        :>> discoveredInField = true;
        :>> relatedTask = "conflictModalBinaryView";
        :>> severity = Severity::High;
    }
    #Resolves dependency from conflictModalBinaryView to issueConflictModalHangsOnBinary;

    part issueResolutionHadNoState : Issue {
        :>> id = "f89a7e36-fed9-48e3-b2ff-898b245a4237";
        :>> title = "Resolving a conflict dimmed the whole modal with no state - working, hung or done were indistinguishable, and the upload it triggers was invisible";
        :>> createdAt = "2026-09-08";
        :>> createdBy = "claudeOpus";
        :>> description = "Owner 2026-09-08: 'give me a state machine during resolution, like updating server... or something. can't just gray the modal on me. UX'. Pressing Keep in the Resolve-conflicts modal dimmed the whole body (opacity .55, pointer-events none) until resolveNoteConflict returned: on a large vault that is a preview re-check, a read, a write and a delete - plus an enqueued upload the modal did not wait for - with the only signal being a greyed screen. The user could not tell whether it was working, hung, or done, and the upload the resolution actually triggers was invisible entirely. Same class as issueBusyStateNotSurfaced (functions in a state the surface did not show), on the one irreversible control. FIX (resolutionStateMachine): the pressed button narrates the plugin's real steps via onStage and then 'Updating the server…' until the engine settles (bounded); the other keep-button disabled, Copy/Close live, no dimming. discoveredInField = true. Severity Medium.";
        :>> discoveredInField = true;
        :>> relatedTask = "resolutionStateMachine";
        :>> severity = Severity::Medium;
    }
    #Resolves dependency from resolutionStateMachine to issueResolutionHadNoState;

    part issuePreserveBothRequiredEditorMerge : Issue {
        :>> id = "f585818d-40d6-40f6-bd64-c46a77fde1d8";
        :>> title = "Preserving both versions of a conflict required the slow editor merge - there was no one-press 'keep both'";
        :>> createdAt = "2026-09-08";
        :>> createdBy = "claudeOpus";
        :>> description = "Owner 2026-09-08: 'open both to merge is so incredibly slow... maybe just keep both that auto keeps both content? i don't want to open it up and merge all the time, most of the time i just want to preserve data'. The modal offered three outcomes - discard the other device's version, discard this device's version, or hand-merge in the editor - so the most common intent, 'lose nothing, decide later', was only reachable through the slowest path (opening both files as editor panes) or by leaving the conflict unresolved. FIX (keepBothResolution): 'Keep both' - one press turns the conflict copy into an ordinary note beside the original ('<name> (this device's version <date>)'), both sync, the conflict ends, nothing is merged by hand; first among the choices; 'Open both to merge' kept last. discoveredInField = true. Severity Medium (UX: the safe outcome was the expensive one).";
        :>> discoveredInField = true;
        :>> relatedTask = "keepBothResolution";
        :>> severity = Severity::Medium;
    }
    #Resolves dependency from keepBothResolution to issuePreserveBothRequiredEditorMerge;

    part issueEngineFsmNotOnPrimitive : Issue {
        :>> id = "244f6d23-b55d-481d-bd35-20644ae7a799";
        :>> title = "The sync engine's EngineState is the one hazard-bearing state machine not on the shared fsm.ts primitive - no explicit table, STPA registration pending";
        :>> createdAt = "2026-09-08";
        :>> createdBy = "claudeOpus";
        :>> description = "Found 2026-09-08 while putting every hazard-bearing state machine on the shared fsm.ts primitive (owner: 'FSM module, used all across the project in places where states that can introduce hazards exist'). Four of five machines moved cleanly because they were already pure reducers (connstate linkNext, mountfsm, transportstate, resolvefsm). The fifth - the sync engine's EngineState in syncengine.ts, the controller c2SyncEngine's own phase and the most hazard-bearing state in the client (H-6 unavailability, H-9 reported state vs actual, H-10 ceasing recovery) - keeps its transitions as class-internal setState() calls interleaved with effects, so there is no rule table to prove total, no tableCoverage, and the STPA registration is STPA-FSM-PENDING. Not a defect in behaviour (syncengine.test covers the paths that exist) but a gap in the property the FSM discipline exists to give: that every hazard-bearing transition is enumerable and analysed. Resolver engineFsmOnPrimitive. discoveredInField = false. Severity Medium.";
        :>> discoveredInField = false;
        :>> relatedTask = "engineFsmOnPrimitive";
        :>> severity = Severity::Medium;
    }
    #Resolves dependency from engineFsmOnPrimitive to issueEngineFsmNotOnPrimitive;

    part issueSyncToolCoexistenceUnguarded : Issue {
        :>> id = "7882a996-4252-4357-9f58-f6bf7db534b6";
        :>> title = "No coexistence rule for another sync tool operating on the same directory";
        :>> createdAt = "2026-09-10";
        :>> createdBy = "claudeOpus";
        :>> description = "Found by the STPA over the same-device authorities (2026-09-10, UCA-52 / SR-47 in .tracking/safety/stpa-authorities.sysml). Step 1 recorded 'other sync tools' as an authority present in the owner's own vault (`.sync-conflict-*` files exist there), but the plugin has no coexistence rule: it neither detects a co-located tool nor recognises that tool's artefacts, so another tool's conflict copies sync everywhere as authored content, and two tools rewriting one file have nothing bounding the loop (the plugin bounds only the echo of its own writes). Hazard H-13 (another same-device authority) and H-6 (a rewrite loop starves real changes). Non-trivial: needs an owner call on whether foreign conflict copies are skipped or synced, and a loop breaker with a threshold.";
        :>> discoveredInField = false;
        :>> relatedTask = "syncToolCoexistence";
        :>> severity = Severity::Medium;
    }
    #Resolves dependency from syncToolCoexistence to issueSyncToolCoexistenceUnguarded;

    part issueReleaseAssetIntegrityUnchecked : Issue {
        :>> id = "0ff1a512-8945-408b-b014-b9250c11c341";
        :>> title = "Published plugin assets are checked for presence, never for integrity";
        :>> createdAt = "2026-09-10";
        :>> createdBy = "claudeOpus";
        :>> description = "Found by the STPA over the release-channel authority (2026-09-10, UCA-58 / SR-50 in .tracking/safety/stpa-authorities.sysml). check-release.mjs and verify-released.yml assert that the manifest version is tagged, published and carries the BRAT assets, and check-release-currency bounds unreleased drift, but nothing attests that the published main.js is the CI build of the tagged commit: no recorded digest, no signature, no post-publish comparison. A replaced or corrupted asset installs through BRAT on every device unnoticed (H-5). Non-trivial: touches release.yml, the release script and the plugin's About surface; signing is a separate owner decision.";
        :>> discoveredInField = false;
        :>> relatedTask = "releaseAssetIntegrity";
        :>> severity = Severity::Medium;
    }
    #Resolves dependency from releaseAssetIntegrity to issueReleaseAssetIntegrityUnchecked;

    part issueMountBaseFrozenAcrossScopeBoundary : Issue {
        :>> id = "6a40f9d8-0c60-4803-aff1-60d8525bb0c7";
        :>> title = "Primary base entries freeze under a mounted folder and drive silent overwrites / delete-remotes on unmount";
        :>> createdAt = "2026-09-11";
        :>> createdBy = "claudeOpus";
        :>> description = "Panel 2026-09-11 (composed-vaults critic, CV1..CV5): (1) while a folder is mounted the primary skips it, so its base entries there keep pre-mount values; on remove the primary pushes the mount's content over its own copy with no conflict copy and delete-remotes what the mount removed — fleet-wide (H-1, H-14). (2) Renaming the mount-point folder left the mount localGone while the primary uploaded the peer's whole subtree into the user's vault. (3) A note dragged into a pull mount is tombstoned on the primary and stranded, with a misleading toast. (4) The source grant is read once per connect, so a mid-session downgrade leaves a Sync mount 'In sync' while every push 403s. (5) Four mount lifecycle writes bypass mountMachine (SR-36 false). Resolver: sprint mountScopeBoundaryHardening.";
        :>> discoveredInField = false;
        :>> relatedTask = "mountScopeBoundaryHardening";
        :>> severity = Severity::Medium;
    }
    #Resolves dependency from mountScopeBoundaryHardening to issueMountBaseFrozenAcrossScopeBoundary;

    part issueCaseRenamePairDeletesOnFoldingPeer : Issue {
        :>> id = "6f15f38a-7f33-449d-865a-fc156cdfbb67";
        :>> title = "A case-only rename made on a case-sensitive peer deletes the note fleet-wide on folding peers";
        :>> createdAt = "2026-09-11";
        :>> createdBy = "claudeOpus";
        :>> description = "Panel 2026-09-11 (host critic, H1 BLOCKER + H2..H7): tombstone `Note.md` + upsert `note.md` in one pass name ONE on-disk file on Windows/macOS/iOS; removeLocal deleted the file the upsert adopted and the host's delete event then tombstoned the new key for every peer (H-1, H-11; SR-45 unmet). Also: an in-flight pass keeps writing after onunload (SR-44's safe state false); the mobile per-file cap equals the desktop default (OOM path); persist() runs on every setBase (a whole-data.json write loop); short writes in the streamed writer; the fold index rebuilt per event; timers not cleared on unload. Resolver: sprint hostCoexistenceHardening.";
        :>> discoveredInField = false;
        :>> relatedTask = "hostCoexistenceHardening";
        :>> severity = Severity::High;
    }
    #Resolves dependency from hostCoexistenceHardening to issueCaseRenamePairDeletesOnFoldingPeer;

    part issueIdentityOneSidedPhantomCopies : Issue {
        :>> id = "88aab9b7-e375-4ae2-bdfc-4d89a6614014";
        :>> title = "Content identity is one-sided and its seam / adopt paths can still spawn phantom copies or drop invisible content";
        :>> createdAt = "2026-09-11";
        :>> createdBy = "claudeOpus";
        :>> description = "Panel 2026-09-11 (identity critic, ID1/ID2/ID4/ID5/ID6/ID8): the push→in-sync override stamps the scan-skip hint on a raw-different file and the write seam then copies a stamp-only local on a remote move (UCA-49 'closed' only in the single-sided case); a 'merge' with one cosmetically-changed side conflicts instead of pulling/pushing; adopt-remote drops a masked timestamp line present on one side only; in-fence trimming reaches YAML block scalars; the display does not fold what identity folds; hot-load is keyed on the vault being private now, not on who wrote the code (a peer's main.js under a since-revoked grant executes). Resolver: sprint contentIdentityTwoSided.";
        :>> discoveredInField = false;
        :>> relatedTask = "contentIdentityTwoSided";
        :>> severity = Severity::Medium;
    }
    #Resolves dependency from contentIdentityTwoSided to issueIdentityOneSidedPhantomCopies;

    part issueForeignSkipSnapshotAndPermanentRelease : Issue {
        :>> id = "3919a5d4-6823-4066-a054-1464dd8d4047";
        :>> title = "The 1.30.17 coexistence code froze the skip setting in mount scopes and let a user release disarm the loop breaker permanently";
        :>> createdAt = "2026-09-11";
        :>> createdBy = "claudeOpus";
        :>> description = "Panel 2026-09-11 (other-sync-tools critic, FT1..FT8; identity critic ID3): the mount runtime captured skipForeignArtefacts as a boolean while the mount io read the live setting — a mid-session toggle could tombstone a based foreign path on the SOURCE; 'Upload current versions anyway' set a standing override so the loop resumed unbounded with the row hidden; the default limit misclassified a person toggling a checkbox; foreign paths already on the server were reported as 'config files'; root-marker detection was unreachable (the host never indexes dot paths); toggling the skip off did not resync; the loop breaker did not reach mounts or the merged-push site. Resolver: sprint coexistenceHardening.";
        :>> discoveredInField = false;
        :>> relatedTask = "coexistenceHardening";
        :>> severity = Severity::Medium;
    }
    #Resolves dependency from coexistenceHardening to issueForeignSkipSnapshotAndPermanentRelease;

    part issueReleasePublishedBeforeVerified : Issue {
        :>> id = "37ddcc33-769c-4b0c-986f-67bee8d07999";
        :>> title = "A release is BRAT-installable before it is verified, a tag can be silently reused, integrity has no anchor outside the release, and no version-tagged server image exists";
        :>> createdAt = "2026-09-11";
        :>> createdBy = "claudeOpus";
        :>> description = "Panel 2026-09-11 (release-channel critic, RL1..RL6): release.yml published non-draft before the verify step and treated a partial upload as released; `gh release create --target` reuses a tag pointing elsewhere (assets = build of main-HEAD); SHA256SUMS lives in the same mutable release as the assets, so the daily check could not detect a rewrite of both (H-5); GITHUB_TOKEN-created tags never trigger server-image.yml, so the version-tagged image docs tell operators to pin never existed; mutable action refs, persisted checkout credentials, no Dependabot; check-release.mjs hid gh's real error and downloaded every asset. Resolver: sprint releaseIntegrityHardening (D0054 amended).";
        :>> discoveredInField = false;
        :>> relatedTask = "releaseIntegrityHardening";
        :>> severity = Severity::High;
    }
    #Resolves dependency from releaseIntegrityHardening to issueReleasePublishedBeforeVerified;

    part issueStpaModelClaimsDrift : Issue {
        :>> id = "08dce644-7590-482d-8732-4ec3f92c3dc9";
        :>> title = "The safety model's claims drifted from the code: SR-5 false, six #Verify edges that verify nothing, unanalysed control actions, an unmodelled operator prune, stale prose";
        :>> createdAt = "2026-09-11";
        :>> createdBy = "claudeOpus";
        :>> description = "Panel 2026-09-11 (SE critic, SE1..SE7; identity ID7; release RL3): SR-5 stated 'never, for ANY vault' against shipped hot-load; six #Verify edges cite DoDs that do not exercise the SR; eight control actions had no UCA and c1User none; POST /api/admin/prune-history destroys SR-1's evidence with no ControlAction/UCA/SR; the D0041 incoming mass-deletion hold was load-bearing but unstated; pmSyncEngine beliefs omitted the terminal `unloading` state and the header still said PENDING; c15ReleaseChannel realizes SRs while declared uncommandable; cc49 and cc55/sr50 over-claimed. Resolver: sprint stpaModelHonesty.";
        :>> discoveredInField = false;
        :>> relatedTask = "stpaModelHonesty";
        :>> severity = Severity::Medium;
    }
    #Resolves dependency from stpaModelHonesty to issueStpaModelClaimsDrift;

    part issueMountCaseSensitiveClaimMismatch : Issue {
        :>> id = "6a041daf-23bb-406d-b5ea-c1e477964c99";
        :>> title = "Mount claim folds case while mount I/O uses the configured spelling on a case-sensitive filesystem";
        :>> createdAt = "2026-09-11";
        :>> createdBy = "claudeOpus";
        :>> description = "Panel 2026-09-11 (composed-vaults critic, CV6 MINOR): on Linux a differently-cased real folder is claimed by the mount (primary excludes it) but every read/write is built from the configured spelling and ENOENTs — the files belong to no scope. Deferred with an OPEN resolver (rare platform combination; no data loss, files simply do not sync).";
        :>> discoveredInField = false;
        :>> relatedTask = "mountCaseSensitiveClaim";
        :>> severity = Severity::Low;
    }
    #Resolves dependency from mountCaseSensitiveClaim to issueMountCaseSensitiveClaimMismatch;

    part issueRoMountConflictCopiesInvisible : Issue {
        :>> id = "ee189947-10d7-49b2-8814-e96b766ae8ba";
        :>> title = "Conflict copies produced on a pull mount are invisible to the read-only-edit keeper flow";
        :>> createdAt = "2026-09-11";
        :>> createdBy = "claudeOpus";
        :>> description = "Panel 2026-09-11 (composed-vaults critic, CV7 MINOR): readOnly && isConflictCopy is a noop in reconcile, so roMountEdits never contains such a copy and 'Keep my edits' cannot sweep it; it stays single-device until the mount is removed (then uploads to the primary — now via re-first-contact after CV1). Deferred with an OPEN resolver.";
        :>> discoveredInField = false;
        :>> relatedTask = "mountRoConflictCopyKeeper";
        :>> severity = Severity::Low;
    }
    #Resolves dependency from mountRoConflictCopyKeeper to issueRoMountConflictCopiesInvisible;

    part issueMonotonicRewriteLoopUndetected : Issue {
        :>> id = "36c427fd-cb86-4305-872c-37f7ee5cadf2";
        :>> title = "The SR-47 loop breaker cannot see a monotonic rewrite loop (a never-seen value each round)";
        :>> createdAt = "2026-09-11";
        :>> createdBy = "claudeOpus";
        :>> description = "Panel 2026-09-11 (identity critic, ID3): a stamper on an unmasked key, or in a .txt / excluded folder, produces a novel hash every round; the returning-content detector never holds it. A per-path push-rate bound was rejected (it would hold a person's own rapid autosaves). SR-47's statement now records this honest scope; the detector is an OPEN resolver.";
        :>> discoveredInField = false;
        :>> relatedTask = "monotonicRewriteDetection";
        :>> severity = Severity::Low;
    }
    #Resolves dependency from monotonicRewriteDetection to issueMonotonicRewriteLoopUndetected;

    part issueAcceptanceTextDriftBlocksGate : Issue {
        :>> id = "60624435-999b-4fbb-b18f-dd3766988968";
        :>> title = "Three accepted Decisions' text drifted after acceptance; keel 0.4.1's acceptance-binds-to-text guard blocks every commit until the owner re-binds";
        :>> createdAt = "2026-09-13";
        :>> createdBy = "claudeOpus";
        :>> description = "keel 0.4.1 (D0308, HARD): d0014, d0025, d0046 - their decision/consequences text at HEAD differs from the text at the SHA their acceptance bound to (editorial edits by the agent on 2026-07-05, 2026-07-12, 2026-09-07). The only remedy is the human's `keel accept <d> --rebind --note ...`. Surfaced by the D0057 resync; owner-only.";
        :>> discoveredInField = false;
        :>> relatedTask = "rebindDriftedAcceptances";
        :>> severity = Severity::High;
    }
    #Resolves dependency from rebindDriftedAcceptances to issueAcceptanceTextDriftBlocksGate;

    part issueCompoundDecisionsUnderD0303 : Issue {
        :>> id = "999d234b-93db-467b-9d9e-dea8628e48cc";
        :>> title = "Seven compound Decisions (created on/after 2026-09-05) violate D0303 option C; keel 0.4.1's decision-scaffolding guard blocks every commit until split or grandfathered";
        :>> createdAt = "2026-09-13";
        :>> createdBy = "claudeOpus";
        :>> description = "keel 0.4.1 (D0303 option C, HARD): d0046, d0048, d0050, d0051, d0053, d0054, d0055 enumerate 2-8 clauses each; the guard wants one Decision per clause with #DependsOn edges. Four are already accepted, so a split re-proposes them (about thirty owner acceptances). Owner policy: split here, or an upstream cutoff/grandfather. Surfaced by the D0057 resync.";
        :>> discoveredInField = false;
        :>> relatedTask = "decisionClauseSplit";
        :>> severity = Severity::High;
    }
    #Resolves dependency from decisionClauseSplit to issueCompoundDecisionsUnderD0303;

    part issue001 : Issue {
        :>> id = "5d22ab95-5252-4af4-a56d-be4beead9c13";
        :>> title = "Typing in a settings text field rewrote the whole base per keystroke and froze the host";
        :>> createdAt = "2026-09-15";
        :>> createdBy = "claudeOpus";
        :>> description = "Typing in a settings TEXT FIELD froze Obsidian. The three text inputs in Advanced (file-size cap, bulk-delete threshold, device name) called saveSettings() from onChange, i.e. on EVERY KEYSTROKE. saveSettings is an immediate persist(), and persist() serializes the whole data.json payload - settings plus base.toJSON(), the entire base map, every synced path with up to 1 MiB of text each, plus mountState. So each character re-stringified and rewrote the full base on the host main thread; on a large vault that is seconds of blocking work per keypress and the app stops responding. Panel H4 already coalesced the setBase write path for exactly this reason on 2026-09-11, but the settings inputs kept the immediate call. Reported from the field 2026-09-15 as 'kept open the settings page and tried to type and it basically crashed'.";
        :>> discoveredInField = false;
        :>> severity = Severity::High;
    }
    #Resolves dependency from settingsFieldWriteCoalesce to issue001;

    part issue002 : Issue {
        :>> id = "0691d9a9-89db-4fb7-996c-3e4869b4145e";
        :>> title = "Obsidian hangs: every reconcile pass rewrote the whole multi-megabyte base to data.json";
        :>> createdAt = "2026-09-16";
        :>> createdBy = "claudeOpus";
        :>> description = "Obsidian hangs while using SelfSync - reported as never having happened before with Obsidian. The owner reports the settings pane triggers it, the pane will not close without a force-close, and the main program stays hung after the pane is force-closed. Mechanism found by measurement (client/perf/persist.perf.ts): data.json carries the WHOLE base, because BaseStore.toJSON copies every mergeable file's full text (up to MAX_BASE_TEXT_BYTES = 1 MiB each) into one object which saveData then stringifies - 10.5 MB of payload for a 2,000-note vault at 5 KB per note, re-built from scratch on every write. Stringify itself is only ~30 ms, so the cost is the WRITE VOLUME, and the plugin forced one at the end of EVERY reconcile pass (reconcileAllOnce set settings.lastSyncedAt then called saveSettings, an immediate persist), on every connect, and on every settings-tab close. On Windows with an AV scanner, or a cloud-synced vault, repeated multi-megabyte writes stall the host's main thread; the writes queue and keep running after the pane is closed, which is why closing it does not recover. Aggravated by, but not caused by, the recent status-indicator work raising repaint and event frequency.";
        :>> discoveredInField = false;
        :>> severity = Severity::Critical;
    }
    #Resolves dependency from persistWriteVolume to issue002;

    part issue003 : Issue {
        :>> id = "e6810c6c-3b18-4a09-a110-eaa15bb02599";
        :>> title = "Obsidian hangs: the settings pane issues one recursive plugin-folder walk per synced plugin per render";
        :>> createdAt = "2026-09-16";
        :>> createdBy = "claudeOpus";
        :>> description = "Obsidian hangs when the SelfSync settings pane is open, reliably reproducible by triggering a BRAT plugin-update notification with the pane open, and requiring a force-kill; the host stays hung after the pane is force-closed. ROOT CAUSE, read from the owner's own instrumented log (C:/notes/ASI - Work, 2026-09-16 16:51, build 1.30.30): the settings tab computes per-plugin sync CONVERGENCE by calling pluginSyncClean(id) for every synced plugin on every render, fire-and-forget, with the answer cached only when the promise RESOLVES. pluginSyncClean runs walkConfigTree - a recursive adapter.list/stat walk over .obsidian/plugins/<id> - so one render of a 10-plugin selection issues TEN concurrent recursive filesystem walks. The log shows settings.display completing at 16:51:27.710 and a SECOND full render beginning 62ms later at 16:51:27.772, each fanning out ten 'beg pluginSyncClean' lines, and NOT ONE of the twenty logs an 'end'. The walks never complete because the adapter calls queue behind a main thread they themselves are starving; the earlier capture's '20 folder(s) + 48 file(s) in 109.0s' config scan and its six-minute gap with no poll pass are the same starvation seen from a different angle. A plugin update is the trigger because BRAT writes many files under .obsidian/plugins/**, each firing a config-watcher callback that called settingsRefresh, and every refresh rebuilt the whole tab and issued another full set of walks - an amplifying loop that never converges.";
        :>> discoveredInField = false;
        :>> severity = Severity::Critical;
    }
    #Resolves dependency from settingsWalkStorm to issue003;

    part issue004 : Issue {
        :>> id = "97b60460-51c1-41cd-985f-0b61d5558c4f";
        :>> title = "The settings tab rebuilt itself wholesale on every event, looping ~3x a second and starving the UI";
        :>> createdAt = "2026-09-16";
        :>> createdBy = "claudeOpus";
        :>> description = "The settings tab re-rendered ITSELF on a loop: the owner's 1.30.32 log shows settings.display running every ~300ms, 85ms a time, indefinitely, with the post-render microtask/timer/frame probes all firing - so the thread was healthy and simply spending roughly a third of itself rebuilding the pane. The consequence the owner reported is that the first-contact direction modal (a trivial DOM modal that does NO work before opening) took five seconds or more to appear: it was starved. ROOT DESIGN FAULT, in the owner's words - 'really should be event driven, no? that's crazy' - settingsRefresh was wired to display(), a full containerEl.empty() plus rebuild, and it was called from SEVENTEEN sites, so any event anywhere repainted the entire tab including every section, every plugin row and the About digest read. Anything that fires repeatedly (a config-watcher callback, a resolved plugin display name, a mount event) therefore becomes a render loop.";
        :>> discoveredInField = false;
        :>> severity = Severity::High;
    }
    #Resolves dependency from scopedEventDrivenSettings to issue004;

    part issue005 : Issue {
        :>> id = "4cb38f30-425e-4bb8-81a4-233eff56c932";
        :>> title = "Status light latches on Syncing after a save when the note's folder case differs from the synced spelling (claim and settle keyed by different spellings)";
        :>> createdAt = "2026-09-29";
        :>> createdBy = "claudeOpus";
        :>> description = "OBSERVATION (owner, st002, 2026-09-29; first reported 2026-09-25): after a save, the status indicator stays on a bare Syncing (no count) while the vault is fully synced, with nothing in the debug log for minutes. REPEATABLE RESULT (3 of 3 runs, real Obsidian 1.12.4 on Windows 11, plugin built from HEAD e490b2dc, 2026-09-29): client/e2e-obsidian/statuslatch.pwspec.ts ARM 3. Steps: (1) seed Folder/note.md, let it sync so the base records Folder/note.md; (2) close Obsidian and re-case the folder on disk to folder/; (3) relaunch and wait for idle; (4) modify folder/note.md. Result: the light enters syncing and is still syncing 45 s later. The plugin's unsyncedEdits map holds folder/note.md. A spy on notePathSettled shows the settle for that pass was issued under Folder/note.md. Control arms: ARM 1 (plain save) and ARM 2 (save plus a second write 120 ms later, the update-time-on-edit shape) both return to idle in 3.1 s. MECHANISM, as read in the code at e490b2dc: noteLocalChange keys the claim by the path Obsidian reports (main.ts:2030). reconcilePath replaces the path with canonicalLocalPath(d, path) (reconcile.ts:1044), which returns the base's case-fold sibling when caseInsensitivePaths holds (reconcile.ts:832-838, set for Windows, macOS and iOS at main.ts:2377). It then fires onPathSettled with the canonical path (reconcile.ts:1104). notePathSettled deletes only an exact key (main.ts:2055), so the claim survives. onDisk claims never age out (main.ts:2187), so the light holds until a whole-vault pass runs settleUnsyncedBefore. NOT VERIFIED: whether the owner's vault currently has a case-divergent folder. issueCasePathDivergence records that it had one. So this is a confirmed latch mechanism; it is not yet confirmed as the cause of the owner's latch. Other open suspects, not reproduced: a localWork bracket left un-decremented, and the skipped repaint on a failed per-path pass (main.ts:2067). RECOMMENDATION (for the implementer; not a prescribed fix): make settlement key-consistent with claim recording, for example by folding case on both sides where caseInsensitivePaths holds, or by settling under both the reported and the canonical spelling. Also found on the way (fixed in the same commit): the e2e harness never answered Obsidian 1.12's trust-author modal, because Playwright's isVisible() ignores its timeout option. Every real-Obsidian spec failed with plugin enabled but never loaded.";
        :>> discoveredInField = false;
        :>> severity = Severity::High;
    }
    #Resolves dependency from statusLatchCaseAliasedSettle to issue005;

    part issue006 : Issue {
        :>> id = "a9b8f024-b9b5-412d-95eb-1d44c86db08a";
        :>> title = "The server folds path case but not Unicode normalisation, so an NFC and an NFD spelling of one name both commit as separate files";
        :>> createdAt = "2026-09-29";
        :>> createdBy = "claudeOpus";
        :>> description = "OBSERVATION (found 2026-09-29 while inventorying path identity for st004): the server's same-file rule folds case but not Unicode normalisation. insert_file stores fold = path.to_lowercase() (server/src/index_store.rs:218) and colliding_key compares on that column (index_store.rs:373-376), which vault.rs:596 uses to refuse a colliding commit. An NFC spelling and an NFD spelling of the same name therefore both commit as separate files. The server has no Unicode normalisation dependency (server/Cargo.toml). REPEATABLE RESULT: not yet exercised against the real server. The client now detects this state: when the manifest holds both spellings, a macOS/iOS device, whose filesystem treats them as one file, reports a duplicate-identity violation and holds both paths (client/test/reconcile.test.ts, path identity NFC/NFD suite, against the fake server, which accepts both). So the failure is loud and non-destructive on the client, but the server still admits the state. IMPACT: two devices, one writing NFC (Windows, Linux) and one writing NFD (a name first created on macOS), can put two records of one note on the server. A Mac then holds that note until one spelling is removed. RECOMMENDATION (for the implementer; not a prescribed fix): fold NFC before lower-casing on the server too, with a migration of the existing fold column, which the fold backfill at index_store.rs:130 already does once for case. It is a server change, so it needs a server-image redeploy.";
        :>> discoveredInField = false;
        :>> severity = Severity::Medium;
    }
    #Resolves dependency from serverFoldNormalisation to issue006;
}
