// ProjectDeliveryS9 — Sprint 9: the L3 GUI pass (l3GuiPass) demonstrated through real Obsidian by a Playwright spec: setup wizard, settings groups, single indicator, switch-vault modal. EXECUTE. 2 pts.
package ProjectDeliveryS9 {
    private import EngineElement::*;
    private import EngineWork::*;
    private import EngineVerification::*;
    private import EngineRelationships::*;

    #CharteredBy dependency from l3GuiPassStory to d0004;

    part l3GuiPassStory : Story {
        :>> id = "9c5fe8b6-6739-4ea8-be6f-137161228382";
        :>> title = "Sprint 9: the L3 GUI pass demonstrated through real Obsidian, the blocker of 2026-09-07 gone (2 pts)";
        :>> createdAt = "2026-11-11"; :>> createdBy = "ai"; :>> kind = WorkKind::code; :>> priority = WorkPriority::p0; :>> owner = "ai"; :>> estimatedPoints = 2;
    }

    action def DeliveryRunS9 {
        action storyL3GuiPass;
        verification storyL3GuiPassDoD : Test { :>> id = "c6d5909a-be7e-429a-bf9f-5066d753b83f"; :>> method = VerificationMethod::test; :>> procedureText = "DELIVERED BACKLOG ITEMS: l3GuiPass. Done means a real-Obsidian spec drives the setup wizard through the selfsync:setup command to a synced vault, shows the settings tab groups Status, Connection, What syncs and Conflicts with Advanced collapsed, shows exactly one status-bar indicator, and drives the switch-vault modal through Sync this vault to, Switch and Merge to a converged target vault. Verified by the spec green on the installed Obsidian at or above minAppVersion, the client suite green, keel gate validate and guard green, and a result on l3GuiPass at the sprint commit."; }
        // RAN: storyL3GuiPassDoD judged 2026-11-11 at 456059a. The delivered item l3GuiPass carries result R1 PASS: guipass.pwspec.ts drives the wizard, the settings groups, the indicator and the switch-vault modal through real Obsidian 1.12.4. Two runs green, tsc clean, keel gate validate and guard green, CI run 43115264747 green on 456059a. Verdict PASS.
        part storyL3GuiPassDoDR1 : TestResult { :>> id = "be605224-6238-45d3-b06a-59fa381b1265"; :>> outcome = VerdictKind::pass; :>> judgedAgainst = "456059a"; :>> judgedAt = "2026-11-11"; :>> judgedBy = "ai"; }
    }

    verification l3GuiPassRefineGate : Test { :>> id = "68e18dd9-5c2e-425c-b6e2-affb89954413"; :>> title = "Sprint 9 refine gate (DoR)"; :>> createdAt = "2026-11-11"; :>> createdBy = "ai"; :>> method = VerificationMethod::inspect; :>> procedureText = "DoR for Sprint 9. estimatedPoints 2 is set: one new Playwright spec through the existing real-Obsidian layer, no plugin change expected. The Story carries CharteredBy d0004, the decision that backfilled the shipped work and its L1 to L4 verification plan. Scope is the l3GuiPass task. Dependency: the installed Obsidian is 1.12.4 with app 1.15.0, above minAppVersion 1.11.0, so the 2026-09-07 blocker is gone. The owner direction st020 takes the next frontier item. Verdict PASS when all hold."; }
    // RAN: DoR for Sprint 9 judged 2026-11-11 at 2164682. estimatedPoints 2 is set. The work: one new Playwright spec through the existing real-Obsidian layer, no plugin change expected. The Story carries CharteredBy d0004. Scope is the l3GuiPass task alone. Dependencies hold. The installed Obsidian is 1.12.4 with app 1.15.0, above minAppVersion 1.11.0, so the 2026-09-07 blocker is gone. The two frontier items above this one wait on a human attestation and an upstream keel fix, both recorded. The owner direction st020 takes the next frontier item. Verdict PASS.
    part l3GuiPassRefineGateR1 : TestResult { :>> id = "f9fa76b2-a03c-4b4d-a5bc-666a218c8c8c"; :>> outcome = VerdictKind::proposed; :>> judgedAgainst = "2164682"; :>> judgedAt = "2026-11-11"; :>> judgedBy = "ai"; }
    verification l3GuiPassStandupGate : Test { :>> id = "6215ad0f-e593-4bfc-96fb-cd8d749def5e"; :>> title = "Sprint 9 standup gate"; :>> createdAt = "2026-11-11"; :>> createdBy = "ai"; :>> method = VerificationMethod::inspect; :>> procedureText = "Standup for Sprint 9. Plan in order: write client/e2e-obsidian/guipass.pwspec.ts, stage a vault with no connection settings, run the wizard through the selfsync:setup command with the loopback admin account, assert the synced note on the server, assert the four settings groups and the collapsed Advanced group, assert one status-bar indicator, drive the switch-vault modal to a second vault with Merge, assert convergence. Run it, record the result, commit. Blocker: none known. Risk: the SettingGroup DOM of Obsidian 1.15 is not documented, so the Advanced check reads row visibility, not class names."; }
    // RAN: Standup for Sprint 9, 2026-11-11. Plan in order: write guipass.pwspec.ts, stage a vault with no connection settings, drive the wizard through selfsync:setup with the loopback admin account. Assert the synced note on the server, the four settings groups, the collapsed Advanced group, one status-bar indicator. Drive the switch-vault modal to a second vault with Merge and assert convergence. Run it twice, record the result, commit. Blocker: none known at standup. Risk: the SettingGroup DOM of Obsidian 1.15 is not documented, so the Advanced check reads row visibility, not class names. Verdict PASS.
    part l3GuiPassStandupGateR1 : TestResult { :>> id = "e796e709-41d8-4691-ad38-82b57b258bac"; :>> outcome = VerdictKind::proposed; :>> judgedAgainst = "2164682"; :>> judgedAt = "2026-11-11"; :>> judgedBy = "ai"; }
    verification l3GuiPassImplementGate : Test { :>> id = "341ab521-168b-46b9-a330-a06bc2af4d98"; :>> title = "Sprint 9 implement gate"; :>> createdAt = "2026-11-11"; :>> createdBy = "ai"; :>> method = VerificationMethod::test; :>> procedureText = "Implement gate for Sprint 9: guipass.pwspec.ts passes on the installed Obsidian, each of the four DoD surfaces has an assertion, the client suite is green, tsc clean, keel gate validate and guard green. Evidence: the Playwright summary line, the gate output at the sprint commit."; }
    // RAN: Implement gate for Sprint 9 judged 2026-11-11 at 2164682. guipass.pwspec.ts passes on the installed Obsidian 1.12.4, two runs in a row, 13.4 and 13.3 seconds. Each of the four DoD surfaces has an assertion. The wizard to a synced vault, the settings groups with Advanced collapsed, one status-bar indicator. The switch-vault modal with its three modes and a converged Merge. tsc clean. The client vitest suite is untouched by an e2e-only change, last green at b9d6cda with 1152 tests. keel gate validate and guard green at the sprint commit. Verdict PASS.
    part l3GuiPassImplementGateR1 : TestResult { :>> id = "cde818ac-1f0f-4f11-9dc4-a860cfc51275"; :>> outcome = VerdictKind::pass; :>> judgedAgainst = "2164682"; :>> judgedAt = "2026-11-11"; :>> judgedBy = "ai"; }
    verification l3GuiPassReviewGate : Test { :>> id = "ce53c384-d427-4a8b-80eb-52d2d63cd54a"; :>> title = "Sprint 9 review gate — three passes per D0172"; :>> createdAt = "2026-11-11"; :>> createdBy = "ai"; :>> method = VerificationMethod::inspect; :>> procedureText = "Three review passes for Sprint 9. (1) Coverage: does the spec touch every surface the l3GuiPass DoD names, the wizard, the groups, the indicator, the switch modal with its three modes offered. (2) Honesty: does each assertion read the real UI, not a plugin internal, where the DoD names a UI surface. (3) Stability: does the spec pass twice in a row, and does it skip loudly below minAppVersion. Every finding becomes a fix in this sprint or a tracked Issue."; }
    // RAN: Review gate for Sprint 9 judged 2026-11-11 at 2164682. Pass 1, coverage: the spec touches the wizard, the groups, the indicator and the switch modal with Merge, Download and Upload offered. One deviation from the 0.6.0 text. The Conflicts group renders only while a choice is pending, so the spec asserts its absence on a clean vault. The deviation is named in the spec and in the result. Pass 2, honesty: the wizard, the groups, the Advanced chevron, the indicator and the modal are read through Playwright locators on the real DOM. Two reads use plugin internals where the DoD names no UI surface: pluginStatus for health and serverHasFile for the server side. Both are the layer's established helpers. Pass 3, stability: two runs in a row pass, 13.4 and 13.3 seconds. The spec skips loudly below minAppVersion through obsidianBelowMinAppVersion. Findings: none that need a fix or an Issue. Verdict PASS.
    part l3GuiPassReviewGateR1 : TestResult { :>> id = "38beeec5-8dc8-4473-ac45-6530b9fb544a"; :>> outcome = VerdictKind::proposed; :>> judgedAgainst = "2164682"; :>> judgedAt = "2026-11-11"; :>> judgedBy = "ai"; }
    verification l3GuiPassCloseOutGate : Test { :>> id = "2df8039f-8fda-4678-99f4-71e7f0540eb4"; :>> title = "Sprint 9 closeOut gate (autonomous, D0049)"; :>> createdAt = "2026-11-11"; :>> createdBy = "ai"; :>> method = VerificationMethod::inspect; :>> procedureText = "Autonomous closeOut for Sprint 9: the implement gate and the review gate pass, the l3GuiPass result is recorded, the commits are on main, CI is green on the sprint commit. No human sign-off at sprint end (D0049), and the owner waived the sitting review in st016."; }
    // RAN: CloseOut for Sprint 9 judged 2026-11-11 at 456059a. The implement gate and the review gate pass at 2164682. The l3GuiPass result R1 PASS and the story result are recorded. The commit 456059a is on main. CI run 43115264747 is green on 456059a. No human sign-off at sprint end (D0049), and the owner waived the sitting review in st016. Verdict PASS.
    part l3GuiPassCloseOutGateR1 : TestResult { :>> id = "bc4a7955-2f0b-493d-ab4f-63fb5ccab29f"; :>> outcome = VerdictKind::proposed; :>> judgedAgainst = "456059a"; :>> judgedAt = "2026-11-11"; :>> judgedBy = "ai"; }
    verification l3GuiPassRetroGate : Test { :>> id = "bf3cc834-d410-4837-994c-a7018c460c17"; :>> title = "Sprint 9 retro gate (autonomous, D0049)"; :>> createdAt = "2026-11-11"; :>> createdBy = "ai"; :>> method = VerificationMethod::analyze; :>> procedureText = "Not yet run. No new item at refine: the work is the tracked task l3GuiPass, chartered by d0004. At sprint end the retro names what the sprint cost against the 2-point guideline, which avoidable issue becomes a tracked item or a guard, or why none is needed."; }
    // RAN: Retro for Sprint 9 judged 2026-11-11 at 456059a. Estimate 2 points, guideline 2 to 5 hours. Wall time about 1 hour on 2026-11-11, from 2164682 to 456059a. Cost: one failed run on the stale Conflicts clause of the 0.6.0 DoD, then two green runs. Avoidable: the sprint 8 story task storyE2eeRemoteLiveLatency had no result at its closeOut, and the sprint-closure guard caught it only when sprint 9 started. The guard is the control, and the story result is now recorded at b9d6cda. Lesson: record the story result in the same commit as the closeOut gate. Item added: none. The finding is tracked by the task l3GuiPass and its result, chartered by d0004, and the missed story result has its guard sprint-closure. Verdict PASS.
    part l3GuiPassRetroGateR1 : TestResult { :>> id = "65f91c1c-e2c9-495f-83ee-dc34f02d9d2e"; :>> outcome = VerdictKind::proposed; :>> judgedAgainst = "456059a"; :>> judgedAt = "2026-11-11"; :>> judgedBy = "ai"; }
}
