// ProjectDeliveryS10 — Sprint 10: the server's same-file rule folds NFC before case (issue006, D0116), with a schema 5 migration and tests. EXECUTE. 3 pts.
package ProjectDeliveryS10 {
    private import EngineElement::*;
    private import EngineWork::*;
    private import EngineVerification::*;
    private import EngineRelationships::*;

    #CharteredBy dependency from serverFoldNormalisationStory to d0116;

    part serverFoldNormalisationStory : Story {
        :>> id = "81e0b7ee-2792-4959-8651-695b5ea470f0";
        :>> title = "Sprint 10: the server refuses an NFD twin of an NFC path, existing rows migrated, pinned by tests (3 pts)";
        :>> createdAt = "2026-11-11"; :>> createdBy = "ai"; :>> kind = WorkKind::code; :>> priority = WorkPriority::p0; :>> owner = "ai"; :>> estimatedPoints = 3;
    }

    action def DeliveryRunS10 {
        action storyServerFoldNormalisation;
        verification storyServerFoldNormalisationDoD : Test { :>> id = "c972e4e4-fab1-4da0-a078-9efccc5463fc"; :>> method = VerificationMethod::test; :>> procedureText = "DELIVERED BACKLOG ITEMS: serverFoldNormalisation. Done means one server function computes the fold key, NFC then to_lowercase, used by insert_file, colliding_key, the backfill and the reindex scan. Schema 5 recomputes every fold on open and keeps twin rows with a warning. A commit of an NFD twin of a live NFC path is refused with the Unicode form named. Verified by server tests for the NFD collision, the v5 refold and the reindex scan, cargo test and clippy green, the real-Obsidian smoke and e2ee specs green on the new binary, keel gate validate and guard green, and a result on serverFoldNormalisation at the sprint commit."; }
        // RAN: storyServerFoldNormalisationDoD judged 2026-11-11 at f974f91. The delivered item serverFoldNormalisation carries result R2 PASS. fold_key is the one server fold. Schema 5 refolds and keeps twins. An NFD twin commit is refused, and the tests pin it. cargo test and clippy green. The Obsidian smoke, e2ee and convergence specs green. keel gate validate and guard green, CI run 43120215921 green on f974f91. Verdict PASS.
        part storyServerFoldNormalisationDoDR1 : TestResult { :>> id = "cd0745f3-8f6a-48fe-8565-48a8bfc0efe9"; :>> outcome = VerdictKind::pass; :>> judgedAgainst = "f974f91"; :>> judgedAt = "2026-11-11"; :>> judgedBy = "ai"; }
    }

    verification serverFoldNormalisationRefineGate : Test { :>> id = "76358aca-e545-4400-886f-68ef3eb0fc53"; :>> title = "Sprint 10 refine gate (DoR)"; :>> createdAt = "2026-11-11"; :>> createdBy = "ai"; :>> method = VerificationMethod::inspect; :>> procedureText = "DoR for Sprint 10. estimatedPoints 3 is set: a Rust fold function, four call sites, a schema 5 migration, server tests, a doc sync of the e2ee spec and deployment.md. The Story carries CharteredBy d0116, the decision that states the fold rule and the no-drop migration. Scope is the serverFoldNormalisation task. Dependencies: the unicode-normalization crate, cargo on this machine. The owner direction st021 says proceed. Verdict PASS when all hold."; }
    // RAN: DoR for Sprint 10 judged 2026-11-11 at abb070b. estimatedPoints 3 is set. The work: a Rust fold function, four call sites, a schema 5 migration, server tests, a doc sync. The Story carries CharteredBy d0116, the decision that states the fold rule and the no-drop migration. Scope is the serverFoldNormalisation task alone. Dependencies hold. The unicode-normalization crate resolves, cargo 1.99 runs on this machine. The two frontier items above wait on phone hardware and on a schema sign-off. The owner direction st021 says proceed. Verdict PASS.
    part serverFoldNormalisationRefineGateR1 : TestResult { :>> id = "7e63b4f3-355c-4c5b-89a7-962294868d25"; :>> outcome = VerdictKind::proposed; :>> judgedAgainst = "abb070b"; :>> judgedAt = "2026-11-11"; :>> judgedBy = "ai"; }
    verification serverFoldNormalisationStandupGate : Test { :>> id = "3dda2879-fa8f-45d4-bce4-bc8ef2c7ee60"; :>> title = "Sprint 10 standup gate"; :>> createdAt = "2026-11-11"; :>> createdBy = "ai"; :>> method = VerificationMethod::inspect; :>> procedureText = "Standup for Sprint 10. Plan in order: add the crate, write fold_key in index_store.rs, route insert_file, colliding_key, the backfill and conflicting_or_unsafe_rels through it, add the v5 refold step that keeps twins and logs them, bump CURRENT_SCHEMA to 5, name the Unicode form in the commit refusal. Tests: NFD collision, v5 refold with twins kept, reindex scan, the schema pins updated. Doc sync: the e2ee spec passages on the server fold and deployment.md. Run cargo test, clippy, the Obsidian smoke and e2ee specs. Blocker: none known. Risk: the e2ee spec chose a case-only cid because NFC was wider than the server identity, so the spec must state why a narrower cid stays safe."; }
    // RAN: Standup for Sprint 10, 2026-11-11. Plan in order: add the crate, write fold_key, route the four fold sites through it, add the v5 refold step that keeps twins, bump CURRENT_SCHEMA. Name the Unicode form in the commit refusal. Tests: NFD collision, v5 refold with twins kept, reindex scan, schema pins. Doc sync: the e2ee spec and deployment.md. Run cargo test, clippy, the Obsidian smoke and e2ee specs. Blocker: none known at standup. Risk: the e2ee spec chose a case-only cid because NFC was wider than the server identity. The spec must state why a narrower cid stays safe. Verdict PASS.
    part serverFoldNormalisationStandupGateR1 : TestResult { :>> id = "68e7d363-2de4-42a1-aa87-f92ea2682698"; :>> outcome = VerdictKind::proposed; :>> judgedAgainst = "abb070b"; :>> judgedAt = "2026-11-11"; :>> judgedBy = "ai"; }
    verification serverFoldNormalisationImplementGate : Test { :>> id = "650d9dee-d43e-4eb2-b270-f349c3ed99ee"; :>> title = "Sprint 10 implement gate"; :>> createdAt = "2026-11-11"; :>> createdBy = "ai"; :>> method = VerificationMethod::test; :>> procedureText = "Implement gate for Sprint 10: fold_key is the one fold, every path fold site calls it, schema 5 refolds and keeps twins, the NFD commit is refused, the new tests pass, cargo test and clippy green, the Obsidian smoke and e2ee specs green on the new server binary, docs synced, keel gate validate and guard green. Evidence: the cargo test summary, the Playwright summary, the gate output at the sprint commit."; }
    // RAN: Implement gate for Sprint 10 judged 2026-11-11 at abb070b. fold_key is the one fold, every path fold site calls it, the grep for to_lowercase finds only fold_key and two test fixtures. Schema 5 refolds on open and keeps twins. The NFD commit is refused. The new tests pass. cargo test --release green, 177 in the lib. cargo clippy -D warnings clean. The Obsidian smoke, e2ee and convergence specs pass on the rebuilt server binary, 3 passed in 1.3 minutes. Docs synced. keel gate validate and guard green at the sprint commit. Verdict PASS.
    part serverFoldNormalisationImplementGateR1 : TestResult { :>> id = "78f2dc94-ccdc-47f3-90c1-486e209f7655"; :>> outcome = VerdictKind::pass; :>> judgedAgainst = "abb070b"; :>> judgedAt = "2026-11-11"; :>> judgedBy = "ai"; }
    verification serverFoldNormalisationReviewGate : Test { :>> id = "cadb871b-8e81-41f6-8192-3493e5ec0d77"; :>> title = "Sprint 10 review gate — three passes per D0172"; :>> createdAt = "2026-11-11"; :>> createdBy = "ai"; :>> method = VerificationMethod::inspect; :>> procedureText = "Three review passes for Sprint 10. (1) Lockstep: does every site that folds a path call fold_key, with a grep for to_lowercase on paths as the check. (2) Migration honesty: does the v5 step keep every row, log each twin pair, and run once per index. (3) Consequences: does the e2ee spec state why the case-only cid stays safe under the wider server fold, and does the client treat the new refusal text like the old. Every finding becomes a fix in this sprint or a tracked Issue."; }
    // RAN: Review gate for Sprint 10 judged 2026-11-11 at abb070b. Pass 1, lockstep: grep to_lowercase server/src finds fold_key, one assertion message and two test fixtures that build the OLD fold on purpose. Every live fold site calls fold_key. Pass 2, migration honesty: the v5 step reads every path, writes fold_key for each, logs each twin pair, drops nothing. It runs once, gated on the stamped version below 5. The test keeps two twins and shows one distinct fold. Pass 3, consequences: the e2ee spec now states that the server fold is wider than the case-only cid, and why a narrower cid stays safe. The client does not branch on the refusal text, reconcile.ts and the transport tests pass it through, so the new wording changes no client path. One finding: the e2e layer runs target/debug, so a release-only build left the first Obsidian run on a stale server. Rebuilt and rerun, 3 passed. No tracked Issue results. Verdict PASS.
    part serverFoldNormalisationReviewGateR1 : TestResult { :>> id = "56055af1-584c-4898-9d73-9a4b85b926fb"; :>> outcome = VerdictKind::proposed; :>> judgedAgainst = "abb070b"; :>> judgedAt = "2026-11-11"; :>> judgedBy = "ai"; }
    verification serverFoldNormalisationCloseOutGate : Test { :>> id = "e544ef4e-3ec9-49a3-b448-74b6d180fb11"; :>> title = "Sprint 10 closeOut gate (autonomous, D0049)"; :>> createdAt = "2026-11-11"; :>> createdBy = "ai"; :>> method = VerificationMethod::inspect; :>> procedureText = "Autonomous closeOut for Sprint 10: the implement gate and the review gate pass, the serverFoldNormalisation result and the story result are recorded, the commits are on main, CI is green on the sprint commit. No human sign-off at sprint end (D0049), and the owner waived the sitting review in st016."; }
    // RAN: CloseOut for Sprint 10 judged 2026-11-11 at f974f91. The implement gate and the review gate pass at abb070b. The serverFoldNormalisation result R2 PASS and the story result are recorded. issue006 no longer shows in keel show open-issues. The commit f974f91 is on main. CI run 43120215921 is green on f974f91. No human sign-off at sprint end (D0049), and the owner waived the sitting review in st016. Verdict PASS.
    part serverFoldNormalisationCloseOutGateR1 : TestResult { :>> id = "cdb2013f-75ff-4550-8cc1-710feb8e9dff"; :>> outcome = VerdictKind::proposed; :>> judgedAgainst = "f974f91"; :>> judgedAt = "2026-11-11"; :>> judgedBy = "ai"; }
    verification serverFoldNormalisationRetroGate : Test { :>> id = "7849dd9c-1e88-4fe7-8089-d17fe26d9255"; :>> title = "Sprint 10 retro gate (autonomous, D0049)"; :>> createdAt = "2026-11-11"; :>> createdBy = "ai"; :>> method = VerificationMethod::analyze; :>> procedureText = "Not yet run. No new item at refine: the work is the tracked task serverFoldNormalisation, resolver of issue006, chartered by d0116. At sprint end the retro names what the sprint cost against the 3-point guideline, which avoidable issue becomes a tracked item or a guard, or why none is needed."; }
    // RAN: Retro for Sprint 10 judged 2026-11-11 at f974f91. Estimate 3 points, guideline 5 to 10 hours. Wall time about 1 hour on 2026-11-11, from abb070b to f974f91. Cost: one stale e2ee test pin at schema 4, and one Obsidian run on a stale debug server binary after a release-only build. Avoidable: the e2e layer spawns target/debug while cargo test --release builds target/release, so a server change needs two builds before the Obsidian specs see it. The review caught it and the specs were rerun. The e2ee spec had chosen a case-only cid on the premise that the server folds case only, so the premise needed a doc sync. Item added: none. The work is the tracked task serverFoldNormalisation, resolver of issue006, chartered by d0116. The two-build step is noted in the e2e helper comment and costs one minute, so no tracked item for it. Verdict PASS.
    part serverFoldNormalisationRetroGateR1 : TestResult { :>> id = "7af67444-b0ba-4f9e-9aa0-2c1f3c1b86df"; :>> outcome = VerdictKind::proposed; :>> judgedAgainst = "f974f91"; :>> judgedAt = "2026-11-11"; :>> judgedBy = "ai"; }
}
