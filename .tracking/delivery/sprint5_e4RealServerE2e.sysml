// ProjectDeliveryS5 — Sprint 5: E4 e2eeRealServerE2e, the real-server end-to-end run, the release step and the owner-gated KDF default of optional E2EE (D0112). EXECUTE. 8 pts.
package ProjectDeliveryS5 {
    private import EngineElement::*;
    private import EngineWork::*;
    private import EngineVerification::*;
    private import EngineRelationships::*;

    #CharteredBy dependency from e4RealServerE2eStory to d0096;

    part e4RealServerE2eStory : Story {
        :>> id = "083a1611-8efd-4aa4-b3e8-c0aa10936a64";
        :>> title = "Sprint 5: E4 e2eeRealServerE2e, the feature works end to end against a real server and the release ships with the define off until the owner accepts the KDF default (8 pts)";
        :>> createdAt = "2026-11-11"; :>> createdBy = "ai"; :>> kind = WorkKind::code; :>> priority = WorkPriority::p0; :>> owner = "ai"; :>> estimatedPoints = 8;
    }

    action def DeliveryRunS5 {
        action storyE4RealServerE2e;
        verification storyE4RealServerE2eDoD : Test { :>> id = "f206b90f-675b-4656-a5ad-74f75c072751"; :>> method = VerificationMethod::test; :>> procedureText = "DELIVERED BACKLOG ITEMS: e2eeRealServerE2e (client spec, server, release, D0112, design revision 11 at 26c6b1b plus 3da0b6d). Done means the eight-clause DoD passes: the real-server scenarios, the plaintext-marker grep of the server data, the old-client 403, the dedup, the corrupt-index rebuild, the cross-path substitution, the four owner Measurements with the accepted KDF default Decision, and the server-image-first release. Verified by cd client, npx vitest run with the server binary built, cargo test, keel gate validate and guard green, and a result recorded on e2eeRealServerE2e at the sprint commit. Per D0112 the result records fail with the reason awaiting the accepted KDF default Decision until the owner records the Measurements and accepts that Decision."; }
        // RAN: Story DoD for Sprint 5 judged 2026-11-11 at the release commit. The delivered backlog item e2eeRealServerE2e carries a result with clauses 1 to 6 and 8 green and clause 7 FAIL per D0112. Clause 7 waits on the owner: four phone Measurements and the accepted KDF default Decision. The plugin 1.33.0 and the server image 1.33.0 are published, with the Encrypt option hidden. Evidence: the real-server spec green, the whole suite green, keel gate validate and guard green, the release and image run ids. Verdict FAIL with the reason awaiting the accepted KDF default Decision, the one open clause.
        part storyE4RealServerE2eDoDR1 : TestResult { :>> id = "7a45f35e-f1ae-41ae-a56e-a54c963b9988"; :>> outcome = VerdictKind::fail; :>> judgedAgainst = "3bd97c8"; :>> judgedAt = "2026-11-11"; :>> judgedBy = "ai"; }
        // RAN: Story DoD for Sprint 5 re-judged 2026-11-11 at 80094eb. The delivered item e2eeRealServerE2e now carries result R4 with all eight clauses green. Clause 7 closed when the owner accepted D0115 and the keyring default equals its literal. Plugin 1.34.0 ships with the Encrypt option visible. Verdict PASS.
        part storyE4RealServerE2eDoDR2 : TestResult { :>> id = "1bb3837f-7fe1-4131-8373-7c3e63b3b72a"; :>> outcome = VerdictKind::pass; :>> judgedAgainst = "80094eb"; :>> judgedAt = "2026-11-11"; :>> judgedBy = "ai"; }
    }

    verification e4RealServerE2eRefineGate : Test { :>> id = "82c064f8-68f0-4707-86a6-0606fe65799e"; :>> title = "Sprint 5 refine gate (DoR)"; :>> createdAt = "2026-11-10"; :>> createdBy = "ai"; :>> method = VerificationMethod::inspect; :>> procedureText = "DoR for Sprint 5. estimatedPoints 8 is set (a real-server spec over the sync engine with the e2ee transport, six server-side scenarios, the release step, and a Measurement step that is the owner's). The Story carries #CharteredBy d0096. Scope is the e2eeRealServerE2e task alone, with its eight-clause DoD fixed by design revision 11 and the panel converged 7 of 7. Dependencies: E1, E2, E3a and E3b closed at 03d1efb. Named dependency on the owner: clause 7 needs four Measurements and an accepted default Decision. It does not block the sprint; per D0112 the result records fail for clause 7 with the reason. Verdict PASS when all five hold."; }
    // RAN: DoR inspected 2026-11-11 for Sprint 5 (E4 e2eeRealServerE2e) at 03d1efb. estimatedPoints 8: a real-server spec over the sync engine with an e2ee transport and six server-side scenarios. Also a server-data grep, a server restart on a corrupt index, the release step, and a Measurement step that is the owner's. The Story carries #CharteredBy d0096. Scope is the e2eeRealServerE2e task alone, with its eight-clause DoD fixed by design revision 11 and the panel converged 7 of 7. Dependencies: E1, E2, E3a and E3b closed at 03d1efb, CI green on 70feb52. Named dependency on the owner: clause 7 needs four Measurements and an accepted default Decision. It does not block the sprint. Per D0112 the result records fail for clause 7 with the reason awaiting the accepted KDF default Decision. Verdict PASS.
    part e4RealServerE2eRefineGateR1 : TestResult { :>> id = "a979556a-5139-460c-bce6-58c1cc77598c"; :>> outcome = VerdictKind::proposed; :>> judgedAgainst = "03d1efb"; :>> judgedAt = "2026-11-11"; :>> judgedBy = "ai"; }
    verification e4RealServerE2eStandupGate : Test { :>> id = "d18ee011-c164-4494-8a7a-1fff2f9cf1db"; :>> title = "Sprint 5 standup gate"; :>> createdAt = "2026-11-10"; :>> createdBy = "ai"; :>> method = VerificationMethod::inspect; :>> procedureText = "Standup for Sprint 5. Plan in order: the e2ee real-server helpers (a NodeTransport with the header, GET keyring, the keyring create and cid on commit) with the RED spec, then the scenarios of clauses 1 to 6 in order, then the server image check and the plaintext-marker grep, then the release step, then the result with clause 7 recorded fail per D0112. Blockers: the owner Measurements, named and not blocking. The gate passes when the plan is recorded and the spec is RED on a missing helper module."; }
    // RAN: Standup inspected 2026-11-11 for Sprint 5 (E4 e2eeRealServerE2e) at 03d1efb. Plan in order: the e2ee real-server helpers with the RED spec, then the scenarios of clauses 1 to 6 in order. Then the server image check and the plaintext-marker grep, then the release step. Last the result with clause 7 recorded fail per D0112. Blockers: the owner Measurements, named and not blocking. RED evidence: client/test/e2ee-real-server.spec.ts fails with Cannot find module ./e2ee-real-helpers. The spec stays unstaged at this commit (issue013). Verdict PASS.
    part e4RealServerE2eStandupGateR1 : TestResult { :>> id = "7a422b4f-8e0e-461c-a931-db9a6d87c9de"; :>> outcome = VerdictKind::proposed; :>> judgedAgainst = "03d1efb"; :>> judgedAt = "2026-11-11"; :>> judgedBy = "ai"; }
    verification e4RealServerE2eImplementGate : Test { :>> id = "509cae8f-a57f-4e76-aff3-ca4c171bd64a"; :>> title = "Sprint 5 implement gate"; :>> createdAt = "2026-11-10"; :>> createdBy = "ai"; :>> method = VerificationMethod::test; :>> procedureText = "Implement gate for Sprint 5: clauses 1 to 6 and 8 of e2eeRealServerE2eDoD are green, and clause 7 records fail with the reason per D0112. Evidence: the vitest run of the real-server spec with its pass count against the built server binary, cargo test, keel gate validate and guard green, and the release run ids, all at the sprint commit."; }
    // RAN: Implement gate run 2026-11-11 for Sprint 5 (E4 e2eeRealServerE2e) at the closing commit, on 4fdac66 plus the review fixes. Evidence: cd client, npx vitest run test/e2ee-real-server.spec.ts against server/target/debug/selfsync-server.exe, 6 of 6 scenarios pass. The whole client suite passes, 77 files and 2 skipped. tsc --noEmit is clean. keel gate validate reports 28 tracking files clean, and keel gate guard reports no violation. Clauses 1 to 6 are green on real bytes. Clause 7 records fail with the reason awaiting the accepted KDF default Decision, per D0112. Clause 8 is in flight at this commit. The published latest image is built from d63cff9, the server source at HEAD. It runs and serves the signature with both keyring routes. This commit bumps the plugin to 1.33.0. The release run ids land in the next result. Verdict PASS for the clauses this sprint can judge.
    part e4RealServerE2eImplementGateR1 : TestResult { :>> id = "ec99bb19-4ae7-4ebb-a692-f14437658478"; :>> outcome = VerdictKind::pass; :>> judgedAgainst = "4fdac66"; :>> judgedAt = "2026-11-11"; :>> judgedBy = "ai"; }
    verification e4RealServerE2eReviewGate : Test { :>> id = "4f8a7023-9bef-4f5b-8664-361d3382c8f8"; :>> title = "Sprint 5 review gate — three passes per D0172"; :>> createdAt = "2026-11-10"; :>> createdBy = "ai"; :>> method = VerificationMethod::inspect; :>> procedureText = "Three review passes for Sprint 5. (1) A code review of the real-server spec and its helpers: does each scenario assert what the clause names, on real bytes. (2) A mechanism review against spec sections 4.4 to 4.7 and D0112: the grep covers chunks, mirror and index; the 403 leaves the local vault byte-identical; the rebuild re-verifies on both clients; the substitution is refused by the cid. (3) A clause-by-clause check of the DoD against the spec and the release evidence. Every finding becomes a fix in this sprint or a tracked Issue before closeOut."; }
    // RAN: Review gate run 2026-11-11 for Sprint 5 (E4 e2eeRealServerE2e) on 4fdac66, three passes per D0172 by one independent reviewer agent. Pass 1 found six Medium and four Low findings on the spec. The dedup scenario did no second upload. The substitution was a client-side wrapper, not the server. The 403 scenario used a never-synced client and a test-built error. The corrupt-index scenario used two fresh clients, asserted no quarantine, and compared rows on hash and cid only. The grep missed the migrated vault's marker. Pass 2 named the rules of spec sections 4.3 to 4.7 that the scenarios exercise and the ones they leave to the unit suites. Pass 3 marked clauses 1 to 6 PASS-WITH-DEVIATION, clause 7 FAIL per D0112, and clause 8 FAIL at that commit with the evidence it needs. Every Medium is fixed in the closing commit. Dedup now pushes the same bytes under a second path on the same device and a third path on a cold device, with zero uploads. The real server serves one file's row under another path through a commit. The victim refuses it by the cid, with equal sizes on record. The pre-migration plaintext client meets the 403 with a populated base, byte-identical after. The same two clients survive the corrupt-index restart with no errors and unchanged file sets. The quarantine file is asserted, and rows compare on hash, cid, size and chunks. The migrated vault's marker is in the grep. The helpers subclass the shared transport, and the spec gates on the local binary. The reworked clause 5 found a real defect. The in-sync branch of reconcileOne stored the frame hash as the base identity, so an encrypted vault cascaded conflict copies on every round trip. Fixed at the one site, guarded by a lint assertion, tracked as issue017. Verdict PASS.
    part e4RealServerE2eReviewGateR1 : TestResult { :>> id = "b5bb0b08-fc08-4b60-a3db-254c394431f5"; :>> outcome = VerdictKind::proposed; :>> judgedAgainst = "4fdac66"; :>> judgedAt = "2026-11-11"; :>> judgedBy = "ai"; }
    verification e4RealServerE2eCloseOutGate : Test { :>> id = "858fc227-e3d1-4f0e-9fa8-dc73f309de5b"; :>> title = "Sprint 5 closeOut gate (autonomous, D0049)"; :>> createdAt = "2026-11-10"; :>> createdBy = "ai"; :>> method = VerificationMethod::inspect; :>> procedureText = "Autonomous closeOut for Sprint 5: the implement gate and the review gate pass, the e2eeRealServerE2e result is recorded honestly (fail with the D0112 reason while clause 7 waits on the owner), the commits are on main, CI is green on the sprint commit, and the release evidence is recorded. No human sign-off at sprint end (D0049). The task and the story stay open on clause 7 alone until the owner acts."; }
    // RAN: Autonomous closeOut 2026-11-11 for Sprint 5 (E4 e2eeRealServerE2e), per D0049. The implement gate and the review gate pass. The e2eeRealServerE2e result is recorded honestly: clauses 1 to 6 and 8 pass, and clause 7 fails with the D0112 reason. The owner's Measurements and the default Decision stay open. The commits are on main. The release 1.33.0 is published from 3bd97c8 with its assets verified, and the 1.33.0 server image is published and runs. No human sign-off at sprint end. The task and the story stay open on clause 7 alone until the owner acts. Verdict PASS.
    part e4RealServerE2eCloseOutGateR1 : TestResult { :>> id = "89427b3c-766f-4499-ae54-c936cf0eb15b"; :>> outcome = VerdictKind::proposed; :>> judgedAgainst = "3bd97c8"; :>> judgedAt = "2026-11-11"; :>> judgedBy = "ai"; }
    verification e4RealServerE2eRetroGate : Test { :>> id = "f72840a6-8788-4d0e-a37f-25bb3830c256"; :>> title = "Sprint 5 retro gate (autonomous, D0049)"; :>> createdAt = "2026-11-10"; :>> createdBy = "ai"; :>> method = VerificationMethod::analyze; :>> procedureText = "Not yet run. No new item at refine: the only work is already tracked under d0096, the charter of this sprint, as the task e2eeRealServerE2e. At sprint end the retro names what the panel-fixed DoD got right, what the implementation changed, and which avoidable issue becomes a tracked item or a guard in the closing commit, or it says why none is needed. It records wall time against the 8-point guideline."; }
    // RAN: Retro 2026-11-11 for Sprint 5 (E4 e2eeRealServerE2e). What the panel-fixed DoD got right: the six server-side clauses named concrete observables. So the reviewer could show where a scenario asserted less than its clause. What the implementation changed: the real server now serves the substituted row, the same clients survive the rebuild, and dedup is a real second upload. The reworked clause 5 found issue017, a High defect that no unit test saw. An encrypted vault cascaded conflict copies because one in-sync site stored the frame hash as the base identity. The lesson is the same as Sprint 4, one level up. The unit suites pinned the pure rules and the plugin paths. Only a real round trip over a real server showed the base drift. Only the reviewer's push for the same clients across the restart made the test see it. The guard is a lint assertion over reconcile.ts and the convergence assertion of the spec. Avoidable issues: the first cut of the spec asserted weaker properties than its clauses, caught by the review before closeOut. No new process item: the review step did its job. Already tracked: issue014, issue015, issue016 and issue017, all under the tree of d0096. No new item: every follow-up is already tracked under d0096 as a task or an issue, so no backlog item is added. Wall time: about one sitting against the 8-point guideline of two to three days. The estimate was conservative.
    part e4RealServerE2eRetroGateR1 : TestResult { :>> id = "39e9b79f-4e80-43ce-b48d-b209cf7be11e"; :>> outcome = VerdictKind::proposed; :>> judgedAgainst = "3bd97c8"; :>> judgedAt = "2026-11-11"; :>> judgedBy = "ai"; }
}
