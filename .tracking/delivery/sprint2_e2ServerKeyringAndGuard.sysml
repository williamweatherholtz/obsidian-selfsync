// ProjectDeliveryS2 — Sprint 2: E2 e2eeServerKeyringAndGuard, the server side of optional E2EE (D0102, D0103). EXECUTE. 8 pts.
package ProjectDeliveryS2 {
    private import EngineElement::*;
    private import EngineWork::*;
    private import EngineVerification::*;
    private import EngineRelationships::*;

    #CharteredBy dependency from e2ServerKeyringAndGuardStory to d0096;

    part e2ServerKeyringAndGuardStory : Story {
        :>> id = "57a14db5-3323-490b-b32e-b1f586b9931a";
        :>> title = "Sprint 2: E2 e2eeServerKeyringAndGuard, the server stores, validates, mirrors and reindexes an encrypted vault without the key (8 pts)";
        :>> createdAt = "2026-11-10"; :>> createdBy = "ai"; :>> kind = WorkKind::code; :>> priority = WorkPriority::p0; :>> owner = "ai"; :>> estimatedPoints = 8;
    }

    action def DeliveryRunS2 {
        action storyE2ServerKeyringAndGuard;
        verification storyE2ServerKeyringAndGuardDoD : Test { :>> id = "f2fd5901-7378-4285-95de-ed7f91690137"; :>> method = VerificationMethod::test; :>> procedureText = "DELIVERED BACKLOG ITEMS: e2eeServerKeyringAndGuard (server, D0102 and D0103, design revision 11 at 26c6b1b plus 3da0b6d). Done means the eight-clause DoD passes: the keyring sidecar with atomic create and GET keyring, frame.rs against the E1 vector, PUT chunk and commit verification for a keyring vault, schema 4 with cid and the encrypted flag with both refusals, the mirror trailer and the frame-splitting rebuild with the three-condition abort, the E2eeHeader downgrade guard inside scoped, missing on a stored frame hash, and the regenerated wire signature. Verified by cd server, cargo test, cargo clippy -D warnings, keel gate validate and guard green, and a pass result recorded on e2eeServerKeyringAndGuard at the sprint commit."; }
        // RAN: Sprint 2 story judged 2026-11-10 at the closing commit. The delivered backlog item e2eeServerKeyringAndGuard carries a PASS result at the closing commit, with one named deviation in its evidence. The implement gate and the review gate pass. The closeOut gate records the sprint closed. Evidence: cargo test 267 green, clippy clean, coverage over the floor, client suite green, keel gate green. Verdict PASS.
        part storyE2ServerKeyringAndGuardDoDR1 : TestResult { :>> id = "2ca397ee-edec-4c39-8020-8e66da0492be"; :>> outcome = VerdictKind::pass; :>> judgedAgainst = "5a75c36"; :>> judgedAt = "2026-11-10"; :>> judgedBy = "ai"; }
    }

    verification e2ServerKeyringAndGuardRefineGate : Test { :>> id = "d0d00908-59f0-4ac3-af36-58667bf7c2ff"; :>> title = "Sprint 2 refine gate (DoR)"; :>> createdAt = "2026-11-10"; :>> createdBy = "ai"; :>> method = VerificationMethod::inspect; :>> procedureText = "DoR for Sprint 2. estimatedPoints 8 is set (a cross-cutting server feature: state, vault, index store, api, wire signature, with tests). The Story carries #CharteredBy d0096. Scope is the e2eeServerKeyringAndGuard task alone, with its eight-clause DoD fixed by design revision 11 and the panel converged 7 of 7. Dependencies: E1 done at 5f7ec9f, so the test vector exists. Rust 1.99, serde_json and sha2 are present. No blocking dependency. Verdict PASS when all five hold."; }
    // RAN: DoR inspected 2026-11-10 for Sprint 2 (E2 e2eeServerKeyringAndGuard). estimatedPoints 8: a cross-cutting server feature with unit and integration tests, two to three days by the guideline. It touches state.rs, vault.rs, index_store.rs, api.rs, vaults.rs, error.rs and wire_signature.rs. #CharteredBy d0096 is on e2ServerKeyringAndGuardStory. Scope: the e2eeServerKeyringAndGuard task alone, with its eight-clause DoD from design revision 11 at 26c6b1b plus 3da0b6d, panel converged 7 of 7. Dependencies: E1 closed at 5f7ec9f, so client/test/e2ee/vector.json exists for the frame test. Rust 1.99 with serde_json and sha2 in server/Cargo.toml. No blocking dependency. Verdict PASS.
    part e2ServerKeyringAndGuardRefineGateR1 : TestResult { :>> id = "32e057cc-8a72-4ada-a0f2-1907f55f6f39"; :>> outcome = VerdictKind::proposed; :>> judgedAgainst = "5f7ec9f"; :>> judgedAt = "2026-11-10"; :>> judgedBy = "ai"; }
    verification e2ServerKeyringAndGuardStandupGate : Test { :>> id = "a3c55f52-2396-4b3a-a04b-41566e78c035"; :>> title = "Sprint 2 standup gate"; :>> createdAt = "2026-11-10"; :>> createdBy = "ai"; :>> method = VerificationMethod::inspect; :>> procedureText = "Standup for Sprint 2. Plan in order: frame.rs with the vector test, index store schema 4 with cid and the encrypted meta key, the Vault flag with both refusals and the abort reason, create_vault under the open lock with the sidecar, GET keyring, put_chunk and commit verification, write_mirror_for and the frame-splitting rebuild with the pre-pass abort, the E2eeHeader extractor inside scoped, the wire signature, then the route-list test. Blockers: none named. The gate passes when the plan is recorded and the first failing test exists."; }
    // RAN: Standup inspected 2026-11-10 for Sprint 2 (E2 e2eeServerKeyringAndGuard) at the refine commit. Plan in order: frame.rs with the vector test, then index store schema 4 with cid and the encrypted meta key. Then the Vault flag with both refusals and the abort reason, and create_vault under the open lock with the sidecar. Then GET keyring, put_chunk and commit verification, write_mirror_for and the frame-splitting rebuild with the pre-pass abort. Last the E2eeHeader extractor inside scoped, the wire signature, and the route-list test. Blockers: none. RED evidence: server/tests/e2ee_frame.rs is written against the E1 vector. cargo test --test e2ee_frame fails to compile with error E0432, unresolved import selfsync_server::frame. The first failing test exists. Verdict PASS.
    part e2ServerKeyringAndGuardStandupGateR1 : TestResult { :>> id = "5acb10a9-192b-4f4d-a921-dd9140da18bc"; :>> outcome = VerdictKind::proposed; :>> judgedAgainst = "5f7ec9f"; :>> judgedAt = "2026-11-10"; :>> judgedBy = "ai"; }
    verification e2ServerKeyringAndGuardImplementGate : Test { :>> id = "b1d71483-c865-4e82-a088-0e4bd2958510"; :>> title = "Sprint 2 implement gate"; :>> createdAt = "2026-11-10"; :>> createdBy = "ai"; :>> method = VerificationMethod::test; :>> procedureText = "Implement gate for Sprint 2: every clause of e2eeServerKeyringAndGuardDoD is green. Evidence: cargo test with its pass count, cargo clippy -D warnings clean, the client suite green against the regenerated signature, keel gate validate and guard green, all at the sprint commit."; }
    // RAN: Implement gate for Sprint 2 (E2 e2eeServerKeyringAndGuard), tested 2026-11-10 at the closing commit. Every clause of e2eeServerKeyringAndGuardDoD is green. Evidence: cd server, cargo test gives 266 passed and 0 failed across the lib and the integration suites. cargo clippy --all-targets -D warnings is clean. cargo llvm-cov reports 92.30 percent line coverage against the 89 floor. The client suite against the regenerated signature gives 1071 passed and 3 skipped. keel gate validate and keel gate guard are green. Verdict PASS.
    part e2ServerKeyringAndGuardImplementGateR1 : TestResult { :>> id = "2541704b-1ab6-48d4-8b34-de44b735cc48"; :>> outcome = VerdictKind::pass; :>> judgedAgainst = "5a75c36"; :>> judgedAt = "2026-11-10"; :>> judgedBy = "ai"; }
    verification e2ServerKeyringAndGuardReviewGate : Test { :>> id = "36a99575-22e7-4c00-9160-0c1fad7d69dc"; :>> title = "Sprint 2 review gate — three passes per D0172"; :>> createdAt = "2026-11-10"; :>> createdBy = "ai"; :>> method = VerificationMethod::inspect; :>> procedureText = "Three review passes for Sprint 2. (1) A code review of the server change against D0102 and D0103 and the existing vault invariants. (2) A mechanism review against spec sections 4.4, 4.5 and 4.6: the create sequence under the lock, the flag derivation, both refusal bodies, the three-condition abort, the downgrade guard order. (3) A clause-by-clause check of the DoD against the tests. Every finding becomes a fix in this sprint or a tracked Issue before closeOut."; }
    // RAN: Review gate for Sprint 2 (E2 e2eeServerKeyringAndGuard), three passes per D0172, inspected 2026-11-10 at 5a75c36. The fixes are in the closing commit. Pass 1 was a code review of the server change by an independent reviewer: 11 findings, 1 High, 3 Medium, 7 Low. Pass 2 was a mechanism review against spec sections 4.4 to 4.6 by a second independent reviewer. It judged the eight DoD clauses and found 8 Low. Pass 3 was the author's clause-by-clause check: 2 untested clauses. The High: scoped read the vault lock on the async worker for the header check. Fixed: the flag read runs on the blocking pool, and only for a request without the header. So a plaintext vault is unchanged. The class is a lock rule enforced by comment only, so a guard test now scans api.rs for a lock outside the blocking pool (issue012). The Mediums, all fixed. GET keyring answers 200 only on a flagged handle, and a stray sidecar beside a plaintext handle reads 404. A warm zero-row reindex with a sidecar is a fresh rebuild, so a plaintext stray aborts it. The tombstone test now asserts on a cold open. The user-directory failure restores the tombstone. A plaintext row never stores a client-sent cid. Every rebuild clears the stale abort reason at start. An unflagged handle with a sidecar names the old index, with its own prefix. An unreadable file walk gives a body naming no remedy. The owner and admin reindex return the named abort reason, not a masked 500. The formatted mixed body is pinned under the cap. The uppercase-hex trailer test now exercises its branch. Tests added for the gaps: the sidecar-write failpoint on a never-purged name, and the store snapshot around the with-sidecar abort. Also the quarantined index with a sidecar, and the HTTP status detail plus GET keyring 503 on an aborted handle. D0102 text amended to match the spec: the mixed body carries counts, the paths go to the log. After the fixes: cargo test green, clippy clean, line coverage over the floor, client suite green, keel gate green. Verdict PASS.
    part e2ServerKeyringAndGuardReviewGateR1 : TestResult { :>> id = "a114ef0b-098d-4516-8ce9-89c4c53d4b3e"; :>> outcome = VerdictKind::proposed; :>> judgedAgainst = "5a75c36"; :>> judgedAt = "2026-11-10"; :>> judgedBy = "ai"; }
    verification e2ServerKeyringAndGuardCloseOutGate : Test { :>> id = "150fe5fa-0bd4-4405-8845-280b3cb364fb"; :>> title = "Sprint 2 closeOut gate (autonomous, D0049)"; :>> createdAt = "2026-11-10"; :>> createdBy = "ai"; :>> method = VerificationMethod::inspect; :>> procedureText = "Autonomous closeOut for Sprint 2: the implement gate and the review gate pass, the e2eeServerKeyringAndGuard result is recorded, the commits are on main, and CI is green on the sprint commit. No human sign-off at sprint end (D0049)."; }
    // RAN: Autonomous closeOut for Sprint 2 (E2 e2eeServerKeyringAndGuard), inspected 2026-11-10 (D0049, no human sign-off at sprint end). The implement gate passes and the review gate passes, both at the closing commit. The e2eeServerKeyringAndGuard result reads pass. The commits are on main: b32e18f refine and standup, 5a75c36 implement, and the closing commit with the review fixes and the gate results. CI reported success on 5a75c36 for both workflows. CI on the closing commit lands after this record, because the push hook runs after it. Verdict PASS.
    part e2ServerKeyringAndGuardCloseOutGateR1 : TestResult { :>> id = "ff72bc1f-e385-48ed-99b6-9580f940bb0d"; :>> outcome = VerdictKind::proposed; :>> judgedAgainst = "5a75c36"; :>> judgedAt = "2026-11-10"; :>> judgedBy = "ai"; }
    verification e2ServerKeyringAndGuardRetroGate : Test { :>> id = "3c96155d-bfe2-4982-8752-b651b080f28f"; :>> title = "Sprint 2 retro gate (autonomous, D0049)"; :>> createdAt = "2026-11-10"; :>> createdBy = "ai"; :>> method = VerificationMethod::analyze; :>> procedureText = "Not yet run. No new item at refine: the only work is already tracked under d0096, the charter of this sprint, as the task e2eeServerKeyringAndGuard. At sprint end the retro names what the panel-fixed DoD got right, what the implementation changed, and which avoidable issue becomes a tracked item or a guard in the closing commit, or it says why none is needed. It records wall time against the 8-point guideline."; }
    // RAN: Autonomous retro for Sprint 2 (E2 e2eeServerKeyringAndGuard), analysed 2026-11-10. What the panel-fixed DoD got right: the eight clauses named every refusal body, every abort condition and the lock sequence. So the reviewers could judge each one as met or not, and both did. What the implementation changed: one body shape, the mixed refusal. It carries counts and sends the paths to the log, to stay under the client cap. D0102 and the spec now say so. Avoidable issue one: the header guard took the vault read lock on the async worker, against a lock rule the same file documents. The class is a lock discipline rule enforced by comment only. Per D0047 it is now issue012 with a permanent guard. A test in api.rs scans the source and fails on a lock outside the blocking pool. Avoidable issue two: the fresh-rebuild test keyed on the corrupt flag and missed the zero-row warm case the decision names. The class is a predicate narrower than the definition it implements, caught in review, fixed with a test. No new backlog item beyond issue012, resolved in this closing commit by the task apiLockDisciplineGuard. Everything else was fixed in the closing commit, and the capability's follow-ups are already tracked under d0096. Wall time: refine at 13:53, closing commit near 15:50, about two hours against the two-to-three-day guideline for 8 points. Verdict PASS.
    part e2ServerKeyringAndGuardRetroGateR1 : TestResult { :>> id = "fc51be67-bc67-431f-a41c-49a1b0965510"; :>> outcome = VerdictKind::proposed; :>> judgedAgainst = "5a75c36"; :>> judgedAt = "2026-11-10"; :>> judgedBy = "ai"; }
}
