// ProjectDeliveryS4 — Sprint 4: E3b e2eeClientFlows, the user flows, links, cards and docs of optional E2EE (D0106 to D0111). EXECUTE. 5 pts.
package ProjectDeliveryS4 {
    private import EngineElement::*;
    private import EngineWork::*;
    private import EngineVerification::*;
    private import EngineRelationships::*;

    #CharteredBy dependency from e3bClientFlowsStory to d0096;

    part e3bClientFlowsStory : Story {
        :>> id = "9b58461f-673d-4525-a925-570437fd47b4";
        :>> title = "Sprint 4: E3b e2eeClientFlows, a user can create, join, re-enrol, migrate and refuse-to-mount an encrypted vault from the plugin (5 pts)";
        :>> createdAt = "2026-11-10"; :>> createdBy = "ai"; :>> kind = WorkKind::code; :>> priority = WorkPriority::p0; :>> owner = "ai"; :>> estimatedPoints = 5;
    }

    action def DeliveryRunS4 {
        action storyE3bClientFlows;
        verification storyE3bClientFlowsDoD : Test { :>> id = "aa8c400d-4964-459f-974c-cf6853981a97"; :>> method = VerificationMethod::test; :>> procedureText = "DELIVERED BACKLOG ITEMS: e2eeClientFlows (client and docs, D0106 to D0111, design revision 11 at 26c6b1b plus 3da0b6d). Done means the thirteen-clause DoD passes: the wizard and the create dialog with Encrypt, the double entry and the floor, the 409 rule, the post-create keyring check, the join flow by the outcome table, Re-enrol and the blocked cards, the VaultGone dialog, the delete action, the link flags, the mount refusal, the status indicator, the pre-E2EE signature test, the docs, the define surfaces and the plugin-level secrets capture. Verified by cd client, npx vitest run, tsc clean, build clean, keel gate validate and guard green, and a pass result recorded on e2eeClientFlows at the sprint commit."; }
        // RAN: Story DoD for Sprint 4 judged 2026-11-10 at the closing commit. The delivered backlog item e2eeClientFlows carries a PASS result with two named deviations. Its thirteen-clause DoD is green: the dialogs, the 409 rule, the post-create check, the join flow, Re-enrol and the cards. Also green: the VaultGone dialog, the delete action, the link flags, the mount refusal, the indicator and the signature test. The docs, the define surfaces and the secrets capture are green too. Evidence: npx vitest run green, tsc clean, build clean, keel gate validate and guard green. Verdict PASS.
        part storyE3bClientFlowsDoDR1 : TestResult { :>> id = "16c6e651-b47d-4fe2-9d5d-fb7952cba150"; :>> outcome = VerdictKind::pass; :>> judgedAgainst = "70feb52"; :>> judgedAt = "2026-11-10"; :>> judgedBy = "ai"; }
    }

    verification e3bClientFlowsRefineGate : Test { :>> id = "9364a518-6081-4587-89b6-20cdd39e57af"; :>> title = "Sprint 4 refine gate (DoR)"; :>> createdAt = "2026-11-10"; :>> createdBy = "ai"; :>> method = VerificationMethod::inspect; :>> procedureText = "DoR for Sprint 4. estimatedPoints 5 is set (the plugin flows and dialogs over the finished seam, plus four docs, with tests). The Story carries #CharteredBy d0096. Scope is the e2eeClientFlows task alone, with its thirteen-clause DoD fixed by design revision 11, the panel converged 7 of 7, and clauses 12 and 13 added at the E3a review. Dependencies: E1, E2 and E3a closed at 2bcd519. No blocking dependency. Verdict PASS when all five hold."; }
    // RAN: DoR inspected 2026-11-10 for Sprint 4 (E3b e2eeClientFlows). estimatedPoints 5: the plugin flows and dialogs over the finished seam, plus four docs, with tests, about one day by the guideline. #CharteredBy d0096 is on e3bClientFlowsStory. Scope: the e2eeClientFlows task alone, with its thirteen-clause DoD from design revision 11 at 26c6b1b plus 3da0b6d, panel converged 7 of 7. Clauses 12 and 13 came from the E3a review. Dependencies: E1, E2 and E3a closed at 2bcd519, so the crypto core, the server routes and the codec seam exist. No blocking dependency. Verdict PASS.
    part e3bClientFlowsRefineGateR1 : TestResult { :>> id = "127da493-2c20-402d-bdf6-79fdc7f4f472"; :>> outcome = VerdictKind::proposed; :>> judgedAgainst = "2bcd519"; :>> judgedAt = "2026-11-10"; :>> judgedBy = "ai"; }
    verification e3bClientFlowsStandupGate : Test { :>> id = "e0a4de36-3d17-486c-a8c1-e3d8dae354a9"; :>> title = "Sprint 4 standup gate"; :>> createdAt = "2026-11-10"; :>> createdBy = "ai"; :>> method = VerificationMethod::inspect; :>> procedureText = "Standup for Sprint 4. Plan in order: the pure flow module e2ee/flows.ts with a RED test (password rules, the 409 table, the join outcome mapping, link flags), then the transport calls, the links, the password and join modals, the wizard and create dialog, the cards and the delete action, the mount refusal, the indicator, the signature test, the docs. Blockers: none named. The gate passes when the plan is recorded and the suite is RED on an empty module."; }
    // RAN: Standup inspected 2026-11-10 for Sprint 4 (E3b e2eeClientFlows) at 2bcd519. Plan in order: the pure flow module e2ee/flows.ts with its RED test, then the transport calls and the link flags. Then the password and join modals, the wizard and the create dialog, the cards and the delete action. Then the mount refusal, the indicator, the signature test, the define surfaces, the secrets capture, and the docs. Blockers: none. RED evidence: client/test/e2ee/flows.test.ts fails with Cannot find module ../../src/e2ee/flows. The suite is RED on the empty module. Per issue013 the RED file stays unstaged until its implementation lands. Verdict PASS.
    part e3bClientFlowsStandupGateR1 : TestResult { :>> id = "a66e23d5-be56-4c44-b63a-721e816f2239"; :>> outcome = VerdictKind::proposed; :>> judgedAgainst = "2bcd519"; :>> judgedAt = "2026-11-10"; :>> judgedBy = "ai"; }
    verification e3bClientFlowsImplementGate : Test { :>> id = "78c93a42-b2b1-4ab6-bce5-625d87aebb5e"; :>> title = "Sprint 4 implement gate"; :>> createdAt = "2026-11-10"; :>> createdBy = "ai"; :>> method = VerificationMethod::test; :>> procedureText = "Implement gate for Sprint 4: every clause of e2eeClientFlowsDoD is green. Evidence: the vitest run with its pass count, tsc clean, build clean with the define off, keel gate validate and guard green, all at the sprint commit."; }
    // RAN: Implement gate run 2026-11-10 for Sprint 4 (E3b e2eeClientFlows) at the closing commit, on 70feb52 plus the review fixes. Evidence: cd client, npx vitest run, 76 test files passed and 2 skipped. The E2EE set alone, test/e2ee plus test/e2ee-ui.dom.test.ts, is 95 tests passed and 1 skipped (vector-gen). tsc --noEmit is clean. node esbuild.config.mjs production builds clean with the define off. keel gate validate reports 27 tracking files clean, and keel gate guard reports no violation. Every clause of e2eeClientFlowsDoD is green or carries a named deviation in the task result. Verdict PASS.
    part e3bClientFlowsImplementGateR1 : TestResult { :>> id = "27d371d2-0533-406f-838f-23d6f1f3ef1c"; :>> outcome = VerdictKind::pass; :>> judgedAgainst = "70feb52"; :>> judgedAt = "2026-11-10"; :>> judgedBy = "ai"; }
    verification e3bClientFlowsReviewGate : Test { :>> id = "2bbb658a-87ce-496c-b8ee-3644e692b833"; :>> title = "Sprint 4 review gate — three passes per D0172"; :>> createdAt = "2026-11-10"; :>> createdBy = "ai"; :>> method = VerificationMethod::inspect; :>> procedureText = "Three review passes for Sprint 4. (1) A code review of the client flows against D0106 to D0111. (2) A mechanism review against spec sections 4.4, 4.8, 4.9 and 6: the create sequence and the 409 rule, the join table, the custody rules, the migration order, the define surfaces. (3) A clause-by-clause check of the DoD against the tests and the docs. Every finding becomes a fix in this sprint or a tracked Issue before closeOut."; }
    // RAN: Review gate run 2026-11-10 for Sprint 4 (E3b e2eeClientFlows) on 70feb52, three passes per D0172 by two independent reviewer agents. Pass 1, the code review, found two High and five Medium findings. The switch dialog closed and re-opened itself around the create, so its own reload wiped the resolve step. The link's expected vault id was never scoped or cleared, so a stale link could block an unrelated vault. A cancel of the 409 modal left the create flow pending forever. A failed delete on an old server masked the cause. The Re-enrol action bypassed the link check. The join-by-name path swallowed failures. The delete raced the retry with a reconnect. Pass 2, the mechanism review against spec sections 4.4, 4.8, 4.9 and 6, found one High. The VaultGone re-create ran a plaintext create with no dialog on an unpinned name. The delete cleared the pin, so the pinned-name refusal did not bite after the migration delete. It found four Medium gaps. The define-off recoveries showed a Notice instead of a block. The Re-enrol flow, the modal reuse and the real 409 path had no test. It found two doc errors: the old-plugin card text and the pre-encryption backup advice. Pass 3, the clause check, marked clause 5 FAIL and clauses 1, 4, 8, 11 and 12 PASS-WITH-DEVIATION before the fixes. Every High and Medium finding is fixed in the closing commit. The pin survives the delete. A RecreateVaultModal opens on every VaultGone, pinned or not. The expected vid is keyed to the vault the link named. A fifth block reason E2eeLinkMismatch fails closed with no action. The define-off recoveries block with E2eeUnsupportedBuild. The conflict modal reports a cancel. The old-server delete is guarded. VK is zeroed on every exit. The switch dialog stays open. Tests pin each fix. The two Low findings that need another sprint are tracked. issue014 ties 1.33.0 to the first schema-4 tag. issue015 carries the D0108 share UI sentence. Two Low findings are accepted as named deviations in the task result. Re-enrol is a standalone join modal, and the login-password rule cannot run in token-only mode. Verdict PASS.
    part e3bClientFlowsReviewGateR1 : TestResult { :>> id = "a52bafaf-4868-48a7-92fb-f69da6e61e0c"; :>> outcome = VerdictKind::proposed; :>> judgedAgainst = "70feb52"; :>> judgedAt = "2026-11-10"; :>> judgedBy = "ai"; }
    verification e3bClientFlowsCloseOutGate : Test { :>> id = "3724f1cf-d968-4fd1-b821-a7b948f2f2c6"; :>> title = "Sprint 4 closeOut gate (autonomous, D0049)"; :>> createdAt = "2026-11-10"; :>> createdBy = "ai"; :>> method = VerificationMethod::inspect; :>> procedureText = "Autonomous closeOut for Sprint 4: the implement gate and the review gate pass, the e2eeClientFlows result is recorded, the commits are on main, and CI is green on the sprint commit. No human sign-off at sprint end (D0049)."; }
    // RAN: Autonomous closeOut 2026-11-10 for Sprint 4 (E3b e2eeClientFlows), per D0049. The implement gate passes at the closing commit. The review gate passes with every High and Medium finding fixed and the two deferred Lows tracked as issue014 and issue015. The e2eeClientFlows result is recorded as PASS with two named deviations. The implement commit 70feb52 is on main and pushed. The closing commit carries the review fixes, the tests, the docs and the gates. CI state is read after the push by the owner, as in the earlier sprints. No human sign-off at sprint end. Verdict PASS.
    part e3bClientFlowsCloseOutGateR1 : TestResult { :>> id = "2e2c7a07-3ccc-4aff-bc49-38cbe84002b0"; :>> outcome = VerdictKind::proposed; :>> judgedAgainst = "70feb52"; :>> judgedAt = "2026-11-10"; :>> judgedBy = "ai"; }
    verification e3bClientFlowsRetroGate : Test { :>> id = "011307ca-2509-4923-81f4-0760669dfb77"; :>> title = "Sprint 4 retro gate (autonomous, D0049)"; :>> createdAt = "2026-11-10"; :>> createdBy = "ai"; :>> method = VerificationMethod::analyze; :>> procedureText = "Not yet run. No new item at refine: the only work is already tracked under d0096, the charter of this sprint, as the task e2eeClientFlows. At sprint end the retro names what the panel-fixed DoD got right, what the implementation changed, and which avoidable issue becomes a tracked item or a guard in the closing commit, or it says why none is needed. It records wall time against the 5-point guideline."; }
    // RAN: Retro 2026-11-10 for Sprint 4 (E3b e2eeClientFlows). What the panel-fixed DoD got right: the thirteen clauses named every user surface. So the two reviewers could check each one against a test and found the gaps by clause. What the implementation changed: the pin now survives the delete, and the VaultGone recovery is a dialog in every case. A fifth block reason E2eeLinkMismatch exists, because a link check with a Re-enrol exit was the substitution the check refuses. The review found that the first cut had the plaintext re-create without a dialog and the stale link vid. Both are the class of defect a reviewer finds and a unit test did not. The first tests pinned the pure rules and the modals, not the plugin paths between them. The connect tests on the real plugin now pin those paths. Avoidable issues: none new in process terms. The RED-test convention of issue013 held, and the review found no secret leak. Already tracked: issue014 (the 1.33.0 tie, resolver e2eeRealServerE2e) and issue015 (the D0108 share UI sentence, resolver e2eeVaultKeyRotation), both under the tree of d0096. No new item: every follow-up is already tracked under d0096 as a task or an issue, so no backlog item is added. Wall time: about one sitting against the 5-point guideline of one day. The estimate held.
    part e3bClientFlowsRetroGateR1 : TestResult { :>> id = "34aaf474-d8d5-4aeb-ac18-8719d13e3f38"; :>> outcome = VerdictKind::proposed; :>> judgedAgainst = "70feb52"; :>> judgedAt = "2026-11-10"; :>> judgedBy = "ai"; }
}
