// ProjectDeliveryS8 — Sprint 8: the 62 second live change latency against the owner's server (issue020) named from captured plugin logs and fixed or documented, before 1.34.1 is cut (st016). EXECUTE. 3 pts.
package ProjectDeliveryS8 {
    private import EngineElement::*;
    private import EngineWork::*;
    private import EngineVerification::*;
    private import EngineRelationships::*;

    #CharteredBy dependency from e2eeRemoteLiveLatencyStory to d0096;

    part e2eeRemoteLiveLatencyStory : Story {
        :>> id = "76e8c090-c2d9-4d21-bf3a-c815067e4a48";
        :>> title = "Sprint 8: the live change latency against the real server named from evidence and fixed or documented, the release waits on it (3 pts)";
        :>> createdAt = "2026-11-11"; :>> createdBy = "ai"; :>> kind = WorkKind::code; :>> priority = WorkPriority::p0; :>> owner = "ai"; :>> estimatedPoints = 3;
    }

    action def DeliveryRunS8 {
        action storyE2eeRemoteLiveLatency;
        verification storyE2eeRemoteLiveLatencyDoD : Test { :>> id = "f38c42c9-a54a-46e9-8358-ebe28558db78"; :>> method = VerificationMethod::test; :>> procedureText = "DELIVERED BACKLOG ITEMS: e2eeRemoteLiveLatency. Done means the cause of the 62 second live change latency is named from the captured plugin logs of both devices, with the log lines cited, and either fixed in code with a test or documented as a proxy setting, and a rerun against the owner server converges the live note under 5 seconds. Verified by the rerun E2EE-MEASURE line, the client suite green, keel gate validate and guard green, and a result on e2eeRemoteLiveLatency at the sprint commit."; }
        // RAN: storyE2eeRemoteLiveLatencyDoD judged 2026-11-11 at b9d6cda. The delivered item e2eeRemoteLiveLatency carries result R3 PASS. The cause is named from the kept logs with cited lines: the reconnect backoff after a server restart. It is documented in docs/deployment.md on the owner's accept-risk (st019). The runs without an outage converge in 0.53 to 1.57 seconds. The client suite is green, keel gate validate and guard green, CI run 43102738323 green. Verdict PASS.
        part storyE2eeRemoteLiveLatencyDoDR1 : TestResult { :>> id = "51e43276-73e8-485e-b10b-36858303de97"; :>> outcome = VerdictKind::pass; :>> judgedAgainst = "b9d6cda"; :>> judgedAt = "2026-11-11"; :>> judgedBy = "ai"; }
    }

    verification e2eeRemoteLiveLatencyRefineGate : Test { :>> id = "3ad97d87-2fbd-48bc-b3ee-e41c69fb8eb9"; :>> title = "Sprint 8 refine gate (DoR)"; :>> createdAt = "2026-11-11"; :>> createdBy = "ai"; :>> method = VerificationMethod::inspect; :>> procedureText = "DoR for Sprint 8. estimatedPoints 3 is set: a log capture option in the spec, one or more diagnostic reruns against the owner server, the cause analysis, a code or doc fix, a verifying rerun. The Story carries CharteredBy d0096. Scope is the e2eeRemoteLiveLatency task. Dependencies: the owner test account on https://notes2.willweatherholtz.com, Obsidian on this machine. The owner direction st016 puts this before the 1.34.1 release and waives the sitting review. Verdict PASS when all hold."; }
    // RAN: DoR for Sprint 8 judged 2026-11-11 at 67221b6. estimatedPoints 3 is set. The work: a log capture option in the spec, diagnostic reruns against the owner server, the cause analysis, a fix, a verifying rerun. The Story carries CharteredBy d0096. Scope is the e2eeRemoteLiveLatency task alone. Dependencies hold. The owner test account on https://notes2.willweatherholtz.com works, Obsidian runs on this machine. The owner direction st016 puts this sprint before the 1.34.1 release and waives the sitting review. Verdict PASS.
    part e2eeRemoteLiveLatencyRefineGateR1 : TestResult { :>> id = "a9ff6139-fc7e-405d-b2dc-7b1cbc8170a5"; :>> outcome = VerdictKind::proposed; :>> judgedAgainst = "67221b6"; :>> judgedAt = "2026-11-11"; :>> judgedBy = "ai"; }
    verification e2eeRemoteLiveLatencyStandupGate : Test { :>> id = "b3726c9e-8b0c-48b5-845e-52acd7714766"; :>> title = "Sprint 8 standup gate"; :>> createdAt = "2026-11-11"; :>> createdBy = "ai"; :>> method = VerificationMethod::inspect; :>> procedureText = "Standup for Sprint 8. Plan in order: add SELFSYNC_E2E_KEEP_LOGS and a device B transport snapshot to the spec, rerun against the owner server, read both logs around the live note, name the cause from the lines, fix or document it, rerun to verify under 5 seconds, record the result, commit. Blocker: none known. Risk: the cause may sit in the proxy, which only the owner can change; then the fix is a documented setting and the rerun needs the owner to apply it."; }
    // RAN: Standup for Sprint 8, 2026-11-11. Plan in order: add SELFSYNC_E2E_KEEP_LOGS and a device B transport snapshot to the spec. Rerun against the owner server, read both logs around the live note, name the cause from the lines. Fix or document it, rerun to verify under 5 seconds, record the result, commit. Blocker: none known at standup. Risk: the cause may sit in the proxy or the host, which only the owner can change. Then the fix is a documented setting and the rerun needs the owner to apply it. Verdict PASS.
    part e2eeRemoteLiveLatencyStandupGateR1 : TestResult { :>> id = "0adf82e3-758a-416d-a620-a06ecd633fd0"; :>> outcome = VerdictKind::proposed; :>> judgedAgainst = "67221b6"; :>> judgedAt = "2026-11-11"; :>> judgedBy = "ai"; }
    verification e2eeRemoteLiveLatencyImplementGate : Test { :>> id = "446d8e27-2587-4b41-af61-fc7f15e9e501"; :>> title = "Sprint 8 implement gate"; :>> createdAt = "2026-11-11"; :>> createdBy = "ai"; :>> method = VerificationMethod::test; :>> procedureText = "Implement gate for Sprint 8: the diagnostic rerun produced both logs, the cause is named with cited lines, the fix is in place, the verifying rerun against the owner server shows convergeEncryptedSecondsLive under 5 seconds, the client suite is green, keel gate validate and guard green. Evidence: the two E2EE-MEASURE lines, the log excerpt, the gate output at the sprint commit."; }
    // RAN: Implement gate for Sprint 8 judged 2026-11-11 at be3f5ae. The diagnostic reruns produced both logs: 36 remote runs, and two loopback restart runs mwcm9clw and mwcmbk4j. The cause is named with cited lines in e2eeRemoteLiveLatencyDoDR3: the reconnect backoff in main.ts line 3238 after ERR_CONNECTION_REFUSED. The fix is a documented behaviour, docs/deployment.md After a server restart, on the owner's accept-risk (st019). The verifying runs against the owner server show convergeEncryptedSecondsLive from 0.53 to 1.57 seconds. Client suite 1152 green, tsc clean, keel gate validate and guard green at the sprint commit. Verdict PASS.
    part e2eeRemoteLiveLatencyImplementGateR1 : TestResult { :>> id = "e891fcf0-f2cb-4bf0-840a-bdd56ecfe61b"; :>> outcome = VerdictKind::pass; :>> judgedAgainst = "be3f5ae"; :>> judgedAt = "2026-11-11"; :>> judgedBy = "ai"; }
    verification e2eeRemoteLiveLatencyReviewGate : Test { :>> id = "69295cf4-fced-4ae1-a68c-17ede21ceec5"; :>> title = "Sprint 8 review gate — three passes per D0172"; :>> createdAt = "2026-11-11"; :>> createdBy = "ai"; :>> method = VerificationMethod::inspect; :>> procedureText = "Three review passes for Sprint 8. (1) The cause against the logs: do the cited lines support the named cause and exclude the other two candidates of the issue020 DoD. (2) The fix: does it address the cause and not mask it, and does a test or a documented setting guard it. (3) The rerun: does the measured latency fall under 5 seconds and does the earlier slow path reproduce without the fix. Every finding becomes a fix in this sprint or a tracked Issue."; }
    // RAN: Review gate for Sprint 8 judged 2026-11-11 at be3f5ae. Pass 1, the cause against the logs. The cited lines of mwcmbk4j show four refused connects on device A. The backoff ladder reads 3s, 4s, 9s, 22s. The reconnect at 21:16:53 lands 11 seconds after the server was back at 21:16:41. That supports the named cause. The proxy candidate is excluded by the 200 second probe, the server candidate by 36 published changes. The 503 slow retry and the idle poll appear in no log. Pass 2, the fix. The owner accepted the latency as a risk (st019). The sprint documents the behaviour and leaves the 30 second cap in place. The cap is a deliberate fleet dispersal after a restart, main.ts line 3227. The reproduction knob SELFSYNC_E2E_RESTART_AT_LIVE guards the documented numbers: anyone can rerun them. No code path changed, so no new unit test. Pass 3, the rerun. 36 remote runs without an outage converge in 0.53 to 1.57 seconds, under 5 seconds. The slow path reproduces on demand with the knob: 13.51 seconds for a 10 second outage, 47.26 for 35. One finding: the fake transport in connect.test.ts called setEncrypted without the optional chain and failed tsc. Fixed in this sprint. No tracked Issue results. Verdict PASS.
    part e2eeRemoteLiveLatencyReviewGateR1 : TestResult { :>> id = "e1adbd59-8fda-4501-aa2a-e7918b55a6ed"; :>> outcome = VerdictKind::proposed; :>> judgedAgainst = "be3f5ae"; :>> judgedAt = "2026-11-11"; :>> judgedBy = "ai"; }
    verification e2eeRemoteLiveLatencyCloseOutGate : Test { :>> id = "8842aed0-e292-4a09-81eb-e8bb1e24ba0f"; :>> title = "Sprint 8 closeOut gate (autonomous, D0049)"; :>> createdAt = "2026-11-11"; :>> createdBy = "ai"; :>> method = VerificationMethod::inspect; :>> procedureText = "Autonomous closeOut for Sprint 8: the implement gate and the review gate pass, the e2eeRemoteLiveLatency result is recorded, the commits are on main, CI is green on the sprint commit. No human sign-off at sprint end (D0049), and the owner waived the sitting review in st016."; }
    // RAN: CloseOut for Sprint 8 judged 2026-11-11 at b9d6cda. The implement gate and the review gate pass at be3f5ae. The e2eeRemoteLiveLatency result R3 PASS is recorded, and issue020 no longer shows in keel show open-issues. The commits 67221b6, f764122, be3f5ae and b9d6cda are on main. CI run 43102738323 is green on b9d6cda. No human sign-off at sprint end (D0049), and the owner waived the sitting review in st016. Verdict PASS.
    part e2eeRemoteLiveLatencyCloseOutGateR1 : TestResult { :>> id = "29641d05-8697-44bb-93b0-700512c6f990"; :>> outcome = VerdictKind::proposed; :>> judgedAgainst = "b9d6cda"; :>> judgedAt = "2026-11-11"; :>> judgedBy = "ai"; }
    verification e2eeRemoteLiveLatencyRetroGate : Test { :>> id = "39795430-b86b-47b4-8220-142b92e5d937"; :>> title = "Sprint 8 retro gate (autonomous, D0049)"; :>> createdAt = "2026-11-11"; :>> createdBy = "ai"; :>> method = VerificationMethod::analyze; :>> procedureText = "Not yet run. No new item at refine: issue020 is tracked with this task as its resolver. At sprint end the retro names what the diagnosis cost, which avoidable issue becomes a tracked item or a guard, or why none is needed. It records wall time against the 3-point guideline."; }
    // RAN: Retro for Sprint 8 judged 2026-11-11 at b9d6cda. Estimate 3 points, guideline 5 to 10 hours. Wall time about 4 hours across two sittings on 2026-11-11, from 67221b6 to b9d6cda. Cost of the diagnosis: 36 remote reruns and a 200 second WebSocket probe found nothing, because the slow run had no kept log. One question to the owner and a 10 second reproduction found the cause. Avoidable: the spec had no log capture and no outage reproduction when the slow run happened. Both gaps closed in this sprint as SELFSYNC_E2E_KEEP_LOGS and SELFSYNC_E2E_RESTART_AT_LIVE, documented in docs/testing.md. Lesson: ask the operator about restarts before a blind rerun campaign. Item added: none. The two tooling gaps are closed in code in this sprint, and issue020 resolves through the task result. No open finding remains to track. Verdict PASS.
    part e2eeRemoteLiveLatencyRetroGateR1 : TestResult { :>> id = "89cd5249-b023-482c-9285-f43d190ad7f2"; :>> outcome = VerdictKind::proposed; :>> judgedAgainst = "b9d6cda"; :>> judgedAt = "2026-11-11"; :>> judgedBy = "ai"; }
}
