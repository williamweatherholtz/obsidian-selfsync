// =====================================================================
// ProjectDelivery — the SelfSync delivery backlog (backfilled 2026-07-04, D0004). The shipped
// milestones (M1-M6, the goal-#1 config-UX overhaul, the 0.6.0 fix set) are DONE tasks, each
// with a method-tagged DoD Test + an appended pass TestResult (judged at the backfill commit;
// the automated suites are green at HEAD). The outstanding backlog (B7/B9/B11 + the L3/L4
// verification gaps) are OPEN tasks — a DoD criterion with NO pass result yet, so `keel orient`
// reports them as the ready/outstanding frontier. Results are APPENDED, never edited.
// =====================================================================
package ProjectDelivery {
    private import EngineElement::*;
    private import EngineWork::*;
    private import EngineVerification::*;
    private import ProjectBusiness::*; // nConfigSync — the Need the config-sync capability derives from

    action def SelfSyncDelivery {
        // ---- open backlog (NOT done) ----
        // Follow-up to changeProvenanceNotify (1.18.0): notify on a peer's config/plugin DELETION too. The
        // source-driven notice covers add/edit changes (they carry provenance); a DELETION does not, because
        // the Deletion wire type has no author/device fields. Extending it needs Deletion provenance on the
        // server + a delete-path notice on the client. Triages issueDeletionProvenanceUnnotified (open).
        action deletionProvenanceNotify;
        verification deletionProvenanceNotifyDoD : Test { :>> id = "6c061da7-17d7-41f0-851a-d6e5dd6c458e"; :>> method = VerificationMethod::test; :>> procedureText = "DONE (green @ 420f4b9): resolves issueDeletionProvenanceUnnotified. A peer DELETING a synced config/plugin file was applied with NO notice (the Deletion wire record carried no author/device, unlike upserts since 1.18.0). Ships MINOR 1.29.0 (new notice capability; SERVER REDEPLOY - SQLite schema v2->v3). SERVER: the Deletion struct gains optional author/device_id/device_name (serde default+skip, additive wire); the `deletions` table gains the same three author_* columns via a v3 migration (probe pragma_table_info + ALTER-ADD, mirroring the v2 files-provenance migration; legacy tombstones read None); delete_checked threads author (SERVER-authenticated user, never a client field) + client-asserted device to index.delete which records them on the tombstone; changes() returns them; the DELETE /file handler reads device_id/device_name from QUERY params (DELETE has no body) + passes the token user as author. Wire signature regenerated (both artifacts; additive - Deletion's new fields are required:false). CLIENT: the Deletion TS type + validateChanges MAP the deletion's snake_case provenance to camelCase (and - fixing a latent forEach-discard, issueUpsertProvenanceNotMapped - map UPSERTS too, so deviceId/deviceName finally reach the notify path, not just author); transport.deleteFile sends device query params; reconcile fires onRemoteConfigDelete from the removeLocal branch (config-only, AFTER the remove succeeds so a failed removal makes no false notice) with the tombstone's provenance, plumbed via a per-pass delByPath map in reconcileAll/reconcileDelta/reconcilePath; main.flushConfigDeletions fires ONE source-attributed Notice per pass (silent for your OWN removal). INDEPENDENT CRITIQUE (findings-only) drove: the notice counts ONLY the named source's removals (never folding a second peer / your own device into one peer's count), the fire-AFTER-remove ordering (no false/repeating notice on a failed removal), reconcilePath carrying the provenance it already fetched, and a conditional restart hint; it confirmed the v2->v3 migration is idempotent, author is unspoofable (server-set), and the validateChanges map change breaks no consumer. Server+client -> SERVER-IMAGE REDEPLOY required. DoD MET: full server cargo test 150 passed (+ delete_records_provenance, delete_with_empty_author, migrate v2->v3) + clippy -D warnings clean; full client vitest 804 passed (+ deletion-provenance mapping, transport device params, reconcile config-delete + fire-after-remove, mixed-batch notice attribution); tsc + production build clean; keel validate + guard green."; }
        part deletionProvenanceNotifyDoDR1 : TestResult { :>> id = "43758f63-b44d-46d9-9bec-57ea3b25a908"; :>> outcome = VerdictKind::pass; :>> judgedAgainst = "420f4b9"; :>> judgedAt = "2026-08-14"; :>> judgedBy = "claudeOpus"; }
        // ===== 1.29.2 — field bug fix: the 1.29.0 optional-field wire-compat regression (owner-reported 2026-08-15). =====
        action optionalResponseFieldNonGating;      // resolver for issueOptionalResponseFieldGates
        verification optionalResponseFieldNonGatingDoD : Test { :>> id = "bbb0f4a7-feea-41e9-b767-c315b1e93b71"; :>> method = VerificationMethod::test; :>> procedureText = "DONE (green @ 300c5f3): resolves issueOptionalResponseFieldGates - an OWNER FIELD REPORT that a 1.29 client refused to sync ('the server dropped Deletion.author/device_id/device_name, which this plugin reads') even though the owner updated BOTH sides. ROOT CAUSE: diffSignature's RESPONSE branch flagged ANY embedded field the server lacks as breaking regardless of `required`, so a NEWER client that ADDED optional response fields (the 1.29 Deletion provenance) hard-blocks sync against an OLDER - or momentarily MID-REDEPLOY - server; a backward-compat regression from 1.29.0. FIX (client-only, wiresignature.ts): an OPTIONAL (required:false) response field the server lacks is NON-breaking (the client reads it undefined-safe) - only a REQUIRED one gates; the retype / required->optional (F2) / request-side / endpoint / type / epoch rules are unchanged. Plus (a) a GUARD test that allowlists every optional response field in a gating type as known-undefined-safe, so a FUTURE optional field fails the test until its consumer is confirmed (converts the invariant from vigilance to a check); (b) a DIRECTIONAL hint - server-lacks-something -> likely the server is older (hedged: 'if you JUST updated the server, update the plugin instead', covering the owner's exact case), server-demands-something-new / higher epoch -> the plugin is older, a retype/mixed -> 'update whichever is older' - so the message no longer just says 'update whichever is older'. INDEPENDENT CRITIQUE confirmed the relaxation is sound (all current optional response fields are undefined-safe: Deletion/FileMeta provenance, ChangesResponse.history_floor keep-and-push, StatusResponse cosmetic/fail-closed, LoginResponse.must_change_password), the asymmetry is preserved (retype + F2 still gate; ef is always the trusted embedded side so a hostile server can't sneak a removal past), and drove the guard test (Finding 1) + the hedged wording (Finding 2, avoid confidently misdirecting when a newer server removed a deprecated field). Client-only, PLUGIN-ONLY (1.29.2). DoD MET: tsc clean, wiresignature vitest (optional-field non-gating + directional hint + the undefined-safe guard), full client vitest green, production build clean, keel validate + guard green."; }
        part optionalResponseFieldNonGatingDoDR1 : TestResult { :>> id = "14598883-e0f2-46d6-8c05-f65745ac1a27"; :>> outcome = VerdictKind::pass; :>> judgedAgainst = "300c5f3"; :>> judgedAt = "2026-08-15"; :>> judgedBy = "claudeOpus"; }
        // ===== 1.29.3 — UX: one concise notice for pending server-side plugins (owner-requested 2026-08-15). =====
        action declinedPluginNoticeCoalesce;        // resolver for issueDeclinedPluginNoticeSpam
        verification declinedPluginNoticeCoalesceDoD : Test { :>> id = "44f2b812-7474-4c5c-a729-b07c245094ff"; :>> method = VerificationMethod::test; :>> procedureText = "DONE (green @ f4ed947): resolves issueDeclinedPluginNoticeSpam (owner request - 'just one indicating there are pending plugins will do'). The declined-plugins notice re-logged on nearly every poll/reconnect because noteDeclined de-duped on the raw declined FILE list, which differs between the full pass + each delta subset. FIX (client-only): (1) fire onDeclined ONLY from the FULL pass reconcileAll - removed it from reconcileDelta, whose partial changed-subset view churned the notice; (2) de-dup on the stable PLUGIN SET (sorted ids + a config-files flag), so it fires once per distinct declined set; (3) simplify to a COUNT ('N community plugins ... aren't synced to this device - enable them in Settings -> SelfSync -> Obsidian configuration'), not the full plugin list. Client-only, PLUGIN-ONLY (1.29.3). DoD MET: tsc clean, plugin-wiring vitest added (one notice per distinct plugin set; a different file subset of the same plugins does NOT re-log; a changed set does; the message is a count, not the list), full client vitest 812 passed, production build clean, keel validate + guard green."; }
        part declinedPluginNoticeCoalesceDoDR1 : TestResult { :>> id = "29300c12-3461-46b3-9f6b-6f69a62ffc8f"; :>> outcome = VerdictKind::pass; :>> judgedAgainst = "f4ed947"; :>> judgedAt = "2026-08-15"; :>> judgedBy = "claudeOpus"; }
        // ===== 1.29.4 — hardening from a 3-lens independent critique of the shipped 1.29.x cluster (2026-08-15). =====
        action cluster129CritiqueHardening;         // resolves the concurrency + migration + multi-source findings
        verification cluster129CritiqueHardeningDoD : Test { :>> id = "64ecc509-6f86-4395-8105-49e5ae006899"; :>> method = VerificationMethod::test; :>> procedureText = "DONE (green @ 63996ba): a 3-lens INDEPENDENT critique (data-safety / concurrency / mixed-fleet-migration) of the shipped 1.29.x cluster (deletion provenance + primary serialization + wire-compat + declined notice). Two MEDIUM + one LOW fixed; the rest verified correct. FIXED: (1) issueHeldResolverWholeScopeClear (MED, concurrency) - the held-review resolvers cleared the WHOLE pending set (pendingBulk*.delete(scope)); since the resolver's base mutation DEFERS behind an in-flight reconcile (the 1.29.1 engine task), that reconcile can add a NEW held path before the tail wipes it -> the new held deletion vanishes from the Conflicts review until the next full scan (safe direction; a trust defect). Now clearHeldPaths subtracts ONLY the applied snapshot (all four resolvers). (2) issueProvenanceMigrationNonAtomic (MED, migration) - the three author_* ALTERs were autocommit + gated by a single-column probe; a crash between them bricked commit/delete forever. Now ensure_provenance_columns adds each column under its OWN probe (idempotent self-heal), for both files (v2) + deletions (v3). (3) issueConfigDeletionMultiSourceUnderreport (LOW) - flushConfigDeletions dropped a second peer's deletions from a mixed pass; now one notice covers ALL notifying sources. VERIFIED CORRECT by the critics (unchanged): the validateChanges forEach->map fix, the v2->v3 downgrade guard (hard-refuse not quarantine) + no-backfill honesty, the wire-relaxation version matrix (1.29 client <-> pre-1.29 server now syncs; older client ignores additive fields), task-serialization liveness + no cross-serializer deadlock, DELETE device-param compatibility. LOW-3 (vault-switch spurious config-delete notice) verified NOT reachable - switchTo uses io.remove directly, never the removeLocal executor that fires onRemoteConfigDelete. DEFERRED: issueSchemaRollbackOpaque500 (F2, a v3->v2 rollback surfaces as an opaque 500). Minor doc notes (F3 hint hedge, F4 pre-1.29-server own-deletion notices) accepted. Server+client (migration) -> SERVER-IMAGE REDEPLOY required (1.29.4); the migration is idempotent + backward-compatible (no CURRENT_SCHEMA bump - still v3 - it self-heals a partially-migrated v3 DB). DoD MET: full server cargo test 151 passed (+ migrate_self_heals_a_partial_provenance_migration) + clippy -D warnings clean; full client vitest 813 passed (+ clearHeldPaths subtract, multi-source config-delete notice); tsc + production build clean; keel validate + guard green."; }
        part cluster129CritiqueHardeningDoDR1 : TestResult { :>> id = "a911249c-1ba3-4986-af12-da8dfa829ca1"; :>> outcome = VerdictKind::pass; :>> judgedAgainst = "63996ba"; :>> judgedAt = "2026-08-15"; :>> judgedBy = "claudeOpus"; }
        action schemaRollbackClearError;            // resolver for issueSchemaRollbackOpaque500
        verification schemaRollbackClearErrorDoD : Test { :>> id = "dc8a144e-073c-4f6f-a50b-faa19de3a165"; :>> method = VerificationMethod::test; :>> procedureText = "DONE (green @ 5effd75): resolves issueSchemaRollbackOpaque500. When an operator rolls the server image BACK after a newer one migrated a vault to a newer schema, index_store's migrate() HARD-refuses with ErrorKind::Unsupported (correct - never quarantine, so no data loss), but scoped() mapped it to AppError::Internal -> a generic 500 'internal error' on every route incl. /status, so the client couldn't diagnose it and the clear message lived only in the server log. FIX (server-only): a new error::vault_open_error helper maps a schema-downgrade (Unsupported) to AppError::Unavailable -> a 503 with a clear, PATH-FREE body ('this server is OLDER than the version that last wrote this vault's data ... update/re-deploy the server ... your data is intact'); any other open failure stays a generic 500 (SEC-6 - the raw message can carry a server path). scoped() (which /status + every sync route funnels through) uses it, so a rolled-back server SELF-DIAGNOSES on the client, which already renders plain-text error bodies (errText). No client change. Server-only -> SERVER-IMAGE REDEPLOY. DoD MET: full server cargo test 152 passed (+ error::tests::vault_open_error_maps_schema_downgrade_to_503_and_others_to_500 - 503+clear body for Unsupported, 500 for other, no raw-text/path echo) + clippy -D warnings clean; keel validate + guard green."; }
        part schemaRollbackClearErrorDoDR1 : TestResult { :>> id = "5b5e8120-2aeb-4de9-9c01-0297d7a3c85e"; :>> outcome = VerdictKind::pass; :>> judgedAgainst = "5effd75"; :>> judgedAt = "2026-08-15"; :>> judgedBy = "claudeOpus"; }
        // Critique of 5effd75 (2026-08-16): harden the message-length coupling; defer the admin-view mislabel.
        action schemaDowngradeMsgHardening;         // resolver for issueSchemaDowngradeMsgLengthCoupling
        verification schemaDowngradeMsgHardeningDoD : Test { :>> id = "50334f83-4e10-4bbc-b671-b8d880c757e2"; :>> method = VerificationMethod::test; :>> procedureText = "DONE (green @ 5e759ce): resolves issueSchemaDowngradeMsgLengthCoupling (MEDIUM, from the critique of 5effd75). The schema-downgrade 503 body was ~276 chars against the client's 300-char plain-text-body cap (transport.ts errText) with only 24 chars of headroom and NO test pinning the cross-language coupling - a reword could silently revert the rollback to an opaque 'HTTP 503'. FIX (server-only): shortened the body to ~190 chars, extracted it to a SCHEMA_DOWNGRADE_MSG const, and added a test assertion that its length stays <= 260 (well under the 300 client cap; UTF-16 code units == chars here) with a comment naming the coupling both ways. Still path-free (SEC-6). The critique's other findings: LOW (the client wraps the body as 'Can't reach the server (...). Retrying...' - the message still surfaces + it self-heals on redeploy; a clean distinct frame would need fragile 503-body matching, left as-is) and LOW deferred (issueAdminHealthMislabelsRollback - the admin health view reports a rolled-back vault as 'missing'; needs a NEW status, tracked). Server-only -> SERVER-IMAGE REDEPLOY. DoD MET: full server cargo test 152 passed (the vault_open_error test now also length-pins the body) + clippy -D warnings clean; keel validate + guard green."; }
        part schemaDowngradeMsgHardeningDoDR1 : TestResult { :>> id = "19947745-9cb9-4dfb-b74f-3accc0e0e7b7"; :>> outcome = VerdictKind::pass; :>> judgedAgainst = "5e759ce"; :>> judgedAt = "2026-08-16"; :>> judgedBy = "claudeOpus"; }
        action adminHealthRollbackStatus;           // resolver for issueAdminHealthMislabelsRollback
        verification adminHealthRollbackStatusDoD : Test { :>> id = "5ae34a20-a730-4796-b47a-013f4f51e42a"; :>> method = VerificationMethod::test; :>> procedureText = "DONE (green @ e378d1e): resolves issueAdminHealthMislabelsRollback (LOW - implemented, not deferred, per the owner 'stop deferring LOWs'). admin.rs vault_health mapped ANY open Err - incl. the schema-downgrade ErrorKind::Unsupported - to 'missing', so /api/admin/vaults reported an intact-but-rolled-back vault as MISSING. FIX (server-only): a new testable open_err_health helper maps Unsupported -> 'incompatible' (intact but needs a newer server), everything else -> 'missing'; NOT the existing 'error' (which nudges reindex, the tombstone-destroying op the downgrade guard prevents). The plugin client drops the status field (validateVaultShares reads only vault+grants), so this surfaces to raw /api/admin/vaults consumers (tooling / a future admin UI). Server-only -> SERVER-IMAGE REDEPLOY. DoD MET: full server cargo test 153 passed (+ admin::health_tests::rolled_back_vault_is_incompatible_not_missing) + clippy -D warnings clean; keel validate + guard green."; }
        part adminHealthRollbackStatusDoDR1 : TestResult { :>> id = "f592e8ce-c015-4380-8f92-47f1e291e9f3"; :>> outcome = VerdictKind::pass; :>> judgedAgainst = "e378d1e"; :>> judgedAt = "2026-08-16"; :>> judgedBy = "claudeOpus"; }
        action rollback503CleanMessage;             // resolver for issueRollback503GenericWrapper
        verification rollback503CleanMessageDoD : Test { :>> id = "87f19340-4127-4ddb-900c-1214c84f3c3b"; :>> method = VerificationMethod::test; :>> procedureText = "DONE (green @ e378d1e): resolves issueRollback503GenericWrapper (LOW - implemented, not deferred). A 503 from /status (the server can't open the vault - a schema-downgrade rollback, or a poisoned lock) fell through to the generic 'Can't reach the server (<body>). Retrying…' wrapper, burying the server's clear operator message inside a transient 'can't reach' frame (the server DID respond). FIX (client-only): establishSession's status() catch detects a 503 (keys on e.info.status===503, NOT fragile body-text matching) and throws a synthetic ServerDegraded carrying the body verbatim; doConnect preserves a synthetic lastIssue, so the operator sees the real reason. Covers both the rollback + poisoned-lock 503. Client-only -> PLUGIN release. DoD MET: tsc clean, plugin-wiring vitest added (a 503 from /status surfaces the server's body, NOT the generic wrapper), full client vitest 814 passed, production build clean, keel validate + guard green."; }
        part rollback503CleanMessageDoDR1 : TestResult { :>> id = "b3163236-9ce7-48dc-bbc5-faad31ccd3b7"; :>> outcome = VerdictKind::pass; :>> judgedAgainst = "e378d1e"; :>> judgedAt = "2026-08-16"; :>> judgedBy = "claudeOpus"; }
        // ===== 1.30.0 — composition recipe: opt-in, reviewed replication of a composed-vault layout (2026-08-17). =====
        action composeRecipeFeature;
        verification composeRecipeFeatureDoD : Test { :>> id = "a1c0e7d2-3b64-4e10-9c20-0a1b2c3d0d01"; :>> method = VerificationMethod::test; :>> procedureText = "DONE (green @ 70915a3): delivers nComposeRecipe (use cases ucExportCompositionRecipe + ucImportCompositionRecipe) - an opt-in, reviewed way to replicate a composed-vault layout WITHOUT a share pushing config or credentials (answers the owner question 'are compositions shared alongside a vault share?' - no, by design: a composition is per-device + colocated with credentials). A user COPIES their composition as a portable selfsync-recipe:// string (mount specs only - source owner/vault/subfolder + local folder + direction - never a token/password/login); the recipient PASTES it and REVIEWS each mount against their OWN grants, applying chosen ones as their own mounts (own local folders; direction fail-closed - Sync only where their grant is read-write, foreign sources default to read-only Pull with opt-up). New client modules composition-recipe.ts (codec + pure import planner) + recipeui.ts (review modal); settings.ts Copy/Import buttons; mounts.ts canonFolder. Client-only -> PLUGIN release (1.30.0, MINOR - new feature); NO server change, NO redeploy. HARDENED IN-PASS by a 3-lens INDEPENDENT critique (correctness / security / UX) before ship. CORRECTNESS: C1 MEDIUM - account/owner compared with raw === but the server lowercases usernames while the client persists as-typed, so a genuine grant could be rejected + an own-vault recipe would not round-trip across devices whose username case differs; fixed with a single canonAccount (trim+lowercase, mirroring main.ts isOwnAccount) on every owner comparison + the emitted recipe owner. C2 LOW - duplicate/self-primary now compare paths canonically (canonFolder, the same NFC+case-fold basis validateMounts uses). C3 LOW - the review modal validates a new row against the IN-EFFECT set (validMounts), so a pre-existing inactive mount cannot falsely block an import. SECURITY: S1 MEDIUM - Copy embedded THIRD-PARTY account names/vault names/paths (for sources shared to the user) while the copy text over-reassured about credentials; now an itemized consent modal lists exactly which shared-vault names will be embedded before copy, and the wording says folder/vault names + paths are included (login + file contents are not). S2 (= UX H1) - a two-way Sync onto a foreign shared vault was sharer-suggested + pre-checked with no destination warning; foreign sources now default to Pull (reader opts up) and a checked Sync row shows an honest 'Sync uploads your changes to <owner>, visible to anyone with access' note, matching MountEditModal. Plus a 200-mount parse cap (UI-jank guard). The critics CONFIRMED CLEAN + UNCHANGED: the isOwn shortcut is NOT exploitable (the server is the access authority - a spoofed owner collapses to the reader's own token, never a cross-tenant read), path-traversal / .obsidian / credential-leak are double-guarded (normMountFolder + validateMounts on both mountPoint AND sourcePath), and fail-closed direction holds across planner + mountFromPlanItem + the modal. UX also fixed: M1 local-folder consequence text; M2 offline (grants unknown) says 'could not verify access, reconnect and try again' not 'ask them to share it'; L1 ready rows first; L2 keep the modal open if every apply failed; L3 the copy notice names excluded inactive mounts. The critique findings became permanent guards (D0047) as new unit tests (case-insensitivity, canonical duplicate, foreign-defaults-to-pull, offline noAccess, size cap). DoD MET: tsc clean, full client vitest 830 passed (+16 composition-recipe: codec round-trip/absolutize/no-credential/malformed/parse-dont-validate/size-cap + planner own/foreign/no-access/self-primary/duplicate/fail-closed/case-insensitive), production build clean, keel validate + guard green."; }
        part composeRecipeFeatureDoDR1 : TestResult { :>> id = "a1c0e7d2-3b64-4e10-9c20-0a1b2c3d0d02"; :>> outcome = VerdictKind::pass; :>> judgedAgainst = "70915a3"; :>> judgedAt = "2026-08-17"; :>> judgedBy = "claudeOpus"; }
        // ===== provenance decoupling (2026-09-07) — governance/naming hygiene, chartered by D0046. =====
        action provenanceDecoupling;               // deletes the orphan upstream tags + retires the 'new-livesync' working name
        verification provenanceDecouplingDoD : Test { :>> id = "08c66d1c-7d72-4f69-974d-83fd3b4d13ca"; :>> method = VerificationMethod::test; :>> procedureText = "DONE (green @ c575ed4c): implements D0046 - decouple SelfSync's provenance from obsidian-livesync. The public repo reported 38 CONTRIBUTORS (owner read it as traction); it was not - 0 stars / 0 forks / 0 watchers / 0 PRs / 0 issues, fork=false, and `git shortlog -sne HEAD` = ONE human author (615 commits) plus two Claude trailer identities. The other ~35 were reachable ONLY via five orphan tags (0.1.0-0.5.0) sitting on the PRE-REWRITE history, an ancestry descending 1475-1497 commits to vrtmrz/obsidian-livesync's 2021-10-12 initial commit; main has been the clean 615-commit line since the squash at 98948a58, but the tags were never deleted and GitHub's contributor graph walks ALL refs incl. tags. Those tags were also the only thing still PUBLISHING upstream source from this repo (tag 0.5.0's tree carried upstream type stubs under obsolete/_types/ and had NO LICENSE at all). ACTION 1: deleted tags 0.1.0-0.5.0 from origin + locally - the full not-descended-from-root set; the owner's initial count was four, and rather than guess on an irreversible public-ref delete the AI surfaced the discrepancy and the owner selected all five (keeping 0.1.0 would have left the whole ancestry reachable, achieving nothing). `git shortlog -sne --all` now returns one author. ACTION 2: renamed the retired working name in BUILD IDENTIFIERS via a committed dry-run-default codemod (.engine/tools/migrations/2026-09-07-decouple-livesync-naming.py, D0067) over 115 sites / 25 files - new_livesync_server->selfsync_server, new-livesync-server->selfsync-server, new-livesync-client->selfsync-client, NewLiveSync->SelfSync (Plugin/Settings/SettingTab) - plus reviewed targeted edits to server/Dockerfile (the codemod's suffix filter missed it; the image build would have broken) and the live docs. Reconciliation gates all balanced: no-leak 146==146, per-rule conservation exact, and a name-masked content residue proving the codemod changed NOTHING but names. CRITICAL EXCLUSION: the bare legacy plugin id 'new-livesync' is NOT renamed - configsync.ts LEGACY_SELF_IDS uses it to exclude the FORMER plugin folder's data.json (this device's server URL + credentials) from config sync, so renaming it would reopen a credential-leak path; every codemod rule matches a strictly LONGER string so the bare id survives by construction, asserted by a post-check (36 -> 36). ACTION 3: README gained a 'Prior art' section stating SelfSync is an independent implementation sharing no code, dependencies, or storage format with obsidian-livesync, which is credited as the prior art that framed the problem. NO upstream MIT NOTICE was added and LICENSE is unchanged - deliberate: MIT's notice-retention duty attaches to copies of the covered work, and with the tags gone this repo contains none, so asserting a livesync copyright would state a derivation that does not exist. Independence was VERIFIED, not assumed: client deps are qrcode-generator alone (no pouchdb/couchdb/octagonal-wheels), the server is an independent Rust implementation (D0005), HEAD's tree carries no upstream source, and BOTH wire-signature.json artifacts contain zero crate-name references - so the crate rename moves no compatibility gate and forces NO redeploy. Dated plan docs under docs/design/plans/ kept their text (their claims are true for their dates); one OPEN issue's stale NewLiveSyncSettings symbol was updated so its refactor target stays actionable. NOT fixed here (out of scope, flagged): client/package.json is 1.22.0 vs manifest 1.30.0, and the NoteConflictModal performance defects that opened the session. DoD MET: server cargo test 234 passed / 0 failed + clippy -D warnings clean; client tsc clean, vitest 830 passed / 2 skipped - UNCHANGED from the 1.30.0 baseline, so the rename altered no behavior - production build clean; keel validate 14 files clean, keel guard ALL PASS. GATE CORRECTION (2026-09-07, same sitting): that keel verdict was produced by a STALE Jul-26-vintage keel binary that was on hand, not the current keel 0.3.1 on PATH which the pre-commit hook actually invokes. Under 0.3.1 this tree additionally reports FOUR pre-existing guard failures (viewpoint-renderer, tool-reference, sprint-closure, cli-surface-declared) plus 19 unread warnings, none caused by this change - tracked as issueEngineVintageGateDrift. The claim above is therefore true of the binary used and NOT of the current gate; the substantive verification (cargo/clippy/tsc/vitest/build) is unaffected and stands."; }
        // RAN: (cd server && cargo test) -> 234 passed / 0 failed, exit 0; (cd server && cargo clippy --all-targets -- -D warnings) -> exit 0, 0 warnings;
        // RAN: (cd client && npx tsc --noEmit) -> exit 0; (cd client && npm test) -> 830 passed / 2 skipped, exit 0; (cd client && npm run build) -> exit 0;
        // RAN: python .engine/tools/migrations/2026-09-07-decouple-livesync-naming.py . -> no-leak 146==146, per-rule conservation exact, name-masked residue identical, legacy id 36->36
        part provenanceDecouplingDoDR1 : TestResult { :>> id = "5c328aa1-e785-43ad-a934-1dda8902d602"; :>> outcome = VerdictKind::pass; :>> judgedAgainst = "c575ed4c"; :>> judgedAt = "2026-09-07"; :>> judgedBy = "claudeOpus"; }
        // ===== no-latent-debt dispositions (2026-09-07, project D0047) — defects surfaced in the =====
        // ===== provenance sitting, now fixed-with-guard or filed open rather than merely mentioned. =====
        action versionRecordDriftGuard;            // resolver for issueVersionRecordDrift
        verification versionRecordDriftGuardDoD : Test { :>> id = "f6085cf0-fc28-464e-af5e-99c28f08f6a4"; :>> method = VerificationMethod::test; :>> procedureText = "DONE (green @ HEAD): resolves issueVersionRecordDrift. client/package.json recorded 1.22.0 while manifest.json recorded 1.30.0 - EIGHT releases of undetected drift. ROOT CAUSE: scripts/bump-version.mjs updated package.json inside a bare try/catch wrapped around a String.replace whose NON-MATCH is a silent no-op, so the bump reported success while leaving that record behind; git history confirms package.json tracked correctly through 1.22.0 (commit e61df7ea) and then stopped. FIX, three parts: (1) the drifted record set to 1.30.0; (2) bump-version.mjs restructured to PREPARE all three edits BEFORE writing any of them and to HARD-FAIL if the package.json pattern does not match - so a future non-match aborts with nothing written instead of half-bumping (the previous shape could leave manifest+versions bumped and package.json behind, which is how the drift compounded); (3) a new scripts/check-version-sync.mjs asserts manifest.json / versions.json / client/package.json all AGREE (and that versions.json maps the current version to the manifest's minAppVersion), wired into .github/workflows/ci.yml as a `version-sync` job so agreement is checked on every push - engine D0047, because a careful writer is not a control. The guard was verified FAIL-FIRST, not merely green: drifting package.json to 1.29.0 made it exit 1 naming the mismatch, and restoring it returned exit 0. NOTE the pre-existing scripts/check-release.mjs checks manifest-vs-tag-vs-GitHub-release but never record AGREEMENT, which is precisely the hole this class came through. DoD MET: check-version-sync exit 0 at HEAD + exit 1 on injected drift; keel validate clean and keel 0.3.1 guard:evidence-cited PASS (the tree's four PRE-EXISTING 0.3.1 guard failures are tracked separately as issueEngineVintageGateDrift and are not caused by this change)."; }
        // RAN: node scripts/check-version-sync.mjs -> exit 0 (all three records agree on 1.30.0); injected-drift negative test -> exit 1
        part versionRecordDriftGuardDoDR1 : TestResult { :>> id = "efecce44-b346-4caf-a448-c50912bdbf28"; :>> outcome = VerdictKind::pass; :>> judgedAgainst = "5e01b211"; :>> judgedAt = "2026-09-07"; :>> judgedBy = "claudeOpus"; }
        action hooksInstall;                       // resolver for issueHooksNotInstalled
        verification hooksInstallDoD : Test { :>> id = "fc9c77a4-fef3-4f02-ab67-6ed34c1bcae0"; :>> method = VerificationMethod::inspect; :>> procedureText = "DONE (green @ HEAD): resolves issueHooksNotInstalled. NO git hook ran in this repo at all. A machine-global core.hooksPath (file:C:/Users/will/.gitconfig) pointed at ~/.githooks, which DOES NOT EXIST, and git silently runs no hooks when hooksPath is a missing directory - so the repo's own .githooks/pre-commit keel validate+guard GATE never fired either, not just the push. Worse, CLAUDE.md 4 asserted 'the post-commit hook pushes every commit', which was false: the commit before this one had to be pushed by hand, and there was no post-commit hook in the repo to begin with. FIX: (1) authored .githooks/post-commit - pushes origin main, refuses to push from a non-main branch, honors SKIP_PUSH=1, and is deliberately NON-FATAL (post-commit runs AFTER the commit is written, so a push failure must report loudly and leave the commit local rather than exit non-zero and imply the commit failed); (2) `git config core.hooksPath .githooks` set for this repo, which OVERRIDES the broken global; (3) both hooks made executable; (4) CLAUDE.md corrected - it now states the hooks are NOT active in a fresh clone and names the one-line enable command, since core.hooksPath is local config that no clone inherits. VERIFIED the gate can actually run: keel is on PATH at /c/Users/will/.local/bin/keel, so the pre-commit hook enforces rather than taking its 'keel not on PATH - gate skipped' branch. OUT OF SCOPE + reported to the owner, not fixed here: the machine-global core.hooksPath is still broken, so every OTHER repo on this machine remains hook-less; that is a workstation config fix, not a repo change. method=inspect is self-evidencing (D0051) - the hook files, the config value, and the CLAUDE.md text are the evidence."; }
        part hooksInstallDoDR1 : TestResult { :>> id = "f2bc8c26-36e2-469e-a87e-642c2e0e8671"; :>> outcome = VerdictKind::pass; :>> judgedAgainst = "5e01b211"; :>> judgedAt = "2026-09-07"; :>> judgedBy = "claudeOpus"; }
        // Re-implemented (owner's choice) — and the dead e2e layer restored in the process; see the DoD.
        action forkedE2eHelperProvenance;          // resolver for issueForkedE2eHelpersUnattributed
        verification forkedE2eHelperProvenanceDoD : Test { :>> id = "27d21487-ed0b-4575-b97f-8a18db394f31"; :>> method = VerificationMethod::test; :>> procedureText = "DONE (green @ HEAD): resolves issueForkedE2eHelpersUnattributed by RE-IMPLEMENTATION, the path the owner chose - and along the way found and fixed the reason the whole real-Obsidian e2e layer had been dead. THE REWRITE: client/e2e-obsidian/helpers/obsidian.ts and obsidianFunctions.ts (confirmed authored by vorotamoroz, 2026-05-11/14) are DELETED and replaced by obsidianDriver.ts and rendererFunctions.ts, written fresh against Playwright's connectOverCDP and Node's child_process/net/http primitives plus ws, with the same public API so the three specs changed only their import paths. Independence MEASURED against the upstream originals after normalising whitespace and comments: the driver shares 13 of 167 code lines, every one of them a preserved public signature (getMainWindow, waitForVaultReady, ObsidianHandle, firstWindow, close), a Playwright idiom (keyboard.press Escape, waitForLoadState, waitForSelector .workspace-ribbon) or a bare token (return;, try {); the renderer functions share 1 of 12, Obsidian's own type shape for enabledPlugins. The 'Ported from' claims are gone; both files state their provenance. Structural differences, not paraphrase: a class-based instance with static start; one generic bounded until() helper for every readiness wait; TCP-probe readiness; a bounded close() that waits for process EXIT and then for the PORT to be released; a bounded dialog-dismissal loop for first-open; renderer functions that reach app via globalThis and are each self-contained because page.evaluate ships source text and an outer-scope reference would ReferenceError in the renderer. THE LAYER WAS DEAD, and quality-first meant baselining BEFORE touching it: the existing (derived) helpers failed 3/3 with 'browserType.connectOverCDP: Protocol error (Browser.setDownloadBehavior): Browser context management is not supported'. First hypothesis - my earlier lockfile-less npm install had floated Playwright from ^1.61.1 to 1.63.0 - was TESTED and FALSIFIED: pinning 1.61.1 reproduced the identical failure. A probe against a real launch showed the installed Obsidian is 1.5.8 on Electron 28 / Chrome 120, whose Browser domain rejects setDownloadBehavior, and Playwright issues it unconditionally on attach - via the http endpoint, the browser websocket, AND a page websocket, all three failing identically. _electron.launch was tried too: 60s timeout, no window (confirming the original authors' note). FIX: the driver runs a tiny local WebSocket shim (CdpShim) between Playwright and Obsidian's browser socket that answers Browser.setDownloadBehavior with an empty success and forwards every other message untouched; a probe logged exactly ONE message shimmed with evaluate, selectors and role queries all working through it. ws is now an explicit devDependency (it was only transitive). A SECOND REAL DEFECT surfaced on the first green-ish run (2 of 3): smoke reported the plugin ENABLED but never LOADED after 30s. Not the renderer function - the passing convergence spec polls the same isPluginLoaded on both its instances. It was a PORT RACE: serial specs reuse port 19222, the previous instance's port can outlive its exit event, and a readiness probe that only asks 'is the port open?' happily attaches to a DYING Obsidian holding someone else's vault. Fixed three ways: a pre-flight wait for the port to be FREE before spawning (bounded, with a plain error naming the held port), close() waiting for the port to actually close, and a positive OWNERSHIP CHECK after attach - the renderer is asked which vault it has open (app.vault.adapter basePath) and a mismatch with the vault we launched is a hard error, never a silent test against the wrong instance. Smoke then went from a 30.7s timeout to a 3.0s pass. FINAL: 3 of 3 real-Obsidian specs PASS in 15.7s at Playwright 1.63.0 (the version a fresh install resolves), each of the two heavy specs launching TWO Obsidian instances and syncing through the real server. This was 0 of 3 before, at every Playwright version. DOC-SYNC: D0046's provenance correction said the README 'Prior art' wording was to be revisited under whichever path was chosen - the wording ('shares no code, no dependencies, and no storage format') now stands as FULLY true and is unchanged. NEW GUARD: tsconfig.e2e.json typechecks e2e-obsidian and e2e-admin, which the main tsconfig never included (include: src, test), so e2e code had never been typechecked at all; wired into ci.yml. Not a release - test tooling only, nothing ships to users. DoD MET: npx tsc -p tsconfig.e2e.json clean; main tsc clean; client vitest 882 passed / 2 skipped; production build clean; real-Obsidian e2e 3 passed; keel validate + guard + gate green."; }
        // RAN: (cd client && npm run test:obsidian-e2e) -> 3 passed (15.7s) at @playwright/test 1.63.0; baseline on the derived helpers was 3 failed (connectOverCDP Browser.setDownloadBehavior), also 3 failed pinned at 1.61.1
        // RAN: (cd client && npx tsc -p tsconfig.e2e.json) -> exit 0; (cd client && npx tsc --noEmit) -> exit 0; (cd client && npx vitest run) -> 882 passed / 2 skipped; (cd client && npm run build) -> exit 0
        // RAN: normalised-line overlap vs upstream originals: obsidianDriver.ts 13/167 (API signatures + Playwright idioms only), rendererFunctions.ts 1/12 (Obsidian type shape)
        part forkedE2eHelperProvenanceDoDR1 : TestResult { :>> id = "0e9158be-c897-41c8-a9cf-5a3892da4dc4"; :>> outcome = VerdictKind::pass; :>> judgedAgainst = "e39eeeab"; :>> judgedAt = "2026-09-07"; :>> judgedBy = "claudeOpus"; }
        // OPEN - both await an owner decision; no pass result yet, so orient lists them.
        action engineVintageResync;                // resolver for issueEngineVintageGateDrift
        verification engineVintageResyncDoD : Test { :>> id = "dcec57d6-d779-42a4-8bfa-4c0bc2762cc5"; :>> method = VerificationMethod::inspect; :>> procedureText = "OPEN: bring .engine/ up to the engine vintage of the keel binary that actually gates commits. The tree's .engine/ is a Jul-2026 vintage; the keel on PATH (and therefore the pre-commit hook) is keel 0.3.1 built 2026-09-03. Because NO hook was installed (issueHooksNotInstalled) AND CLAUDE.md documented the validator as a local Windows release-build path that does not exist in this repo, a 6-week-stale sibling build was run by hand instead - so this drift accumulated invisibly, and every recent 'keel guard ALL PASS' in the records was that stale binary's verdict, not the gate's. Under 0.3.1 the tree shows FOUR failing guards, none caused by the provenance work: (1) viewpoint-renderer, 9 violations - declared renderers name commands 0.3.1 does not expose (keel orphans, suspect, decisions, indicators, rootedness, tier-satisfaction, attestation-coverage, concern-coverage, critique-policy); NOTE CLAUDE.md section 1 documents all of these as available, so the doc surface is stale too and doc-sync rides this fix. (2) cli-surface-declared, 1 - .engine/cli/commands.sysml absent; the guard names keel migrate as the fix. (3) tool-reference, 1 - .engine/skills/engine-triage/SKILL.md line 27 references .engine/tools/triage_reminder.py, which does not exist, so a follower hits a dead path. (4) sprint-closure, 1 - tracked separately as issueMootedTaskUnstamped. Plus 19 unread warnings across viewpoint-renderer, manifest-coverage, verification-trace, parser-coverage, base-first-justification and control-event-coverage. A keel migrate --dry-run reports 481 .engine/ files / 481 edits / 0 blockers and touches NOTHING in .tracking/, client/, server/ or CLAUDE.md; it also lists 7 .engine/ files this binary does not ship (architecture-audit, code-critique, functional-decoupling, mutation-testing, property-based-testing, release-versioning processes + schema/core/risk.sysml) which it PRESERVES for manual review. DoD: owner-accepted engine resync (a 481-file process/schema-definition change, so section 3a/4 require acceptance + a co-committed Decision for the D0070 process-change keystone), then the residual violations fixed by hand (the dead triage_reminder.py reference; the viewpoint renderer command names reconciled against the real 0.3.1 surface, with CLAUDE.md section 1 corrected in the same commit), then keel guard green under the PATH binary and the 19 warnings read and either actioned or explicitly accepted. PROGRESS (project D0048, same sitting): NO LONGER BLOCKING. Three of the four were fixed ADDITIVELY without migrating - cli-surface-declared by adding .engine/cli/commands.sysml plus the .engine/schema/cli/cli.sysml defining its types (both NEW files, extracted from a scratch `keel init`, nothing overwritten); viewpoint-renderer by rewriting the 9 renderer strings to `keel show <lens>`, verified empirically rather than from help text; tool-reference by correcting the engine-triage skill's claim that a UserPromptSubmit hook fires (it does not exist - sprint30). sprint-closure was resolved separately via issueMootedTaskUnstamped. A pre-existing VerificationMethod::analyze typo in D0040 surfaced once the CLI schema resolved and was fixed. keel validate / guard / check-engine are now ALL 0 by exit code. WHAT REMAINS for this task: the wholesale 481-file `keel migrate` resync, DEFERRED because attempting it REGRESSED the tree - it overwrote .engine/schema/core/relationships.sysml with the stock copy, cutting 25 metadata def declarations to 18 and deleting the 7 markers D0045 deliberately added, which took keel validate from pass to fail and marker-vocabulary from 0 to 228 violations (attribute-vocabulary 0 to 1216). It was rolled back cleanly (nothing committed). DoD for the remaining work: re-apply D0045's marker declarations and the attribute-vocabulary declarations ON TOP of the resync, prove both guards still green, read the 19 non-blocking warnings and either action or explicitly accept each, and carry upstream the observation that `keel migrate --dry-run` reported 0 blockers for a change that silently deleted a project decision's effect. PROGRESS 2 (2026-09-07, same sitting, owner: 'continue through entire backlog. quality first'): the wholesale resync is APPLIED under a committed transform (.engine/tools/migrations/2026-09-07-engine-vintage-resync.py) and recorded as project D0050 (PROPOSED). Route: `keel migrate .` to the 0.3.1 stock tree; project-owned engine files restored from HEAD (skills-registry, schema/codeaudit/codeelement.sysml, contracts/reverify.toml, deliverable-manifest.txt); D0045's 11 markers re-added BY NAME to relationships.sysml (idempotent script) and each given the D0139(B) `doc` justification; the 8 project-only skills moved verbatim (same ids) into per-skill registry.sysml files (D0222) and the shared registry taken stock; the 6 project-only processes re-expressed in the vintage's shape (`action` usages, `first X then Y` successions replacing `:>> order`, an `// APPLIES-WHEN:` condition each); the 74 nested #Covers edges hoisted to package level so they parse (issueNestedCoversEdgesSkipped). CONTROL TOTALS: markers - D0045's 11 project declarations re-added by name, then `Changes` retired as dead (0 AST edges, 0 prose uses), so 17 engine + 10 project = 27 declared, each project marker carrying its D0139(B) doc justification; AISkill registrations 35 -> 52 (27 stock per-skill + 8 project + new stock skills), no id lost (duplicate-identity 0 after the move); viewpoints 20 -> 32; engine files 260 -> 559 (incl. D0050 + the transform); parser-coverage skipped 81 -> 7 (= stock baseline); #Covers AST edges 0 -> 74. GATES under the PATH keel 0.3.1: validate 0, check-engine 0, guard ALL PASS by exit code. WARNINGS READ (90 at first green): verification-trace 4 -> typed #Verify edges authored; manifest-coverage 2 -> two tasks added to the manifest and re-verified; base-first-justification 5 -> doc justifications on every project marker; parser-coverage -> resolved by the hoist, baseline back to 7; viewpoint-renderer 2 -> honest 'planned' viewpoints (baselines, requirements), accepted as-is; decision-scaffolding 73 + control-defect-registry 2 -> ENGINE reference decisions d0173-d0294 and engine-held issues 331/333, not this project's to fix, carried upstream. WHAT REMAINS FOR A PASS: the owner's `keel accept d0050` (the DoD's first clause is owner acceptance of the resync). Nothing else is outstanding. Resolves issueEngineVintageGateDrift."; }
        // RAN: The DoD's first clause - owner acceptance of the resync - is met: the 0.3.1 resync record (superseded by its eight clause records d0066..d0073) was accepted by the owner on 2026-09-13 from the decision page ('[x] Accept all 34 clause records'), and the follow-on 0.4.1 resync (d0057) was accepted the same day ('[x] Ratify the update as applied'). RAN earlier and recorded in the DoD: keel validate / check-engine / guard green under the PATH binary after the resync; the transform committed; the warnings read. Resolves issueEngineVintageGateDrift.
        part engineVintageResyncDoDR1 : TestResult { :>> id = "12a935d9-723b-4088-aca4-2d5cd38a65a7"; :>> outcome = VerdictKind::proposed; :>> judgedAgainst = "d7fc5711"; :>> judgedAt = "2026-09-13"; :>> judgedBy = "claudeOpus"; }
        action mootedTaskStamp;                    // resolver for issueMootedTaskUnstamped
        verification mootedTaskStampDoD : Test { :>> id = "6a230d4b-7472-4193-820c-d30fa9acb8ab"; :>> method = VerificationMethod::inspect; :>> procedureText = "DONE (green @ HEAD): resolves issueMootedTaskUnstamped. The owner rejected the framing outright - 'why are we making moot tasks at all? i don't get it. if it's important, we need verification.' - which is correct, and none of the three options offered (stamp inconclusive / delete / extend VerdictKind) was taken as posed. We do not create moot tasks deliberately: embeddedTimestampHardening was a genuinely planned task whose SUBJECT was deleted under it by timestampIgnoreRedesign (1.9.0), which retired the whole 'SelfSync owns created/updated' model. So the real question is not how to stamp a zombie but whether its concerns survived - and that was CHECKED rather than assumed. Item by item: F9 (a manual edit of a managed created/updated is honored, not reverted every sync) DISSOLVED - the revert existed only because SelfSync owned and restored those fields, and there are no managed fields now. F14 (formatIsoOffset labels a historical stamp DST-correctly) and F15 (the >1 MiB re-stamp churn-killer) DISSOLVED - verified by grep: formatIsoOffset, fstimes.ts and timestampBackfill.ts are all gone from client/src and client/test, leaving only a settings-key cleanup in settings.ts. F12 SURVIVED: it concerns the (size,mtime) scan-skip missing a body-only change from an mtime-preserving tool, which was never specific to timestamp ownership, and that skip is very much alive (reconcile.ts baseStatUnchanged plus the reconcileAll fast path). RESOLUTION: the zombie action + DoD are DELETED (no TestResult existed, so no attestation is destroyed; issueTimestampHardeningFollowups already resolves from timestampIgnoreRedesign, not from this task, so no typed edge breaks), and the surviving F12 concern is filed as its own Issue (issueScanSkipMtimePreservedBlindspot) so it is carried by the model instead of by a dead task's prose. The comment that folded a real-Obsidian backfill e2e into this task is corrected too: that gap dissolved with the backfill. method=inspect is self-evidencing (D0051) - the greps, the surviving call sites and the edge check are the evidence."; }
        // RAN: grep -rn "formatIsoOffset|fstimes|timestampBackfill" client/src client/test -> only a settings-key cleanup remains (F14/F15 dissolved);
        // RAN: grep -n "baseStatUnchanged" client/src/reconcile.ts -> live at :446 and :1160 (F12 survives); grep "#Resolves .* issueTimestampHardeningFollowups" -> resolves from timestampIgnoreRedesign, not the deleted task
        part mootedTaskStampDoDR1 : TestResult { :>> id = "608d5052-92c9-4880-9650-848c2c9467b7"; :>> outcome = VerdictKind::pass; :>> judgedAgainst = "5e01b211"; :>> judgedAt = "2026-09-07"; :>> judgedBy = "claudeOpus"; }
        // Test half DONE; awaits the owner's acceptRisk attestation (see acceptance.sysml scanSkipResidualAccept).
        action scanSkipBoundaryPin;                // resolver for issueScanSkipMtimePreservedBlindspot
        verification scanSkipBoundaryPinDoD : Test { :>> id = "b7c41e02-5a6d-4f18-9c33-2e5a71d09f44"; :>> method = VerificationMethod::test; :>> procedureText = "PART 1 DONE, PART 2 AWAITING HUMAN ATTESTATION. (1) THE BOUNDARY IS PINNED by four reconcile tests written against the real reconcileAll (not a stub): a same-size AND same-mtime out-of-band body change IS skipped - the accepted residual, stated exactly; the hole is exactly the stat gate - once mtime moves the same change is pushed; a scan-hit can NEVER become delete-local - with the remote deleted and a stale-stat local EDIT, the rmeta-present gate forces a real read, the hash differs, and edit-wins-keep-local preserves the edit; and the control - remote deleted with local genuinely unchanged - does delete locally, so the guard is shown to be the difference and not a blanket refusal. TWO HARNESS FACTS learned the honest way (each first produced a wrong-reason result and was corrected, not papered over): the (size,mtime) stamp is recorded only when a pass READS and CONFIRMS equality, so a freshly pulled file is re-hashed once before it is ever skipped - the seed needed a confirming second pass; and reconcileAll takes a note's stat from io.list() - the adapter's own stat, as in production - not from deps.statOf, which is reconcilePath's single-file source, so the test drives mtime through list(). (2) THE TYPED DISPOSITION: the acceptance of this residual is now stated in the model as a method=confirmation Test carrying disposition = DispositionKind::acceptRisk, authored as scanSkipResidualAccept in .tracking/verification/acceptance.sysml. Its #Dispositions edge to the finding is WITHHELD until attestation, because keel 0.3.1 treats the bare edge as closure even with no verdict recorded and had hidden this open issue (issueUnattestedDispositionClosesFinding). Its TestResult is deliberately NOT recorded: an acceptRisk is a HUMAN judgment and CLAUDE.md 3c forbids inferring a confirmation from 'continue' or from the work being done - it is recorded only on the owner's explicit word on THIS claim. Until then the issue stays open, truthfully. Client-only test change; no behaviour change. Part 1 verified: tsc clean; reconcile.test.ts 150 passed; full client vitest green; build clean. Resolves issueScanSkipMtimePreservedBlindspot."; }
        // RAN: scanSkipBoundaryPinDoD judged 2026-11-11 at 475ef54. Part 1 as in R1: the four reconcile tests pin the boundary, reconcile.test.ts green in the client suite at b9d6cda. Part 2: the owner attested the acceptRisk disposition on 2026-11-11 (Statement st021), recorded as scanSkipResidualAcceptR1 judged by wweatherholtz. The #Dispositions edge to issueScanSkipMtimePreservedBlindspot is authored in the same commit. keel show open-issues no longer lists the issue, open count 10. Verdict PASS.
        part scanSkipBoundaryPinDoDR1 : TestResult { :>> id = "2edc41bd-56bf-4201-972c-832cb2155cde"; :>> outcome = VerdictKind::pass; :>> judgedAgainst = "475ef54"; :>> judgedAt = "2026-11-11"; :>> judgedBy = "ai"; }
        // RAN: (cd client && npx vitest run test/reconcile.test.ts) -> 150 passed incl. the 4 scan-skip boundary cases; (cd client && npx tsc --noEmit) -> exit 0
        // ===== conflict-modal performance + honesty (2026-09-07) — owner field report. =====
        action conflictModalPerf;
        verification conflictModalPerfDoD : Test { :>> id = "e0347b7f-6b0a-4ec9-87d1-0863c48fde72"; :>> method = VerificationMethod::test; :>> procedureText = "DONE (green @ HEAD): fixes the owner-reported conflict-modal report - 'resolve conflicts is extremely slow, claims things have changed since i last opened the file which i haven't done, doesn't seem to ignore metadata timestamp fields like it should in the diff view, and takes forever to apply'. All four complaints traced to distinct defects; each was MEASURED or reproduced by a failing test before the fix, and each carries a permanent guard (engine D0047). (1) issueConflictDiffQuadratic - unifiedLineDiff called lcsPairs, an O(n*m) DP over a NESTED number matrix, on whole notes with NO size bound; merge3 already had MAX_MERGE_LINES for exactly this, the diff view had nothing. MEASURED on a fast desktop for notes differing by ONE line: 200 lines 3ms, 4k 447ms, 6k 1.06s, 8k 1.96s, 12k 4.5s - on the UI thread, on modal open AND again after every resolve, and several times worse on mobile. FIX: strip the common prefix/suffix first (they are context under any alignment, so the emitted diff is IDENTICAL and a one-line edit in a 12k-line note collapses to a 1x1 problem), then cap the remaining cells at MAX_DIFF_CELLS=2,000,000 and, above it, report the whole region as changed rather than allocating the matrix - the same fall-back-to-conflict escape merge3 takes. 12k-line case went 3922ms -> under 250ms (the whole merge.test.ts file now runs in 16ms). (2) issueStalePreviewFalsePositive - the 'that file changed since you opened this' refusal that the owner had NOT caused. TWO causes, both in the stale-preview guard's use of readTextOrEmpty, which returns an empty string on ANY read failure: a transient Windows lock read as a rewritten file, and the comparison was on RAW decoded text while the modal's own diff normalizes EOL - so a CRLF rewrite, or an ignored `updated:`/`modified:` frontmatter bump by another plugin (or an engine re-write on the 4s safety-net poll while the modal sat open), blocked the apply over a difference the user was never shown. FIX: a new previewStillCurrent returns match/changed/unreadable, judging on CONTENT IDENTITY via normalizedContent (EOL/BOM normalized, ignored timestamp keys masked) - the SAME basis the sync engine uses - and a read failure now says 'couldn't read X just now (it may be locked)' instead of blaming a change. A REAL body change still refuses (tested). (3) issueConflictDiffShowsIgnoredTimestamps - the diff rendered RAW text, so a frontmatter key the user told SelfSync to IGNORE, and which the engine treats as no change at all, still drew a red/green changed line: the modal contradicting its own setting. FIX: renderDiff takes the path's ignore patterns (a new plugin.ignorePatternsForPath mirroring reconcile's private ignorePatternsFor gating - feature on, .md, not .obsidian/ config, not an excluded folder) and diffs normalizedContent of both sides, so those lines are neither a change nor shown as context; the no-changes message names them. (4) issueConflictModalSerialScan - the 'extremely slow' open. The cosmetic auto-dismiss sweep ran BEFORE the first render: 2N STRICTLY SEQUENTIAL disk reads plus FOUR full UTF-8 decodes per file (isMergeable twice, then sameIgnoringEol decoding both again) behind a 'Checking conflicts...' placeholder - so the modal took ~2N round-trips to show anything, even though it only ever displays ONE conflict. FIX: render FIRST (real content after ~2 reads, not ~2N), then sweep in the background and redraw only if something was dismissed; the free extension gate (new isTextExt, extracted from isMergeable so the text-extension list keeps one home) runs BEFORE any read so a binary attachment costs ZERO IO; each side is decoded ONCE via a strict fatal decode (a binary can still never be compared as text - critique F1 holds); and the reads run at concurrency 8 instead of serially. (5) issueConflictResolveRepaintsPerFile - 'takes forever to apply'. resolveNoteConflict ended with settingsRefresh + statusListener FIRED IMMEDIATELY, and the settings tab's re-render re-derives the conflict list from vault.getFiles() over the whole vault. Since the sweep calls resolve once PER FILE, clearing 200 false conflicts did 200 full settings repaints plus 200 whole-vault scans. FIX: a coalesced requestUiRefresh (50ms trailing, cleared on unload so no timer leaks). (6) issueConflictModalDoubleApply - render() was fired UNAWAITED and nothing blocked re-entry, so a double-tap on an IRREVERSIBLE either-side choice could enter resolve() twice, the second racing a half-applied first. FIX: a busy flag guards resolve + merge, the body dims while an apply is in flight (honest feedback rather than live-looking buttons that do nothing), and an open_ flag stops the background sweep and any render after the modal closes, instead of reading files and writing into a detached contentEl. Client-only -> PLUGIN release; NO server change, NO redeploy. DoD MET: tsc --noEmit clean; full client vitest 842 passed / 2 skipped (was 830 - 12 new tests: 3 diff perf/correctness guards, 4 stale-preview guards incl. a read-failure and a still-refuses-a-real-change case, 5 modal DOM guards incl. render-before-sweep, zero-IO-for-binary, double-tap-applies-once and the two timestamp-masking cases); production build clean."; }
        // RAN: (cd client && npx tsc --noEmit) -> exit 0; (cd client && npx vitest run) -> 842 passed / 2 skipped, exit 0;
        // RAN: (cd client && npm run build) -> exit 0; measured pre-fix diff cost 12k lines = 3922ms, post-fix < 250ms (guard asserts it)
        part conflictModalPerfDoDR1 : TestResult { :>> id = "365eea1f-3c27-41db-bc5d-8297968d3186"; :>> outcome = VerdictKind::pass; :>> judgedAgainst = "f8e83508"; :>> judgedAt = "2026-09-07"; :>> judgedBy = "claudeOpus"; }
        action settingsPluginWalkCache;            // resolver for issueSettingsRepaintWalksEveryPluginFolder
        verification settingsPluginWalkCacheDoD : Test { :>> id = "de077ce3-238e-4efb-a574-4ba23dd27057"; :>> method = VerificationMethod::test; :>> procedureText = "DONE (green @ HEAD): resolves issueSettingsRepaintWalksEveryPluginFolder - the defect that actually explains the owner's report, found only because they pushed back on the first explanation ('the diffs i was seeing were only on ~100 line files, but still took > 6 seconds'). That falsified the quadratic-diff story for THEIR case: at ~100 lines the diff is about 3ms measured, so it cannot produce 6 seconds. ROOT CAUSE: settings.ts renderPluginChecklist called pluginSyncClean(id) for every synced plugin on every render unconditionally - even immediately after applying the cached answer - and pluginSyncClean runs walkConfigTree, a RECURSIVE adapter.list/stat walk of .obsidian/plugins/<id>. resolveNoteConflict ends by calling settingsRefresh (a full display()), so ONE 'Keep this device's' click cost one filesystem walk per synced plugin; ~10 plugins on Windows with antivirus, or a cloud-synced vault needing placeholder hydration, is seconds. FIX (client-only, settings.ts): walk only when the convergence answer is NOT cached. The cache was already designed to be invalidated where it matters - deleted per-plugin after a push/pull changes convergence (line ~955), cleared wholesale on hide() so re-opening re-checks - so this removes redundant work rather than introducing new staleness, and the staleness that remains errs safe (a live button is a guarded no-op via the act() guard, never a wrong action). IMPORTANT SCOPE NOTE recorded honestly: the earlier coalescing fix (issueConflictResolveRepaintsPerFile) collapses N repaints into one and therefore only ever helped the BATCH sweep - it would NOT have fixed a single click, so without this change the owner's actual symptom would have survived the release. Guarded FAIL-FIRST: a new settings-ui DOM test renders the tab three times with two synced plugins and asserts the walk count stays at 2; against the pre-fix code it saw 6. DoD MET: tsc --noEmit clean; full client vitest 844 passed / 2 skipped (was 842); production build clean; keel validate + guard + check-engine + gate green."; }
        // RAN: (cd client && npx vitest run test/settings-ui.dom.test.ts) -> 26 passed; pre-fix the new guard failed with 'expected 6 to be 2'
        // RAN: (cd client && npx tsc --noEmit) -> exit 0; (cd client && npx vitest run) -> 844 passed / 2 skipped, exit 0; (cd client && npm run build) -> exit 0
        part settingsPluginWalkCacheDoDR1 : TestResult { :>> id = "c6a016cc-afb5-4042-9830-9aecf33e0682"; :>> outcome = VerdictKind::pass; :>> judgedAgainst = "2381bc18"; :>> judgedAt = "2026-09-07"; :>> judgedBy = "claudeOpus"; }
        action conflictPerfHarness;                // real perf test + the improvement it revealed
        verification conflictPerfHarnessDoD : Test { :>> id = "ce43cd34-f73b-4ee5-a463-dbc73a4adf3c"; :>> method = VerificationMethod::test; :>> procedureText = "DONE (green @ HEAD): builds a REAL performance test for the Resolve-conflicts path and iterates the implementation against it until the numbers are good, per the owner's instruction to 'make a real test and improve implementations until performance is great'. WHY A REAL ONE: the existing stub tests could prove ordering ('render does not await the sweep') but not COST, and the whole defect class was about IO COUNT under slow storage - so a stub could never have caught it. New client/perf/conflicts.perf.ts (vitest.perf.config.ts, excluded from npm test) drives the REAL NoteConflictModal, real walkConfigTree and real unifiedLineDiff against the REAL filesystem in temp vaults, with a per-read LATENCY INJECTION that models the environments where this actually hurt: antivirus on every open (Windows) or a cloud-synced vault hydrating placeholders. TWO HARNESS BUGS WERE FOUND AND FIXED IN THE TEST ITSELF before its numbers could be trusted, both of which had made the code look fine: (a) it waited on the modal's HEADER text, but render() writes the header BEFORE awaiting its two file reads, so it was timing the header rather than a usable modal - the criterion is now the presence of the choice buttons, i.e. the state a user can act on; (b) the fake IO wrapped SYNCHRONOUS readFileSync in async, so there was no real latency and the entire background sweep drained inside a single setTimeout(0), making 'reads before paint' meaningless - it now uses fs/promises. MEASURED RESULTS (dev SSD): time-to-usable is FLAT in the conflict count - 10.5ms at n=1 and 13.9ms at n=300; at an injected 10ms/read (the reported scenario) 18.7ms at n=1, 15.8ms at n=50, 34.5ms at n=300, against the ~6,000ms of reads the OLD pre-render sweep ordering required at n=300, which is exactly the owner's '>6 seconds' on ~100-line notes. The diff costs 0.07ms at 100 lines (confirming it was never their bottleneck), 0.27ms at 1k and 2.50ms at 10k (was 4,500ms). deriveNoteConflicts over 5,000 vault paths is 0.71ms, cheap enough per render. The APPLY bottleneck is quantified separately: one settings re-render walks every synced plugin, costing ~4ms at 0 latency but ~300ms across 10 plugins once stat has any latency - per click - and the convergence cache reduces that to ZERO. IMPLEMENTATION IMPROVEMENT the harness then revealed (issueConflictRenderSerialReads): render() awaited its two reads SEQUENTIALLY, and they are the only two between opening the modal and it being usable, so slow storage paid double for nothing. Now Promise.all - time-to-usable at 10ms/read halved (38.3 -> 18.7ms at n=1, 45.1 -> 34.5ms at n=300) and the end-to-end apply went from a 47.0ms median / 62.6ms worst to 30.9ms / 31.8ms. Thresholds are asserted with roughly 4x headroom for slower CI machines while still failing hard if the 2N-reads-before-usable ordering ever returns (that would be seconds, not milliseconds). One honest caveat recorded in-file: setTimeout resolution on Windows is coarse (~1-15ms), so the 2ms and 10ms stat rows are not distinguishable and must be read as a single modest-latency data point, not a curve. Client-only -> PLUGIN release. DoD MET: tsc --noEmit clean; full client vitest 844 passed / 2 skipped; the 7 perf assertions pass; production build clean; keel validate + guard + check-engine + gate --workspace all green."; }
        // RAN: (cd client && npx vitest run --config vitest.perf.config.ts perf/conflicts.perf.ts) -> 7 passed, exit 0
        // RAN: (cd client && npx tsc --noEmit) -> exit 0; (cd client && npx vitest run) -> 844 passed / 2 skipped, exit 0; (cd client && npm run build) -> exit 0
        part conflictPerfHarnessDoDR1 : TestResult { :>> id = "ef7e5634-4e9b-416d-b9b0-4304678be641"; :>> outcome = VerdictKind::pass; :>> judgedAgainst = "47b9f03a"; :>> judgedAt = "2026-09-07"; :>> judgedBy = "claudeOpus"; }
        action conflictDiffInvisibleReveal;        // resolver for issueConflictDiffInvisibleChars
        verification conflictDiffInvisibleRevealDoD : Test { :>> id = "96b5d8ac-d533-43bc-a2c4-48540bdcdc90"; :>> method = VerificationMethod::test; :>> procedureText = "DONE (green @ HEAD): resolves issueConflictDiffInvisibleChars. OWNER REPORT: the conflict diff showed a lot of 'pseudo changes' - a '- tagNames:' / '+ tagNames:' pair of VISUALLY IDENTICAL lines - and the owner asked whether it was an encoding or CR/NL problem, reasoning that a good diff should be line-return agnostic. INVESTIGATED rather than assumed, and the premise was half right. Line endings were ALREADY agnostic and are not the cause: a probe over unifiedLineDiff shows CRLF vs LF, a lone CR, and trailing blank lines all produce ZERO changed lines (now pinned by a test). What DOES surface as a visually-identical -/+ pair is a character you cannot see: a trailing space or tab, a tab-vs-spaces indent, a non-breaking space (U+00A0, which renders exactly like a space), a zero-width space/joiner or BOM, or NFC-vs-NFD Unicode. For the owner's ASCII 'tagNames:' the cause is whitespace or an invisible char, not Unicode. DESIGN DECISION - reveal, never hide: these are NOT ignored, because in Markdown two trailing spaces are a HARD LINE BREAK, a tab is not four spaces inside a code block, and U+00A0 is not U+0020, so folding them together would hide a real edit and could silently discard the user's version on an irreversible either-side choice. FIX (client-only, noteconflict.ts): a new exported revealInvisible marks the invisibles on CHANGED lines only - trailing spaces as middle dots, tab as an arrow, NBSP as a shouldered open box, zero-width/BOM as an empty set - leaving unchanged CONTEXT lines clean so a normal diff is not peppered with markers; and a new exported invisibleOnlyDifference detects the case where every changed line is identical once invisibles are folded (NBSP and tabs to spaces, zero-width stripped, trailing whitespace trimmed, NFC-normalised) and drives an explanatory line above the diff telling the user the versions look identical, naming each marker, and saying WHY the difference is kept. Tab-vs-spaces indent is deliberately NOT classed as invisible-only: it changes indent WIDTH, which is semantic in Markdown (list nesting, code blocks), so the arrow marker explains it but the modal does not claim the versions are indistinguishable. PROCESS NOTE worth recording: writing these tests took several attempts because pasted invisible literals were silently mangled by shell heredoc escaping - twice producing a test that passed for the wrong reason (both sides of an NBSP comparison ended up as plain spaces, so 'nothing changed' read as a pass) and once corrupting the test file outright, which was restored from git. Every invisible character in the new tests is therefore written as an explicit \\uXXXX escape, and the source regexes too, so no future edit can silently rot them. Client-only -> PLUGIN release; no server change, no redeploy. DoD MET: tsc --noEmit clean; full client vitest 854 passed / 2 skipped (was 844 - 10 new: 7 in a new test/invisible-diff.test.ts covering EOL-agnosticism, trailing-space-is-real, the markers, ordinary-text-untouched, the invisible-only predicate both ways, and NFC/NFD; plus 3 modal DOM tests asserting the explanation appears, the markers render, and an ORDINARY diff gets no markers); the 7 real-filesystem perf assertions still pass; production build clean; keel validate + guard + check-engine + gate --workspace all green."; }
        // RAN: (cd client && npx vitest run test/invisible-diff.test.ts) -> 7 passed; (cd client && npx vitest run test/modals-ui.dom.test.ts) -> 24 passed
        // RAN: (cd client && npx tsc --noEmit) -> exit 0; (cd client && npx vitest run) -> 854 passed / 2 skipped, exit 0; (cd client && npm run build) -> exit 0
        part conflictDiffInvisibleRevealDoDR1 : TestResult { :>> id = "73267e7d-55be-4a62-96f5-1a8bfba6ffb6"; :>> outcome = VerdictKind::pass; :>> judgedAgainst = "02b297b0"; :>> judgedAt = "2026-09-07"; :>> judgedBy = "claudeOpus"; }
        // OPEN - content identity does not Unicode-normalise; needs its own pass (hash migration).
        action contentIdentityUnicodeNormalise;    // resolver for issueContentIdentityNotUnicodeNormalised
        verification contentIdentityUnicodeNormaliseDoD : Test { :>> id = "2b2330fa-f9f9-4c55-8d3b-704d59ba5b45"; :>> method = VerificationMethod::test; :>> procedureText = "DONE 1.30.6 @a2bba145 (settled: normalise-on-COMPARE; no migration needed). normalizedContent - THE content-identity primitive in client/src/frontmatter.ts - now NFC-normalises the text, so NFC and NFD spellings of canonically-equivalent content are one identity and a macOS/Windows vault no longer generates phantom conflict copies for non-ASCII notes nobody edited. User files are never rewritten (normalise-on-WRITE rejected: SelfSync does not rewrite content). The migration question dissolved rather than being solved: the persisted normHash field was REMOVED (base.ts strips a legacy value on load and never re-persists it; reconcile.ts always recomputes identity from text), so there is no stored hash to shift, grandfather or restamp - normHashDecide records that decision. Cost: String.prototype.normalize on identity computation only; the conflict-modal perf harness (perf/conflicts.perf.ts) stayed within budget. Tests (content-identity.test.ts): NFC and NFD forms of the same text are the SAME identity; genuinely different accented text is still different; legacy normHash stripped on load and the entry type has no cached-hash field. ORIGINAL PROBLEM (kept for the record): decide and implement Unicode normalisation for note CONTENT identity. normalizedContent / normalizedHash compare NFC and NFD forms of canonically-equivalent text as different, so a vault spanning macOS (historically NFD) and Windows/Android (NFC) can generate phantom conflict copies for non-ASCII notes nobody edited. DoD must settle: normalise-on-COMPARE (cheap, no rewrite of the user files, but every stored normHash shifts and needs a migration or a grandfather rule) versus normalise-on-WRITE (fixes it at the source but rewrites user content, which SelfSync otherwise never does); the base-hash migration path either way; mobile cost of normalising large notes on every identity computation; and a test using real NFD content rather than a synthetic string. Until then the conflict UI at least states that the two versions are visually identical (invisibleOnlyDifference NFC-folds), so the symptom is explicable. Resolves issueContentIdentityNotUnicodeNormalised."; }
        // RAN: RAN: cd client && npx vitest run - Test Files 53 passed | 1 skipped (54); Tests 882 passed | 2 skipped (884); Duration 90.35s; at 4a991a54 (2026-09-07 18:51). content-identity.test.ts green: NFC/NFD same identity, owner's real meeting.md conflict identity-equal, body trailing space preserved, legacy normHash stripped.
        part contentIdentityUnicodeNormaliseDoDR1 : TestResult { :>> id = "039f99bc-7d74-496b-a890-1e7b6c265d1d"; :>> outcome = VerdictKind::pass; :>> judgedAgainst = "4a991a54"; :>> judgedAt = "2026-09-07"; :>> judgedBy = "claudeOpus"; }
        action conflictCopyAndLoadSweep;          // copyable diff + load-time converged-conflict sweep
        verification conflictCopyAndLoadSweepDoD : Test { :>> id = "3ac33193-104a-4461-82f9-9ba4be4c898f"; :>> method = VerificationMethod::test; :>> procedureText = "DONE (green @ HEAD): two owner asks, one of them a question that turned out to name a real defect. ASK 1 - 'let the Resolve conflicts modal let me copy text so we can fix it explicitly'. The diff pre had no user-select:text, while the LOG modal's pre (main.ts) has had it plus a Copy button all along - so the conflict text was unselectable and there was no way to get at it. FIX: user-select:text + cursor:text on the diff pre, and a 'Copy both versions' button placed FIRST among the actions (reaching for the text must never require committing to a side) that puts a plain-text report on the clipboard - the path, the marked-up diff with its marker legend, then BOTH versions VERBATIM. Verbatim, not the normalized/timestamp-masked forms the diff renders, because the point is repairing the real file. Deliberately not truncated. Falls back to a notice telling the user to select manually if the clipboard is unavailable (older mobile webview / permissions), rather than failing silently. ASK 2 - 'i'm not sure if refreshing the plugin autoresolves as much as it can and this is a genuine outstanding issue, or if it was just flagged and isn't being reanalyzed on a plugin update as it should. which is it?' ANSWER, from the code: BOTH halves, and neither is what it looks like. It is NOT a stale flag - a note conflict is DERIVED from a conflict-copy FILE on disk (listNoteConflicts recomputes from vault.getFiles() every call, D-conflict-model), so the count can never drift from reality. BUT refreshing the plugin auto-resolved NOTHING: grep confirms the cosmetic sweep was called from exactly one place, the modal's run(), and nothing - not onload, not reconcile - ever re-examined an existing conflict copy. So a conflict that had since CONVERGED (identical content, or differing only in line endings or ignored timestamp keys) sat in the count indefinitely and then vanished the moment someone opened the modal - which reads exactly like a stale flag being cleared, even though it never was one. The owner's suspicion was right about the symptom and the mechanism was the opposite of a cache. FIX (issueCosmeticConflictsNotSweptOnLoad): the sweep MOVED from the modal to the plugin as dismissCosmeticConflicts(shouldContinue) - it was never a UI concern - and onLayoutReady now runs it once per load, fire-and-forget, failure-tolerant, logging a notice when it clears anything. Deleting a copy is safe BY CONSTRUCTION there: it only happens when content identity says the two sides are the same, so nothing authored is lost, and binary/invalid-UTF-8 pairs are excluded by the extension gate BEFORE any read (a lossy decode can make two DIFFERENT binaries compare equal - critique F1). The modal delegates and passes its open_ flag as the continue predicate, so closing it stops the background work. A REAL BUG WAS INTRODUCED AND CAUGHT BY THE FULL SUITE: run() had one try/catch around render() AND the sweep, so a sweep failure wiped an already-drawn conflict and replaced it with 'Couldn't load conflicts'. The sweep is background work the user never asked for; its failure must not destroy the UI they are waiting on. Now caught separately, with a test that throws from the sweep and asserts the rendered conflict survives. THREE TESTS THAT PASSED FOR THE WRONG REASON were found and fixed while doing this, all the same failure mode - asserting against a path the code no longer takes: (a) two modal tests stubbed readBytesOrNull to prove reads-before-paint and zero-IO-for-binary, but the sweep had moved to the plugin so the modal never calls it - the properties were re-tested against the REAL plugin io and the vacuous modal versions deleted; (b) the new plugin-level fixtures used names like 'x (conflict).md', which match the real conflict-copy scheme NOWHERE (base.ts wants '<stem> (conflict <device> <14-digit UTC ts>[-tag])<ext>'), so they derived ZERO conflicts and two tests passed on empty input. Fixture names corrected, and a sanity test now asserts the fixtures ARE recognised as conflict copies - including that the old shape is NOT - so this class cannot silently return. The plugin-wiring harness also gained a vault.getFiles() projected from its in-memory io, so conflict DERIVATION is exercised for real rather than stubbed. Client-only -> PLUGIN release; no server change, no redeploy. DoD MET: tsc --noEmit clean; full client vitest 858 passed / 2 skipped (was 854 - net +4 after deleting 2 vacuous tests and adding 6: the fixture-name sanity guard, converged-vs-genuinely-different, EOL-and-timestamp-only convergence, binary-never-compared-with-zero-reads, stale-entry-skipped, and the failing-sweep-does-not-wipe-the-modal case); the 7 real-filesystem perf assertions still pass; production build clean; keel validate + guard + check-engine + gate --workspace all green. Resolves issueConflictDiffNotCopyable."; }
        // RAN: (cd client && npx tsc --noEmit) -> exit 0; (cd client && npx vitest run) -> 858 passed / 2 skipped, exit 0
        // RAN: (cd client && npx vitest run --config vitest.perf.config.ts perf/conflicts.perf.ts) -> 7 passed; (cd client && npm run build) -> exit 0
        part conflictCopyAndLoadSweepDoDR1 : TestResult { :>> id = "3e351101-1d44-4134-920b-bbf2b361b8ee"; :>> outcome = VerdictKind::pass; :>> judgedAgainst = "6dd273dc"; :>> judgedAt = "2026-09-07"; :>> judgedBy = "claudeOpus"; }
        action conflictDiffShowIgnoredLines;      // resolver for issueConflictDiffHidesIgnoredLineLoss
        verification conflictDiffShowIgnoredLinesDoD : Test { :>> id = "43fa155f-6fd1-43d9-bbf1-4badab1c2298"; :>> method = VerificationMethod::test; :>> procedureText = "DONE (green @ HEAD): resolves issueConflictDiffHidesIgnoredLineLoss and closes a related silent-data-loss hole in the auto-sweep. Found because the owner used the new Copy button and pasted a REAL conflict back - the feedback loop working exactly as intended. THE DEFECT (mine, shipped in 1.30.1): renderDiff fed normalizedContent() into unifiedLineDiff. normalizedContent DROPS an ignored timestamp line entirely, which is correct for a content-identity HASH - a plugin adding `updated:` must never cause a conflict - but wrong for a DIFF: when only ONE side has the line, dropping it from both sides makes it INVISIBLE. The owner's note carried `created: 2026-04-01T14:54` and `updated: 2026-06-08T09:40` on the Windows copy only, absent from the other device, and the rendered diff did not show them at all. So 'Keep the other device's' would have silently deleted two lines with nothing on screen saying so - on an IRREVERSIBLE either-side choice. That is precisely the hiding the invisible-character work had just argued against, reintroduced one layer up. FIX: a new frontmatter.maskedForDisplay masks the timestamp VALUE instead of removing the line (placeholder IGNORED_TS_PLACEHOLDER), so two sides whose timestamps merely DIFFER still compare equal - the whole point of the ignore setting, preserved - while a line present on one side only now shows as a + or -. Used by both the rendered diff and the clipboard report, so the copied text matches the screen. Only lines INSIDE the frontmatter fences are touched; body text is untouched (tested). SECOND, INDEPENDENT HOLE closed in the same pass, found by reasoning about the same data: dismissCosmeticConflicts compared with normalizedContent, which drops ignored lines - so two sides could be 'identical' by content identity while one still HAD a `created:` the other lacked, and the sweep keeps the note and deletes the copy. On a load-time automatic sweep that is a silent destruction of a creation date the user never chose to lose. The owner's file has exactly that shape and escaped only because its trailing spaces happened to differ too. The sweep now also requires ignoredTimestampKeysPresent() to match on both sides: an AUTOMATIC action must lose nothing whatsoever, so this case is left to the human, who can now SEE the lines in the diff. A timestamp that merely changed on both sides still auto-resolves (tested both ways). ROOT CAUSE OF THE CONFLICT ITSELF, diagnosed and NOT fixed here (see issueFrontmatterTrailingSpaceConflictLoop): the six differing lines differ ONLY by a trailing space - `tagNames: ` on one device versus `tagNames:` on the other - which is two YAML writers disagreeing on how to serialise an empty value, and semantically identical in YAML (both null). Content identity does not normalise trailing whitespace, so every rewrite on either device regenerates the conflict indefinitely. Fixing it means changing normalizedContent, which shifts every stored normHash, so it needs its own pass and an owner decision - deferred deliberately rather than slipped into a UI fix. Client-only -> PLUGIN release; no server change, no redeploy. DoD MET: tsc --noEmit clean; full client vitest 868 passed / 2 skipped (was 858 - 10 new: 8 in test/ignored-timestamp-display.test.ts built from the owner's actual frontmatter, including one that pins the OLD hiding behaviour as the bug being locked out, plus 2 plugin-level sweep-safety cases); the 7 real-filesystem perf assertions still pass; production build clean; keel validate + guard + check-engine + gate --workspace all green. NOTE one pre-existing test had to be CORRECTED, not deleted: it asserted the ignored key was 'masked out entirely, so it is neither a change NOR shown as context' - it encoded the hiding behaviour, and now asserts the honest form (present as context, value masked)."; }
        // RAN: (cd client && npx vitest run test/ignored-timestamp-display.test.ts) -> 8 passed; (cd client && npx vitest run test/plugin-wiring.test.ts) -> 70 passed
        // RAN: (cd client && npx tsc --noEmit) -> exit 0; (cd client && npx vitest run) -> 868 passed / 2 skipped, exit 0; (cd client && npm run build) -> exit 0
        part conflictDiffShowIgnoredLinesDoDR1 : TestResult { :>> id = "a148d350-39e7-4689-8143-3ea01212ad25"; :>> outcome = VerdictKind::pass; :>> judgedAgainst = "deec3d9f"; :>> judgedAt = "2026-09-07"; :>> judgedBy = "claudeOpus"; }
        // OPEN - the ROOT CAUSE of the reported conflict loop; needs the same hash-migration decision
        // as the Unicode-normalisation issue, so it is tracked with it rather than slipped in.
        action frontmatterTrailingSpaceIdentity;  // resolver for issueFrontmatterTrailingSpaceConflictLoop
        verification frontmatterTrailingSpaceIdentityDoD : Test { :>> id = "bbca0a36-9a20-4a90-a6ba-af772fd8e33e"; :>> method = VerificationMethod::test; :>> procedureText = "DONE 1.30.6 @a2bba145 (settled: frontmatter-only trailing-whitespace trim in normalizedContent; no migration needed because the persisted normHash was removed - see contentIdentityUnicodeNormalise / normHashDecide). Lines INSIDE the frontmatter fences are compared with trailing whitespace trimmed (`key: ` == `key:`, both YAML null); BODY lines are untouched (two trailing spaces are a Markdown hard line break). Tests (content-identity.test.ts): `key: ` and `key:` inside frontmatter are the SAME; the owner's REAL conflict (99 Utilities/journal classes/meeting.md, Metadata Menu fileClass frontmatter) becomes identity-equal so it would never be generated; a trailing space in the BODY is preserved; a real VALUE difference in frontmatter is still a difference; a note with no frontmatter is unaffected; ignored timestamp keys still masked and the value-shape gate still respected. ORIGINAL PROBLEM (kept for the record): stop the trailing-space conflict LOOP by normalising trailing whitespace on lines INSIDE the frontmatter fences in content identity. In YAML `key: ` and `key:` are the same null value, so two devices whose plugin versions serialise an empty value differently produce semantically identical files that content identity calls divergent - regenerating the same conflict on every rewrite, forever. Body lines must stay UNTOUCHED: in Markdown two trailing spaces are a hard line break. DoD must settle the migration, because normalizedContent feeds normalizedHash and changing it shifts every stored normHash - a persisted hash from the old algorithm stops matching a freshly computed one, which can make files look changed once and generate exactly the conflict copies being eliminated. Options: recompute-and-restamp every base normHash on the upgrade load; grandfather stored hashes and only apply the new rule to freshly computed ones; or compare both ways during a transition window. Pair this with issueContentIdentityNotUnicodeNormalised - same file, same migration, same decision - and cover it with a test built from the owner s real Metadata Menu fileClass frontmatter. Resolves issueFrontmatterTrailingSpaceConflictLoop."; }
        // RAN: RAN: cd client && npx vitest run - Test Files 53 passed | 1 skipped (54); Tests 882 passed | 2 skipped (884); Duration 90.35s; at 4a991a54 (2026-09-07 18:51). content-identity.test.ts green: NFC/NFD same identity, owner's real meeting.md conflict identity-equal, body trailing space preserved, legacy normHash stripped.
        part frontmatterTrailingSpaceIdentityDoDR1 : TestResult { :>> id = "e6fabc18-f365-4b49-b61f-4f9536459661"; :>> outcome = VerdictKind::pass; :>> judgedAgainst = "4a991a54"; :>> judgedAt = "2026-09-07"; :>> judgedBy = "claudeOpus"; }
        action contentIdentityNormalisation;     // resolves BOTH identity root causes; no migration needed
        verification contentIdentityNormalisationDoD : Test { :>> id = "940c0dce-ef98-41d7-afae-6508e12674b9"; :>> method = VerificationMethod::test; :>> procedureText = "DONE (green @ HEAD): fixes BOTH content-identity root causes of the owner's recurring phantom conflicts - issueFrontmatterTrailingSpaceConflictLoop and issueContentIdentityNotUnicodeNormalised - in one pass, since they are the same function and were blocked on the same question. THE MIGRATION TURNED OUT TO BE UNNECESSARY, and that is the headline. The owner chose 'recompute and restamp' from the three options offered, but investigating the persisted state BEFORE building it showed there is nothing stale to restamp: BaseEntry.normHash is a field NOTHING EVER WRITES. reconcile.setBase - the single writer - stores { hash, text? } only; the one assignment anywhere (mountengine.ts:59) is a load-time TYPE GUARD preserving a field that is never populated. So reconcile.baseNormHash always falls through to recomputing the hash from the stored base TEXT at comparison time, which means BOTH sides of every comparison move together the instant normalizedContent changes. A restamp would have been ceremony over a no-op, and was not performed; the premise was corrected to the owner rather than the approved plan executed regardless. A regression test now PINS that premise (setBase persists no normHash, text IS kept) so that if anyone ever starts persisting normHash the test fails and a migration becomes genuinely required. FIX 1 - frontmatter trailing whitespace. normalizedContent now strips trailing spaces and tabs on lines INSIDE the frontmatter fences (inclusive of the fence lines). In YAML `key: ` and `key:` are the same null value, so two devices whose plugin versions serialise an empty value differently were producing semantically identical files that identity called divergent - regenerating the SAME conflict on every rewrite, indefinitely. The owner's pasted conflict was exactly this on six keys at once (tagNames, filesPaths, bookmarksGroups, excludes, extends, favoriteView) in a Metadata Menu fileClass. THE BOUNDARY IS THE POINT and is pinned by its own test: body text is UNTOUCHED, because in Markdown two trailing spaces are a HARD LINE BREAK - real content, where folding would silently change rendering and could discard a deliberate edit. FIX 2 - Unicode. normalizedContent now applies NFC to the whole text, so canonically-equivalent sequences are ONE identity - 'cafe' with a precomposed e-acute and the same word with e plus a combining acute. macOS has historically produced NFD where Windows and Android produce NFC, and this project explicitly targets cross-platform desktop-plus-mobile vaults, so without it a note nobody edited could conflict forever. Canonical equivalence cannot merge two genuinely different texts, and a test asserts cafe-with-accent is still distinct from cafe-without. PERFORMANCE, measured rather than assumed - the NFC cost was the flagged risk for mobile and it is negligible: 0.03ms for a 1KB note, 0.02ms at 10KB, 0.29ms at 100KB, 2.41ms at 1MB per identity computation. Measured with a scratch harness that was then deleted rather than left behind. RISK HANDLING: this is the highest-blast-radius change of the sitting - it redefines what the sync engine considers the same file, feeding reconcile, three-way merge, the cosmetic override and the delete-local decision. It was written test-first (3 of 9 new assertions failed before the change, and the two that mattered most - body-hard-break preserved, and the no-migration premise - PASSED before it, proving the boundary and the premise independently of the fix), then validated against the entire existing suite as the real safety net: 877 passed, ZERO failures, including the integration matrix, merge-eol, reconcile and the cross-user sharing e2e. Client-only -> PLUGIN release; no server change, no redeploy. STILL OPEN and filed rather than fixed: issueNormHashDeadPersistedField - normHash is dead persisted state, and its mere presence in the interface is what made both the docs and the AI believe a migration was needed; it should be either populated (a real perf win: no re-hash from text per comparison, at the cost of making future identity changes need a real migration) or removed. DoD MET: tsc --noEmit clean; full client vitest 877 passed / 2 skipped (was 868 - 9 new in test/content-identity.test.ts); the 7 real-filesystem perf assertions pass; production build clean; keel validate + guard + check-engine + gate --workspace all green."; }
        // RAN: (cd client && npx vitest run test/content-identity.test.ts) -> 9 passed (3 failed pre-fix; the body-hard-break and no-migration guards passed pre-fix)
        // RAN: (cd client && npx tsc --noEmit) -> exit 0; (cd client && npx vitest run) -> 877 passed / 2 skipped, exit 0
        // RAN: (cd client && npx vitest run --config vitest.perf.config.ts perf/conflicts.perf.ts) -> 7 passed; (cd client && npm run build) -> exit 0
        // RAN: NFC cost measured 0.03ms @1KB, 0.02ms @10KB, 0.29ms @100KB, 2.41ms @1MB per identity computation
        part contentIdentityNormalisationDoDR1 : TestResult { :>> id = "231b46eb-0824-4779-879f-3f25471746cf"; :>> outcome = VerdictKind::pass; :>> judgedAgainst = "5b06cf4d"; :>> judgedAt = "2026-09-07"; :>> judgedBy = "claudeOpus"; }
        // normHash REMOVED (was dead persisted state with a 1.8.x staleness trap) — see the DoD.
        action normHashDecide;                    // resolver for issueNormHashDeadPersistedField
        verification normHashDecideDoD : Test { :>> id = "605be995-eadd-4522-b491-347f75cc12a5"; :>> method = VerificationMethod::test; :>> procedureText = "DONE (green @ HEAD): resolves issueNormHashDeadPersistedField by REMOVING the field - and the investigation CORRECTS a claim made one sprint earlier. The prior DoD stated that nothing had ever written normHash, so no migration was needed. HEAD never writes it - true - but git history shows 1.8.x DID (commits 39585324 and e5e090bc, 2026-07-29: `e.normHash = await normalizedHash(...)`), and the 1.9.0 timestampIgnoreRedesign deleted the writers while leaving the field, its toJSON persistence, a load-time type guard in mountengine, AND a read in reconcile.baseNormHash that TRUSTED a stored value over recomputation. So any vault that ran 1.8.x carries stale cached identities in data.json today, and the 1.30.6 normalisation change (frontmatter trailing space + NFC) guarantees those disagree with a fresh computation. Blast radius, reasoned precisely: a stale stored hash can only FAIL to match a fresh one (matching would require a SHA-256 collision), so the failure is a spurious conflict copy or an unpushed cosmetic change - the safe direction, never a wrong delete - but it is exactly the phantom-conflict class being eliminated. DECISION: remove rather than populate. A cached identity depends on BOTH the user's ignored-timestamp keys (settings can change at any time) AND the normalisation algorithm (which just changed), so any persisted value is a staleness trap with two independent triggers; the perf it would save is measured at 0.03ms per 1KB note and 2.4ms per 1MB (normalizedContent), which buys nothing worth that hazard. The owner-approved recompute-and-restamp therefore takes its safest form - there is no cached field at all, so nothing can ever be stale again. CHANGES: BaseEntry loses normHash; BaseStore's constructor STRIPS a legacy value from a persisted blob (and any other unknown field) so no code path can read it even in memory; toJSON stops writing it, so the stale value disappears from data.json on the next save without a dedicated migration step; mountengine's load guard no longer carries it over; reconcile.baseNormHash always recomputes from stored text. Doc-sync: base.ts's comment described normHash as 'the NORMALIZED content hash at the last sync' - behaviour that had not happened since 1.9.0 and which is precisely what made a restamp migration look necessary; rewritten to state the actual design and why. Three existing tests encoded the old contract and were REVERSED, not deleted: base.test.ts asserted normHash round-trips (now asserts a legacy value is dropped), mountengine.test.ts asserted a well-typed normHash is kept (now asserts it is never carried over), and content-identity.test.ts's header claimed nothing ever wrote it (now states the 1.8.x history and that legacy values are stripped). Client-only -> PLUGIN release; no server change. DoD MET: tsc --noEmit clean; full client vitest 878 passed / 2 skipped; production build clean; keel validate + guard + gate green."; }
        // RAN: (cd client && npx tsc --noEmit) -> exit 0; (cd client && npx vitest run) -> 878 passed / 2 skipped, exit 0; (cd client && npm run build) -> exit 0
        // RAN: git log --all -S"normHash" -- client/src -> writers existed in 39585324 + e5e090bc (1.8.x), none at HEAD
        part normHashDecideDoDR1 : TestResult { :>> id = "cb52fcce-d3bc-416a-86ce-4fe0b25b0ae3"; :>> outcome = VerdictKind::pass; :>> judgedAgainst = "a2bba145"; :>> judgedAt = "2026-09-07"; :>> judgedBy = "claudeOpus"; }
        // OPEN - repository policy call: commit the lockfile (+ npm ci), or record why it floats and pin exact versions.
        action lockfilePolicy;                    // resolver for issueNoLockfileFloatingToolchain
        verification lockfilePolicyDoD : Test { :>> id = "ac71d7d2-2bd5-4eaf-a4a8-db0638f7c814"; :>> method = VerificationMethod::inspect; :>> procedureText = "OPEN: make the client toolchain reproducible, by owner decision. Today client/.gitignore excludes package-lock.json, none was ever committed, and ci.yml + release.yml run npm install, so @playwright/test ^1.61.1 resolved to 1.63.0 on a fresh install this sitting and can move again without a commit. Two honest options: (A) un-ignore and commit client/package-lock.json and switch ci.yml + release.yml to npm ci, so the lockfile is authoritative - then a fresh checkout, CI and a release all build the same dependency tree; or (B) record a Decision stating why floating resolution is wanted and pin exact versions in package.json (no carets) as the reproducibility mechanism instead. Either way the choice and its reason must be a recorded Decision, since the current state has no recorded reason. DoD: the chosen mechanism in place, one fresh clone + npm install/ci producing the same @playwright/test and esbuild versions as the committed record, and CI green under it. PROGRESS 2026-09-07 (owner: 'process whole backlog'): option (A) APPLIED under project D0051 (PROPOSED): root .gitignore no longer excludes package-lock.json; client/package-lock.json committed (generated at HEAD, lockfileVersion 3, @playwright/test 1.63.0); ci.yml (npm-audit + client-tests) and release.yml install with `npm ci`; `npm ci --dry-run` resolved the lock clean. DoD closes on `keel accept d0051` (or the owner rejects and the commit is reverted). Resolves issueNoLockfileFloatingToolchain."; }
        // RAN: The lockfile policy record (superseded by its three clause records d0074..d0076) was accepted by the owner on 2026-09-13 from the decision page ('[x] Accept all 34 clause records'): client/package-lock.json is committed and ci.yml + release.yml install with npm ci (applied 2026-09-07, green on every run since, incl. release runs 34642524653 / 34646379834 / 34724420921). Resolves issueNoLockfileFloatingToolchain.
        part lockfilePolicyDoDR1 : TestResult { :>> id = "ed9f2c98-715c-4ad5-b59d-d3d0fc033e62"; :>> outcome = VerdictKind::proposed; :>> judgedAgainst = "d7fc5711"; :>> judgedAt = "2026-09-13"; :>> judgedBy = "claudeOpus"; }
        // OPEN - upstream keel defect; carried to sysmlv2-ai-toolkit. Local mitigation is in place.
        action keelDispositionLensReport;         // resolver for issueUnattestedDispositionClosesFinding
        verification keelDispositionLensReportDoD : Test { :>> id = "91e5d072-9fd0-4888-8ddc-76a0494e3adc"; :>> method = VerificationMethod::inspect; :>> procedureText = "OPEN: carry issueUnattestedDispositionClosesFinding to the keel toolkit (sysmlv2-ai-toolkit) as a defect report with the reproduction from this repo - a method=confirmation Test with disposition=acceptRisk, no TestResult, and a #Dispositions edge makes the target issue vanish from keel show open-issues; deleting the edge line brings it back. The fix belongs upstream: the open-issues and dispositions lenses should require a recorded verdict on the disposition Test before treating a finding as dispositioned. DoD here: the report filed upstream (link recorded), and once a fixed keel is installed, re-author the withheld #Dispositions edge for scanSkipResidualAccept BEFORE attestation as a regression check - the issue must stay open until the TestResult lands. Until then the local mitigation (edge withheld until attestation) keeps this repo honest. PROGRESS 2026-09-07: FILED upstream as https://github.com/williamweatherholtz/sysmlv2-ai-toolkit/issues/62 (with the reproduction). Clause 2 - the regression check once a fixed keel is installed - remains; the DoD stays open until then."; }
        // RAN: keelDispositionLensReportDoD judged 2026-11-11 at 05f6366 on keel 0.4.1 build 444333d. Clause 1 holds: the report is filed upstream as sysmlv2-ai-toolkit issue 62, state OPEN today. Clause 2, the regression check: the withheld edge from scanSkipResidualAccept to issueScanSkipMtimePreservedBlindspot was authored with no TestResult on the disposition Test. keel show open-issues then reported open 10 instead of 11, and the issue was absent from the list. The defect still reproduces on 0.4.1, so the edge is withheld again. Verdict FAIL, reason: upstream fix not yet installed.
        part keelDispositionLensReportDoDR1 : TestResult { :>> id = "7d80ac98-5c16-4f85-9c59-9c42e55e362b"; :>> outcome = VerdictKind::fail; :>> judgedAgainst = "05f6366"; :>> judgedAt = "2026-11-11"; :>> judgedBy = "ai"; }
        // OPEN - backfill: 103 DoDs read DONE in prose but carry no verdict (issueHistoricalDoDsUnstamped).
        action dodBackfillStamp;                 // resolver for issueHistoricalDoDsUnstamped
        verification dodBackfillStampDoD : Test { :>> id = "2706b517-fd15-4cca-acd5-b8384945c0be"; :>> method = VerificationMethod::inspect; :>> procedureText = "DONE 2026-09-07 (transform .engine/tools/migrations/2026-09-07-dod-backfill-stamp.py; census 109 = 85 stamped + 16 owner-listed + 5 mooted + 3 pending, reconciled by the script's own totals, idempotent re-run stamps 0). STAMPED 85: 76 method=test DoDs whose criterion is the suites green, against the FULL deliverable gate actually run at HEAD 468027ac (server 9 suites ok + clippy clean; client tsc/build ok, vitest 882 passed with the real-server integration + sharing e2e specs running; e2e typecheck ok), each carrying the artifacts it names, checked present at HEAD; 9 method=inspect DoDs whose code/config facts were RE-INSPECTED today (evidence lists file:line); perfHarnessScaleLatency by its own npm run test:perf receipt. OWNER-LISTED 16 (not stampable by the AI - D0016/D0051): deferUxEnhancements, acceptOpenEnumRisk, acceptMobileFsyncRisk (confirmations the record says the owner gave on 2026-07-11 - only the owner can stamp them, `keel append-result --judged-by wweatherholtz`), sittingReview20260807b (per-sitting review), scanSkipBoundaryPin part 2 + scanSkipResidualAccept (acceptRisk attestation), l3GuiPass / l4MobileOndevice / perfDevicePass (operator demos), critiqueR8Fixes (an independent critic's verdict), settingsGroupingPolish (design judgment), engineVintageResync (`keel accept d0050`), lockfilePolicy (policy decision), keelDispositionLensReport (upstream filing channel), stpaSafetyAnalysis (waits on D0017), stpaSuspicionPropagation (toolkit change), dodBackfillStamp (this). MOOTED 5: acEmbeddedTimestamp / acNormalizedIdentity / acTimestampConflictResolve / acDriveFsTimes / acExcludedFolders - their SystemRequirements were retired by timestampIgnoreRedesign (1.9.0) but never superseded by a Decision, so no verdict is recordable; the owner's superseding Decision is the honest close. PENDING 2: b11ParallelChunk (a sequential-vs-parallel wall-clock comparison nobody can re-run), requirementTraceabilityBackfill (its 'every SR verified' claim held for 19 SRs then; at HEAD tier-satisfaction reads 101/155 - 54 later compliance SRs carry no Test - so a pass at HEAD would be false; that gap is the tier-satisfaction burndown). sr11/sr16/sr19 re-linked (#Verify edges in acceptance.sysml) once their DoDs carried a verdict - all 25 STPA SafetyRequirements now verify-linked. ORIGINAL FINDING: the delivery record carried 103+ verification Tests (DoDs) with NO TestResult at all - 80 method=test, 14 inspect, 3 demo, 1 analyze, 1 critique, 4 confirmation - although their action comments and procedure texts read DONE (m1ProtocolDoD through round7RecoveryFixesDoD, uiFunctionalAuditDoD, autoReindexDoD, round1DeferredHardeningDoD, ...). Found 2026-09-07 while linking STPA SafetyRequirements to verifying Tests: three SRs (sr11, sr16, sr19) could not be linked because the Test that verifies each exists in the server suite but its DoD was never stamped, so linking it would claim a verification nobody recorded. Most of these DoDs predate the write-API and evidence-cited conventions (2026-07); the work shipped, the verdict was never written down. DoD for this task, in the D0067 shape (backfill-with-recorded-basis, never fabricated): (1) classify every unstamped DoD as REPRODUCIBLE (its criterion is the current gate or a named test that still exists - stamp pass at HEAD with a `// RAN:` receipt from a real run), MOOTED (its subject was retired, e.g. the embedded-timestamp acceptance Tests superseded by timestampIgnoreRedesign 1.9.0 - record the superseding Decision as the basis, no pass fabricated), or JUDGMENT (inspect/demo/confirmation whose evidence would have to be the owner's word - list them for the owner, never stamp on their behalf); (2) apply the stamps through `keel append-result` with the receipt naming the run; (3) control totals: 103 classified = stamped + mooted + owner-listed, reconciled in the commit; (4) re-link sr11/sr16/sr19 once their DoDs carry a result. Until then the honest state is: shipped work, unrecorded verdicts, and it is TRACKED here rather than implied by prose."; }
        // RAN: RAN: python .engine/tools/migrations/2026-09-07-dod-backfill-stamp.py . (dry-run) -> stamped=85 owner=16 mooted=5 pending=3 total=109; --apply -> 85 append-result writes, 0 failures; re-run -> stamped=0 already=85 (idempotent); keel validate 15 files clean; keel guard ALL PASS; post-census: 18 delivery + 6 acceptance Tests remain unstamped, every one named in the owner/mooted/pending lists
        part dodBackfillStampDoDR1 : TestResult { :>> id = "cd171968-d9aa-4fda-a104-eae0392c6711"; :>> outcome = VerdictKind::pass; :>> judgedAgainst = "468027ac"; :>> judgedAt = "2026-09-07"; :>> judgedBy = "claudeOpus"; }


        // RAN: RAN: keel gate guard decision-scaffolding . -> PASS at 183c1550 (7 violations -> 0): the guard's prescribed remedy (D0303 option C) applied - one Decision per clause, verbatim clause text, #DependsOn chain, clause 1 #Supersede-ing the compound parent: d0046->d0058..d0060, d0048->d0061..d0065, d0050->d0066..d0073, d0051->d0074..d0076, d0053->d0077..d0081, d0054->d0082..d0085, d0055->d0086..d0091 (34 clause Decisions, all PROPOSED - the owner accepts them; the compound parents' decision field is the pointer, their acceptances stand in history).

        // ---- shipped milestones (DONE) ----
        action m1Protocol;          // M1: auth + changes/get/put/delete + WS, two-client propagation
        action m2ChunkingBinary;    // M2: content-defined chunking, content-addressed store, binary+dedup
        action m3ConflictMerge;     // M3: base-aware reconcile, diff3 three-way merge, conflict-copy
        action m4MultiTenant;       // M4: accounts (argon2id) + named vaults, vault-scoped routes
        action m5Mobile;            // M5: mobile-safe paths — isDesktopOnly:false, requestUrl, pure-TS chunker
        action m6Packaging;         // M6: BRAT packaging + release workflow + Docker/reverse-proxy
        action goal1ConfigUx;       // goal #1: setup wizard + status-first grouped settings
        action rel06FixSet;         // 0.6.0: vault-switch resolution, single indicator, settings reorg
        action testHardeningClient; // Phase 1 (D0026): close the client imperative-edge test gaps the audit found. Real transport.ts unit tests (CAS 409/404→CommitConflictError, 30s timeout race, errText, the diagnose() ladder, login mustChange) over a controllable requestUrl; first tests for the 4 previously-zero-coverage UI modules (vaultswitch destructive mirror/fork flows incl. the SF1 read-only-with-local-data-must-prompt guard, confirm dismissal semantics, devicelink no-password-in-link, configdir first-contact direction); merge3 EOL/conflict/large-input tests; fixed the tautological https-not-refused test. CAUGHT + FIXED a MEDIUM defect: merge3 CRLF normalization (issueMergeCrlf). Coverage is COMPUTED + floored (D0026), not attested.
        action testHardeningServer; // Phase 2 (D0026): close the server orchestration/concurrency test gaps. New tests/ws.rs — first WebSocket integration suite (subprotocol-token auth valid/missing/garbage/empty, per-user cap → 503, global-reserve rollback, ConnGuard teardown counter → 0, revoke-mid-session, must_change gate); drove ws.rs 13.5%→76% line coverage with the ConnGuard/counter invariants directly asserted (no leak, no cap bypass). New tests/hardening.rs — concurrent-commit CAS race (exactly one 200/one 409), DoS bounds (oversized chunk 400, body 413, 10k-hash cap 400), degraded-storage 503-not-empty-manifest contract, vaults-per-user cap, corrupt-JSON-store fail-loud, api.rs 403/404/409 mapping + idempotent leave/delete. Fixed the flaky env-mutating config_defaults_and_env test (serialized on a Mutex, env saved/restored). Server line coverage 86.4%→90.0%. No server defects found — primitives were sound, the gap was purely untested concurrency/WS/bounds.
        action realObsidianE2eSmoke; // Phase 3 (D0026): the real-Obsidian e2e layer the headless suite structurally can't cover. A Playwright+CDP harness (client/e2e-obsidian/) launches an ISOLATED real Obsidian instance (pre-seeded obsidian.json vault registry + fixed --remote-debugging-port + connectOverCDP, so it never touches a running Obsidian), opens a staged vault with the freshly-built plugin auto-enabled, and asserts END-TO-END: the plugin constructs (real ObsidianVaultIo + requestUrl glue loads), auto-connects from persisted settings, and a seeded note actually SYNCS to a real spawned server (serverHasFile). Ported/adapted from origin/test_real_obsidian. LOCAL/NIGHTLY gate — needs Obsidian installed, so not in per-PR CI (specs self-skip when absent); `npm run test:obsidian-e2e`. Verified green locally (5-12s). The harness supports fuller scenarios (two-device convergence, conflict, status UI) as follow-ups.
        action realObsidianE2eMultiDevice; // Phase 3 expansion (D0026): TWO-DEVICE convergence through real Obsidian — the core SelfSync promise the headless suite + single-device smoke can't show. Parameterized the CDP launcher port so two ISOLATED Obsidian instances run concurrently (distinct ports + user-data-dirs), both syncing one server vault; renderer helpers create/modify/read notes via the real app.vault (firing genuine file events). convergence.pwspec.ts asserts BIDIRECTIONAL: a note made on device A reaches device B, AND a change on B flows back to A, plus both plugins reach a healthy (non-offline) status. Green locally (~13-20s). Deliberately NOT a live divergent-conflict test: forcing a deterministic conflict through two auto-syncing GUIs is flaky, and the conflict LOGIC (3-way merge, conflict-copy) is already covered headlessly (reconcile.test + integration-matrix). Local/nightly gate.
        action postOverhaulHardening; // Post-overhaul backlog (D0026 follow-on): two maintenance fixes. (1) Bumped vitest + @vitest/coverage-v8 2.1.9→3.2.7 so the full `--coverage` run works on Node 24 (v2.1.9 predated Node 24; its v8 provider crashed nondeterministically under fileParallelism:false). All 388 tests pass under the major bump, all coverage floors hold — verified locally EXIT 0. (2) Removed the baked SYNC_USER/SYNC_PASSWORD from the server Dockerfile ENV (SecretsUsedInArgOrEnv — a password in ENV persists into image layers); code defaults + boot weak-password guard unchanged, creds now provided at runtime. Resolves issueDockerfileEnvSecret.
        action falseAbsenceDeleteFix; // Data-safety (D0047, issueFalseAbsenceDelete): a delete-remote must never fire on mere absence-from-the-listing. reconcile.ts delete-remote now requires CONFIRMED absence via a direct per-path probe (confirmedAbsent: io.exists, else a read — never the fallible io.list()); a file that's absent from the listing but still readable/existing (a failed directory enumeration, or an unhydrated OneDrive Files-On-Demand placeholder) is KEPT, not tombstoned fleet-wide. Plus enumerateConfig now LOGS a directory-list failure instead of silently treating the dir as empty. Correct-by-construction (owner declined a bulk guard, wanted proper behavior). Fail-first regression in reconcile.test ('CONFIRMED absence'): a placeholder file is not tombstoned; a genuinely-deleted file still is. Resolves issueFalseAbsenceDelete.
        action configListSetMerge; // Config-sync hardening (issueConfigListDisable) + real-Obsidian config-sync coverage. #1: community-plugins.json is now UNION-merged as a grow-only set of enabled ids (configsync.ts isEnabledListConfig/mergeEnabledPluginsJson + a reconcileOne branch), so a shorter synced copy can never DISABLE a locally-installed plugin (nor drop SelfSync's own id); enables propagate, disables don't (correct-by-construction, not a guard). #2: a two-device real-Obsidian e2e (client/e2e-obsidian/configsync.pwspec.ts) proves config sync propagates a plugin A→B and B's own enabled plugin survives A's shorter list. Verified: configsync.test set-merge units, reconcile.test union-merge integration (fail-first), full headless suite 396 passed, and the Playwright+CDP config-sync test green. Resolves issueConfigListDisable.
        action deliverableTestGate; // STANDING GATE (D0026): "all deliverable tests green + coverage floors met" as a COMPUTED, reverifiable fact. method=test DoD names the reproducible gate (reverify.toml + CI); its TestResult is the immutable point-in-time observation. Mapped in deliverable-manifest.txt to server/src + client/src + the test trees, so ANY source change makes it suspect (keel suspect) and `keel reverify` re-runs the gate + re-stamps at HEAD — never a prose pass-attestation.

        // ---- outstanding (open frontier) ----
        action b7AuthHardening;     // B7: expiring/revocable tokens, token-only persist, TLS guidance, optional E2EE
        action b9DurabilityStreaming; // B9 Part A: append-only index journal (D0010)
        action streamingReassembly; // B9 Part B: streamed reassembly of large downloads (desktop streams, mobile buffers)
        action b11ParallelChunk;    // B11: parallelize chunk transfer (large-file perf)
        action l3GuiPass;           // L3: manual Obsidian GUI verification of 0.6.0 (esp. switch + indicators)
        action l4MobileOndevice;    // L4: on-device mobile run (foreground sync, resumable initial sync)
        action vaultSharingP1;      // vault sharing Phase 1: server ACL + authz + registration policy + web admin
        action shareClientConsume;  // vault sharing Phase 2: plugin syncs vaults shared with you
        action configSyncSafety;    // 0.10.4: config sync additive + adjudicated (never delete/resurrect); crash fix
        action requirementTraceabilityBackfill; // CR d0011: backfill the missing SR->Test #Verify traceability (resolves the escape Issue)
        action settingsGroupingPolish; // DONE (inspect, 26dc385): the settings tab is grouped into a status-first card + four concern sections (Setup & transitions / Connection / What syncs / Advanced), each a headed group of named+described Settings — never atomized-per-setting. The intelligent grouping was built into the goal-#1 config-UX overhaul (informed by LiveSync's confusing-settings study), so the end-of-project polish pass confirms it reads sensibly with no rework needed. Resolves issueSettingsGrouping.
        action critiqueClientWave;      // DONE (0.10.14): the 5 client data-integrity/correctness fixes from the adversarial critique
        action critiqueServerHardening; // DONE (0.10.16, code): SEC-1/2/MED-1/MED-2/MED-3(semaphore)/DI-3/DI-4/SEC-3 + the Low backlog — cargo-green, needs operator redeploy
        action round1CriticFixes;       // DONE (0.10.17): 15 of 18 fresh Round-1 3-lens critic findings fixed (6 SEC, 4 DI, 5 CONC); 3 dispositioned accept-risk/defer
        action round1DeferredHardening;  // DONE (0.10.32, 7524aba): the 3 deferred Round-1 findings — SEC#4 runtime orphan-chunk GC (ContentStore::sweep_orphans, upload-driven + interval-gated + TTL-spared), CONC#5 durable pending-switch (clear only after switchTo succeeds), and DI#4 (reindex prefer-store-over-stale-mirror, already shipped by round6CriticFixes 0.10.27). Resolves issueOrphanChunkQuota + issueSwitchPendingClear.
        action residualLowFindings;      // DONE (backlog sprint 2): both platform/effort-deferred LOW findings are now fixed, the capabilities they waited on having since landed. issueStreamWholeHash — the client's incremental SHA-256 (streamhash.ts Sha256, R17) EXISTS and streamFileToDisk uses it (sync.ts:121-130 verifies the reassembled whole-file hash before the atomic rename) → resolved (was stale-open). issueReindexSingleChunk — a Rust CDC chunker (server/src/chunker.rs) now matches the client gear-hash BYTE-FOR-BYTE (golden-vector parity test both sides), and reindex chunks each file with it instead of one giant blob. Tests: chunker::matches_the_client_chunker_byte_for_byte, vault::reindex_chunks_a_large_file_into_many_chunks_that_reassemble, client chunker-parity. (The two ACCEPTED-inherent/cosmetic siblings — issuePullTOCTOUResidual, issueTransientGreenLight — remain signed off won't-fix under D0020.)
        action cmmcComplianceBacklog;    // MOOTED by D0027 (2026-07-15): its sole scope was the two CUI-DATA-specific controls — SC.3.13.11 (FIPS crypto) + SC.3.13.16 (CUI-at-rest). The owner confirmed this deployment stores NO CUI, so both are formally NOT APPLICABLE (recorded as D0027, which now #Resolves issueCmmcFips + issueCmmcAtRest as a mooting Decision). No code items remain. Service-protecting controls (auth/MFA/lockout, TLS SC.3.13.8, access control, audit) stay in force. Reopens only if a deployment ever stores CUI.
        action cmmcForcedChangeReuse;    // DONE (server, real-tested): password-reuse history (IA.3.5.8 — users.rs is_password_reused/rotate_password, cap 5) + forced-change-on-reset/create (IA.3.5.9 — must_change flag enforced in the AuthToken extractor; blocks all routes but change/logout). Tests: users.rs reuse_history + must_change_flag; admin.rs password_change_rejects_reuse + admin_created_account_is_forced_to_change_password. Resolves issueCmmcPwReuse + issueCmmcForcedChange.
        action cmmcMfa;                  // DONE (server, real-tested): multifactor authentication (IA.3.5.3 — TOTP RFC 6238 second factor + single-use recovery codes for privileged/admin accounts, self-enrolled via /admin, verified at login). Self-contained crypto (totp.rs, no new deps) pinned to RFC 4231/6238 vectors. Tests: totp.rs totp_rfc6238_vectors + hmac_sha1_rfc4231; admin.rs mfa_totp_full_lifecycle. Resolves issueCmmcMfa.
        action critRoundCmmc;            // DONE (server + client, real-tested): white-glove CMMC L2 / NIST 800-171 rev2 assessor round (AC/IA/AU + SC/SI/CM). Headline: fixed an OVERSTATED-MET — IA.3.5.3 MFA was opt-in only, not required for privileged accounts; added REQUIRE_ADMIN_MFA=1 enforcement in require_admin (an admin can't act until TOTP-enrolled) + honest posture. Also: audit failed MFA enable/disable (AU.3.3.1); per-user WS connection sub-cap (SC.3.13.1, no single-account notification DoS); centralized the client cleartext-http refusal in httpReq so ALL token-bearing account calls refuse http-to-remote (SC.3.13.8 now genuinely whole-channel → met); broadened the boot guard to the whole weak/short bootstrap-password class (CM.3.4.2). Honesty reclassifications: 3.13.8 partial→met, 3.1.11 met→partial (idle = liveness + absolute cap, not user-inactivity). Tests: admin.rs require_admin_mfa_blocks_admin_until_totp_enrolled; config.rs refuses_known_weak_and_short; transport.test SC.3.13.8. Resolves issueCmmc2Mfa/AuditMfa/WsPerUser/Cleartext/BootGuard.
        action critRoundStd;             // DONE (client + server, real-tested): standard 3-lens critique round (data-integrity + security + sync). Fixed 6: reconcileDelta now supplies locallyPresent so the C1 transient-unreadable guard is active on the poll-delta path (KEYSTONE — a present-but-unreadable file during a delta could silently resurrect a deletion or lose a diverged edit; found INDEPENDENTLY by two critics); delete-local restore is CAS-guarded (expectedVersion 0, no lost update); a download vault-switch applies the bulk-delete ratio guard (a partial "ready" manifest can't mass-delete local-only notes); realtimeConnected reset on connect (no stale-green flash); server commit routes LARGE reassemblies through a permit pool (bounds aggregate memory-amplification DoS across many vaults); the WS path now enforces the must_change gate. Tests: reconcile.test crit-round cases; server suite green. Resolves issueCritDeltaGuard/RestoreCas/DownloadSwitch/RealtimeStale/CommitDoS/WsMustChange.
        action hfConfirmAndSidePicking;  // DONE (1.5.2, client-only): HF fixes — in-app confirm modal + side-picking consistency (PATCH). A small in-app ConfirmModal (confirm.ts) replaces all four native window.confirm() destructive guards (mirror-switch/fork-overwrite/leave-share/sign-out), consistent + styleable on mobile. Standardized the 'pick a side' surfaces: removed the biasing CTA from the unbiased note-conflict + config-conflict choices (a highlighted default on a 50/50 irreversible choice invited a capture-error tap); aligned config vocabulary to 'Use this device's' / 'Use the synced version'; CTA reserved for the genuinely-safe default (vault-switch Merge). Resolves issueSidePickingInconsistent/issueNativeConfirmMobile.
        action hfStatusSurfacingAndPreview;  // DONE (1.6.0, client-only, FEATURE): final human-factors batch — surface status where it's reachable, set expectations before a config commit, keep long-op state visible. (1) A 'Sync status' command toasts the current status words on demand — a one-tap readout on mobile, where the only persistent indicator is a textless sidebar icon (a truly persistent on-screen TEXT indicator isn't available: Obsidian mobile has no status bar and view.addAction is icon-only — honest partial mitigation of issueMobileStatusTextless). (2) ConfigDirectionModal intro copy now sets expectations before a whole-side overwrite — 'only files that differ change, everything else is left alone, later edits reconcile normally' (a true diff/count preview needs a local-vs-server compare the modal lacks; deferred — issueBlindConfigOverwrite copy-level mitigation). (3) statusDisplay shows a persistent 'Switching vault…' state whenever a fork/switch is in flight, DERIVED from the saved pendingSwitch flag so it survives suspend/resume and clears when the switch reconcile completes (issueLongOpTransientCompletion). MINOR per semver (adds the status command + persistent switch state). Resolves issueMobileStatusTextless/issueBlindConfigOverwrite/issueLongOpTransientCompletion.
        action hfStatusAndWarnings;  // DONE (1.5.1, client-only): human-factors fixes — status correctness + warning calibration (PATCH). statusDisplay idle on a READ-ONLY vault now reads 'Synced (read-only) — your edits stay on this device' with a lock glyph (was a misleading green 'Fully synced'); idle uses a STEADY glyph (check/lock) instead of the spinner, so a healthy polling device isn't stuck at a permanent yellow spinner (the spinner is reserved for connecting/syncing); the vault-switch download confirm now says local removals go to the recoverable vault trash (was the miscalibrated 'can't be undone'), reserving heavier wording for the server-upload case. Resolves issueStatusIndicatorMisleads/issueMiscalibratedSwitchWarning.
        action deferUxEnhancements;  // DECLINED (2026-07-13, human-attested): three UX-critique findings the user chose NOT to act on now — the obsidian:// protocol handler (issueNoProtocolHandler), setup-wizard state persistence (issueWizardStatePersistence), and the deeper IA restructures + residual lows (issueDeepIaRestructure). Real but larger; deferred by explicit wweatherholtz instruction ("record these as declined items"). This action IS the recorded deferral disposition (no code); resolves those three issues so they're tracked-as-declined rather than dangling.
        action surfaceSharingAndConflicts;  // DONE (1.5.0, client-only, FEATURE): surfaced the inbound-sharing + conflict flows the critique found undiscoverable. New command-palette commands: 'Switch vault' (was only in settings), 'Redeem a share link', 'Resolve conflicts' (routes to whichever kind is pending, else a notice); the setup command renamed 'Set up / reconfigure connection'. A 'Redeem a share link' button added to the UNCONFIGURED status card (the new-recipient entry point — no longer requires knowing to paste a share link into a setup field). And startRedeem now OPENS the Switch modal after an already-signed-in redeem (redeemed vault appears in 'Shared with you') instead of leaving the second step to a missable toast. MINOR per semver. Resolves issueSharingConflictsDiscoverability.
        action pluginAdoptionRestartHint;  // DONE (1.4.0, client-only, FEATURE): closes the plugin-adoption ending — after 'Install all from the sync' the plugins looked synced but weren't active (Obsidian loads plugins only at startup; the only hint was a transient toast). Now a STANDING mod-warning banner in the Synced-community-plugins group counts plugins adopted-but-not-installed-locally and says 'fully close and reopen Obsidian (on mobile, swipe the app away) to enable them'; plus a 'Checking the server for plugins…' placeholder while the server list hasn't populated yet (so a fresh vault doesn't read as 'nothing to sync'). MINOR per semver (new user-facing state). Resolves issuePluginAdoptionSilentRestart.
        action guardDestructiveActions;  // DONE (1.3.2, client-only): UX-critique data-safety guards (PATCH). The vault-switch Download/Upload MIRROR modes now confirm() before deleting local-only / remote-only files (naming which side loses files, 'can't be undone') — previously a single tap; Fork refuses/confirms when the name matches an existing owned vault (it uploads unconditionally, so a collision would overwrite); Sign out confirm()s (token-only mode has no saved password → re-login needed). Merge (safe default) still needs no confirm. Resolves issueUnguardedDestructiveActions.
        action uxPolishBundle;  // DONE (1.3.1, client-only): UX-critique quick-win polish (all fixes/copy → PATCH). Recovery error messages now name real buttons ('Reconfigure'/'Switch') not the command-palette name; setup/consent banner renders line breaks (white-space:pre-wrap); Max file size validates on blur (notice + revert, no silent fail); conflict-log breadcrumb → 'Settings → Conflicts'; 3 log-viewer toasts gained the 'SelfSync:' prefix; 'Keep the other device's'; 'fully close and reopen Obsidian' (mobile-clear) replaces 'reload Obsidian'; change-password warns other token-only devices need the new password; removed dead statusTitle() (+ its test) that had diverged from statusDisplay(). Resolves issueUxQuickWins.
        action forkVault;  // DONE (1.3.0, client-only, FEATURE): a direct "Fork this vault" action (Switch modal) — copies the CURRENT vault's local content into a NEW vault you own and switches this device to it; the original is untouched. Especially useful on a read-only shared vault (yields your own editable copy). Reuses tested primitives: createRemoteVault(name) then switchToVault(name,'upload','',false). Makes explicit what was previously a manual switch-to-new-vault + upload. MINOR per semver.
        action statusDetailAndResuming;  // DONE (1.2.0, client-only, FEATURE): the status line was a bare "Syncing…" with no detail, so when nothing was pending it looked like nothing was happening. Now statusDisplay(phase) always says WHAT: "Syncing… N pending" while transferring, "Syncing… checking for changes" while assessing (never a bare label); idle distinguishes "Fully synced" vs "Synced (polling)" by realtime health. Plus a new transient "Resuming…" state shown after a context switch (mobile resume via visibilitychange) while sync state is re-assessed — set in onResume, cleared once the phase settles (idle/offline) or transfers start (pending>0). One source of truth used by the settings row + ribbon/status-bar tooltip. MINOR per semver (new user-facing state).
        action adoptServerPlugins;  // DONE (1.1.0, client-only, FEATURE, extends D0025): fixes the fresh-vault bootstrap gap — the plugin allowlist was built from LOCALLY-INSTALLED plugins only, so a new vault (none of the source vault's plugins installed) had an empty list and could never adopt them, and expecting the user to pre-install what they don't yet know exists is backwards. Now reconcileAll reports the server's community-plugin ids (onRemotePlugins); settings shows the UNION of installed + server-side plugins (server-only ones labelled "from the sync — will be installed"), ticking one pulls its files = installs it (download-only for not-installed); plus a one-click "Install all from the sync" bootstrap. Respects the peer-plugin-code gate; opt-in (running third-party code stays a deliberate act). MINOR bump per semver (new capability, not a fix).
        action pendingExcludesDeclined;  // DONE (1.0.39, client-only): FIELD — reopening a vault showed 20+ pending syncs that never transferred. The pending pre-classifier counted remote files this device DECLINES (config surface off / plugin not allowlisted) — reconcileOne skips them, so the count never drained (worse on mobile, which backgrounds mid-pass). Fix: reconcileAll + reconcileDelta exclude accepts()-filtered files from the pending set (honest 'work this device will do'), and surface them via a new onDeclined callback → a coalesced, change-only log naming the community plugins / config files on the server that aren't in this device's selection + how to enable them (also explains that plugin sync is opt-in on BOTH ends). Resolves issuePendingCountsDeclinedFiles.
        action configSyncPerPluginDirection;  // DONE (1.0.38, client-only, extends D0025): per-plugin first-contact direction — the "lighter form" the user asked for. Each synced community plugin carries its own direction (configSync.pluginDir, persisted, keyed by id), shown as an inline download/upload dropdown that appears only when the plugin is synced (read-only → "download only" text). Defaults to the Community surface's direction. The synced-plugins list is now COLLAPSIBLE (<details>, expanded when ≤8, state persists across re-renders) so a big roster doesn't flood the pane, independent of a mixed per-plugin direction set. main.ts setPluginSync/setPluginDir/communityConfigDir; recordConfigConflict prefers a plugin path's own pluginDir over the surface direction; loadSettings keeps a fresh pluginDir. Read-only forces download everywhere.
        action configSyncFirstContactDirection;  // DONE (1.0.37, client-only, implements D0025): settings (config) sync now declares an EXPLICIT first-contact direction PER SURFACE when turned on — {download = adopt synced, upload = make this device's canonical}, MERGE dropped (config is opaque, a line-merge could corrupt it). Replaces the reactive per-file 'keep local / take remote' prompt-on-divergence with an upfront intent (ConfigDirectionModal). Read-only shares: offered, default OFF, download-only (opt-in; never pushes; never auto-clobbers the reader's config). Mechanism: session-transient per-surface pendingConfigDir consumed by recordConfigConflict to auto-resolve a NO-BASE divergence via resolveConfigConflict; a later concurrent edit (shared base) still prompts. Pure configSurfaceOf + configAutoResolveChoice. Accepted by wweatherholtz (per-surface + read-only-default-off).
        action configSyncEventDriven;  // DONE (1.0.36, client-only): made mobile config DETECTION event-driven (user direction). The WS already makes the RECEIVE path event-driven (server poke → pull); the gap was the SENDER noticing its OWN config edit, where mobile lacks a reliable `raw` FS event. Now Obsidian UI events are proxies: css-change (theme/snippet/appearance) + layout-change (plugin toggle / panes) TRIGGER the cheap stat-skipping config scan on demand (coalesced + rate-limited to ~once/CONFIG_EVENT_MIN_GAP_MS, since layout-change also fires on plain navigation). The 30s periodic scan is demoted to a BACKSTOP for the rare change that fires no event. Common mobile config edits now sync near-instantly instead of ≤30s. Follows the 1.0.35 cheap-scan (fastCheapConfigScan) which made frequent scanning viable.
        action fastCheapConfigScan;  // DONE (1.0.35, client-only): FIELD — config sync felt ~5 min on mobile. Desktop is live (vault `raw` event); mobile lacks it and fell back to a 120s config re-hash + suspends when backgrounded. Fix (user chose 'cheap fast scan'): (1) reconcileLocalConfig skips a file whose on-disk (size,mtime) match the base stat-stamp → the scan runs often without re-hashing every synced plugin's bytes; (2) CONFIG_SCAN_INTERVAL_MS 120s→30s; (3) a visibilitychange listener forces a config scan on app-resume. Detection ~2 min → ~30s (instant on reopen). Resolves issueConfigSyncMobileLatency.
        action editorStatusCleanupOnUnload;  // DONE (1.0.34, client-only): FIELD — the note header stacked 6 sync icons (1 green + 5 red). The opt-in in-editor indicator is added via view.addAction, which Obsidian does NOT auto-clean on unload (unlike addRibbonIcon/addStatusBarItem), and onunload didn't remove it — so every plugin update orphaned the old instance's icon and the new instance added another (dead ones frozen at their last phase). Fix: onunload now removes all editorActionEls (mirrors the setEditorStatus-off cleanup) → idempotent across reloads. Existing orphans clear on one Obsidian restart. Resolves issueEditorStatusIconLeakOnReload.
        action connErrorAbortsPass;  // DONE (1.0.33, client-only): FIELD — a mobile resume before DNS was ready flooded the log with ~200 per-file UnknownHostException errors (a whole-connection failure isolated per-file, meant for one bad file). New isConnectionError classifier (host-resolution + connection-refused/reset/unreachable; deliberately NOT per-file content/read errors) makes reconcileAll/reconcileDelta/config loops ABORT the pass on the first connection error (shared connAbort flag short-circuits the remaining files) → engine goes offline + backs off ONCE. A genuine single-file error still isolates. Resolves issueConnErrorPerFileFlood.
        action conflictReadOnlyAndBinaryCorrectness;  // DONE (1.0.31, client-only): 3-lens critique + field-report fixes to conflict/sync correctness. (1) FIELD: read-only vault no longer manufactures unsyncable, permanently-flagged conflict copies for a no-base divergence — on read-only, a copy is preserved ONLY for a genuine both-sides edit vs a known base (action 'merge'); a no-base divergence adopts the owner's bytes with NO copy; an existing conflict-copy file is no longer reported 'won't sync'. (2) F1 (High): the cosmetic-EOL guard + modal auto-dismiss are gated on isMergeable (extension + fatal-UTF-8), so a binary attachment can't be lossy-collapsed to 'equal' and silently clobbered. (3) F3: resolveNoteConflict 'keep mine' re-checks the stale-preview guard immediately before the write (TOCTOU). (4) F4: startPolling early-returns when unloading (no leaked interval on unload-during-connect). (5) F5: listNoteConflicts requires the original to exist (no look-alike/orphan flagged). (6) F6: resolveShareGrant fails closed on an unknown perm. Resolves issueFalseConflictReadOnlyBinary/issueCosmeticGuardBinaryClobber/issueResolveMineToctou/issueUnloadPollLeak/issueConflictCopyLookalikeDelete/issueShareGrantFailOpen.
        action shareRedeemStoreConsistency;  // DONE (server): 3-lens critique fixes to share-redeem cross-store consistency. (1) F2a: shares.rs grant() snapshots + restores its grant set on a save() I/O failure, so a failed grant never lingers in memory (the redeem rollback can't leave a live grant + a re-redeemable link). (2) F2b: share-link self-redeem (owner redeems own link) now unredeems (releases the claim) so it doesn't burn the single-use invite. Resolves issueGrantSaveRollback/issueSelfRedeemBurnsLink.
        action shareLinkRedeemConsumeLast;  // DONE (1.0.30 server): server dual-source sweep (client-audit follow-up) finding. share_link_redeem consumed the single-use link (.share-links.json) BEFORE the grant (.shares.json) succeeded, so a recoverable grant failure (owner at cap / grant I/O error) — or a crash between the two file writes — permanently BURNED the invite with no grant. Fix: redeem still claims the link atomically (single-use preserved under concurrency), but the handler now rolls the claim back via ShareLinkStore::unredeem on BOTH failure branches → the link survives to retry (only the narrow crash-between-writes window remains, accepted). Fails closed (redeemed_by never feeds authz). Resolves issueShareLinkBurnedOnFailedGrant.
        action shareRefreshedOnConnect;  // DONE (1.0.30, client-only): killed a second dual-source-of-truth (client-side audit follow-up to D0024). The cached vaultOwner/vaultReadOnly were frozen at redeem time and drifted from the server's share grant (the authority) — an owner flipping read↔write or revoking access was invisible until a manual re-Switch. Fix: connect() now re-derives our access from listShared() on EVERY reconnect via the pure resolveShareGrant(grants, owner, vault) → the cached flag is a projection of the grant, not a copy. Revocation is caught before a push would 403 (clear card message, files untouched, auto-recovers if re-granted). Own vaults short-circuit (no extra call). Tests: sharelink.test resolveShareGrant (notShared / read→read-only / readWrite-upgrade / revoked-when-absent).
        action conflictModelDerivedFromVault;  // DONE (1.0.29, client-only, implements D0024): re-architected conflict tracking to kill the dual-source-of-truth. NOTE conflicts are now DERIVED PURELY FROM THE VAULT (deriveNoteConflicts over the vault file list; the strict-named copy file IS the record) — settings.noteConflicts array + recordNoteConflict/clearNoteConflict deleted; listNoteConflicts/count/badge/modal are pure projections; resolveNoteConflict is total/idempotent (missing copy → no-op, no 'File does not exist'). CONFIG conflicts stay the reconcile-refreshed store (no artifact by design). Fixes stale entries, dual-truth counts, blank modal — by construction, not patching.
        action pendingProgressAndConflictResilience;  // DONE (1.0.28, client-only): (1) sync progress reworked from 'N/M files examined' (total is noise) to '# PENDING' — files that actually need transfer, driving to 0. reconcileAll pre-classifies pending cheaply from remote-hash-vs-base + real tombstones + new-local (no local hashing); reconcileDelta's changed set IS the pending set. onProgress is now single-arg (pending). (2) Conflict-modal RESILIENCE: a stale conflict entry (copy/note already gone → 'File does not exist') no longer aborts the whole modal ('Couldn't load conflicts') — each auto-dismiss entry is isolated in its own try/catch and skipped.
        action conflictModalFixAndSyncProgress;  // DONE (1.0.27, client-only): (1) the 'Resolve conflicts' modal rendered BLANK — the auto-dismiss loop awaited through all N files before drawing, and an error left it empty. Fixed: run() shows an immediate 'Checking conflicts…' placeholder, auto-dismisses cosmetic copies WITH a visible progress count, then draws; wrapped in try/catch so an error shows a message, never a blank body. (2) Sync PROGRESS: reconcileAll fires onProgress(done,total); the plugin throttles to integer-% and surfaces 'Syncing… N/M' in the status-card row + the light tooltip (syncstate light('syncing', detail)).
        action falseEolConflictFixAndDiff;  // DONE (1.0.26, client-only): sync falsely flagged 46 'conflicts' whose two versions were identical — they differed ONLY by line endings (Windows CRLF desktop vs mobile LF) and, with no common base (first sync/adopt of two independent-but-identical copies), decide() returned conflict-copy and spawned a spurious copy per file. Fix: sameIgnoringEol() guard in reconcileOne's merge/conflict-copy branch converges on the remote bytes (records base, NO copy) when the only difference is EOL/trailing-newline. UX: NoteConflictModal now (a) auto-dismisses cosmetic-only copies already on disk (clears the 46 without 46 clicks) and (b) shows a real line-level DIFF (unifiedLineDiff via merge.lcsPairs; −other/+this-device, context dimmed) for genuine conflicts — the requested diff view.
        action granteeLeaveShare;        // DONE (1.0.25, server+client): a shared-with user can now DECLINE/LEAVE a shared vault (drop their OWN access) — previously only the owner could revoke. SERVER: DELETE /api/shared {owner,vault} (api::leave_share) forces grantee=caller so you can only remove your own grant; audited. CLIENT: transport.leaveShare + plugin.leaveSharedVault (also disconnects if it's the vault you're currently syncing; local files kept) + a 'Leave' button per entry in the Switch modal's 'Shared with you' list (confirm dialog). e2e proves 200-before / 403-after / gone-from-shared-list against the real server.
        action settingsPanelTargetedCleanup;  // DONE (1.0.24, client-only): targeted settings-panel declutter (user-approved scope). 'Redeem link' removed from the current-vault row (it gains access to a DIFFERENT vault, not an action on the current one) and moved into the Switch-vault modal as 'Redeem a share link' — it belongs with choosing/gaining vaults (redeeming adds to 'Shared with you'). 'Reconfigure' (was on the Server row) and 'Disconnect' (was in the status row, duplicating 'Sign out') moved to Advanced → Connection with a description distinguishing Reconfigure / Disconnect / Sign out. Status card is now leaner (Server fact has no button; Vault row: Share [if owned] + Switch; status row: Diagnose + Add a device). Answered separately: the shared 'default' vault was created by the pre-1.0.19 multi-vault modal (audit log share_link_create target will/default) — clutter now removed.
        action redeemE2ECoverage;        // DONE (test-only): the missing end-to-end test that would have caught the 1.0.20-1.0.23 share-flow gaps in ONE run instead of four user-found regressions. sharing-e2e.spec adds 'must-change account → change password → redeem a share LINK → sync' against the REAL server: asserts a fresh admin-created account is must-change-gated (login ok + /api/vaults 403), changePassword clears it (200), a read-write share LINK is created + redeemed (binds the grant, single-use), and the recipient syncs the owner-qualified vault. NodeTransport gained loginFull/createUserRaw/changePassword/createShareLink/redeemShareLink/listShared/rawStatus. Root-caused the blind spot: the createUser helper HID must-change (did the forced change internally), so no test ever drove a must-change account through login/redeem.
        action wizardForcedPasswordChange;  // DONE (1.0.23, client-only): a fresh/admin-created account hit 'vaults: HTTP 403' when signing in via the setup wizard (incl. the guided-redeem flow). Cause: the account is must-change-password gated (IA.3.5.9 — every route 403s until the password is set), but the wizard ignored the flag and barreled into listVaults. Fix: HttpTransport.login now returns {token, mustChange}; the wizard, on mustChange, shows a 'Set a new password' step (changePassword → fresh un-gated token) then continues (afterAuthenticated: redeem in redeem-mode, else load vaults). loginRemote (established re-login) unwraps .token.
        action guidedRedeemViaSetup;     // DONE (1.0.22, client-only): a share link now BOOTSTRAPS setup instead of requiring you to be set up first (the anti-pattern the user flagged — the link IS the onboarding). plugin.startRedeem(link) is the single entry: if already signed in to the link's server, redeem now (+ 'use Switch'); otherwise open SetupWizardModal in REDEEM mode — server prefilled from the link, guide sign-in (login OR register), then finishRedeem() persists the session, redeems, adopts the shared vault (vaultId/vaultOwner/readOnly) and reconnects. No vault-picker step in redeem mode. The wizard's paste hand-off + Settings 'Redeem link' both route through this.
        action redeemNotSetUpGuardAndDirect;  // DONE (1.0.21, client-only): the 'Invalid URL' on redeem persisted after 1.0.20 because a SECOND new URL threw — redeemShareLink compared normalizeServer(this.settings.serverUrl) with an EMPTY serverUrl on a not-set-up device (new URL('') → 'Invalid URL'). Extracted redeemTargetError(linkServer, deviceServer): guards the empty/not-set-up case with clear guidance ('Set up SelfSync and sign in to <server> first') and the wrong-server case, no crash. Also: the setup-link paste hand-off now REDEEMS DIRECTLY (Notice on result) instead of opening the redeem modal — no second click. Redeem stays authenticated + server-specific (a fresh device must sign in to the link's server first).
        action shareLinkUrlParseFix;     // DONE (1.0.20, client-only): redeeming a share link threw 'Failed to construct URL: Invalid URL' on Obsidian mobile. Root cause: parseShareLink/parseSetupLink did `new URL(link.replace(scheme,'https://'))` → `https://redeem?…`, a bare-label host the Android WebView URL parser rejects. Both now read the query DIRECTLY via URLSearchParams on the substring after '?' (no fake-host URL, decoding preserved). Regression test with the exact failing percent-encoded link.
        action shareCurrentVaultOnly;    // DONE (1.0.19, client-only): ShareManageModal simplified to share ONLY the vault this device is currently syncing (settings.vaultId) — no per-vault loop, no vault picker, no vault labels/headings (title 'Share this vault'). Drops the confusing multi-section modal (one block per owned vault, incl. the stray auto-created 'default') that made it easy to create a link for the wrong vault. A vault shared-with-you (vaultOwner set) or not-yet-synced shows a clear can't-share message. Pending links filtered to the current vault.
        action shareUxAndCaseInsensitiveNames;  // DONE (1.0.18): field-reported sharing/UX fixes. (1) Share/redeem errors surfaced 'is not valid JSON' — RequestUrlResponse.json throws on a plain-text error body; transport now reads r.text (errText helper) so the server's real message shows (share/unshare/create-link/redeem/create-vault). (2) Pasting a selfsync-share:// link into the device-setup 'Paste setup link' field failed 'Not a SelfSync setup link' — the paster now detects a share link (isShareLink) and hands off to RedeemShareLinkModal (prefilled). (3) Usernames are now CASE-INSENSITIVE (canonicalized to lowercase at login/register/users_create/share-grantee) — 'Will'/'DANA'/'Bhu' map to the one lowercase account; non-breaking since stored keys were always lowercase. Also explains the per-vault share sections (one per owned vault; the stray 'default' vault is the bootstrap auto-create).
        action usernameRuleAndUx;        // DONE (server-only): admin add-user rejected emails without stating why. safe_name now also admits '+' and '@' (path- + filesystem-safe, no traversal — enables email/plus-addressed usernames; still lowercase-canonical), a shared NAME_RULE string is surfaced in the 'invalid username' error (users_create + register), and admin_ui.html states the rule under the add-user row. Fixes the field report: silent-ish rejection with no expectation.
        action skipOsJunkFiles;          // DONE (1.0.17, client-only): the plugin now skips OS/tool junk (Thumbs.db, .DS_Store, desktop.ini, .git anywhere in the path, + .selfsync-part/.selfsync-tmp temps) instead of attempting to sync them and logging one HTTP 400 per file. isJunkFile() in configsync.ts is an EXACT mirror of the server's is_junk; folded into shouldSync (the shared io+reconcile accept gate) so junk is never pushed and no base is recorded (no phantom delete). Fixes the field-reported Thumbs.db 400 noise.
        action vaultNameAndSizeLimits;   // DONE (1.0.16, real-tested): two field-reported UX fixes. (1) VAULT NAME: the wizard + vault switcher now sanitizeVaultName() (trim + lowercase, matching the server's lowercase-only safe_name) before create, so "Testbrsin" becomes "testbrsin" instead of a bare HTTP 400; isValidVaultName tightened to lowercase-only (client rule == server rule) + a clear inline message. (2) CONFIGURABLE SIZE LIMITS: per-file cap was hard-coded (50 MB mobile / 200 MB desktop) — now a per-device "Max file size to sync (MB)" setting (default 200, maxSyncBytes()) and a server MAX_FILE_MB env (Config::max_file_bytes, default 512, enforced in api::commit; vault backstop raised to 4 GiB absolute). Answers the field reports: the mobile 50 MB skip + the vault-name 400.
        action deployComposeHardening;   // DONE: deploy/ compose cleanup + published server image. Removed the local `build: ../server` (the server now ships as a prebuilt GHCR image ghcr.io/williamweatherholtz/obsidian-selfsync-server, published by a new release.yml server-image job on each version tag; compose uses `image:`). Dropped redundant env (DATA_ROOT + BIND_ADDR — image-fixed internal address/path, not user knobs) and the no-op `expose:` (Compose same-network reachability needs neither expose nor ports). Added an explicit healthcheck (curl /health on the sync port, served on every surface) + Caddy `depends_on: service_healthy`. New deploy/docker-compose.noproxy.yml (server only, sync bound to 127.0.0.1:8080) for operators who terminate TLS themselves. Documented the REGISTRATION first-run-seed semantics (env seeds .registration.json only on first boot; afterward /admin is authoritative + persists across reboots — answers the reboot/override question honestly). doc-sync: deployment.md + README corrected (the stale `expose:`-not-`ports:` claim, env table, noproxy + image/pull guidance).
        action perfHarnessScaleLatency;  // DONE: headless real-world PERFORMANCE harness (client/perf, `npm run test:perf`) — spawns the real server + headless clients through the real chunk/reconcile engine, measuring SCALE (initial push/pull + no-op rescan by vault size) and PROPAGATION LATENCY (single-edit A->B round-trip). Results + interpretation in docs/architecture/92-perf-scale-latency.md: propagation is flat ~20-29ms p50 from 50->3000 notes (O(change)); no-op rescan sub-second at 3000 files (scan-skip); initial push is per-file-round-trip bound (~110 notes/s, debug/loopback floor). Env: loopback + debug build (a pessimistic floor).
        action perfDevicePass;           // OPEN: the real-device fidelity pass (desktop + phone via BRAT 1.0.15, real server/TLS/network) for scale + propagation — protocol + results template in docs/architecture/93-real-device-perf-protocol.md. Awaits the operator's hardware run; findings route as Issues.
        action capabilityShareLinks;     // DONE (server + client, real-tested): D0023 — share a vault by sending a single-use LINK (no username, in-plugin, no admin), redeem-binds-to-account. Server: sharelinks.rs store (.share-links.json, hashed/single-use/TTL'd, permission server-side) + owner-scoped create/list/revoke + AuthToken-gated redeem (mints a D0008 grant bound to the redeemer). Client: selfsync-share:// codec, transport methods, ShareManageModal create/pending-list/revoke + RedeemShareLinkModal + a settings "Redeem link" action. Implements D0023 / serves nVaultSharing. Tests: sharelinks.rs 3 unit + admin.rs 2 integration; client sharelink.test 6 + modals DOM 3.
        action acceptOpenEnumRisk;       // DONE (accept-risk, human-attested): open-registration username enumeration is accepted as inherent to open self-registration — de-oracling /api/register would break the UX (a user must be told a name is taken to pick another), and anyone can create accounts in that mode anyway. Mitigation is operator guidance: run registration invite-only/closed (the default), which removes the public register surface entirely. Resolves issueCritOpenEnum.
        action acceptMobileFsyncRisk;    // DONE (accept-risk, human-attested): the mobile buffered-write fsync durability gap is accepted as a known, intractable platform limitation — mobile exposes no fsync API, so the narrow crash-window (a pulled note lost between write and OS flush while base persisted) cannot be closed in code; desktop is durable. Resolves issueCritMobileFsync.
        action critResidual2;            // DONE (server + client, real-tested): two more residuals cleared. WS half-open liveness (SC-adjacent) — the server sends an application heartbeat every ~30s (ws.rs) and the client runs a liveness timer (main.ts) that treats the socket as dead + re-dials if no frame arrives within WS_STALE_MS, so the status light no longer stays green over a half-open socket (browsers hide protocol ping/pong from JS). Audit source-IP (AU.3.3.2) — require_admin now threads the caller's ClientIp, so the high-value privileged-function-denied events carry the source (read-only-route denials keep "-", proxy-correlated). Tests: syncstate.test isWsStale; server admin suite green with the require_admin signature change. Resolves issueCritWsLiveness + issueCmmc2AuditSource.
        action critResidualEasy;         // DONE (server, real-tested): the two low-effort residuals cleared — TOTP in-window replay protection (users.rs records the last consumed 30s step per user; a code from a consumed step is rejected, RFC 6238 §5.2) and the SC.3.13.13 claim-wording correction (sync allowlist, not an execution trust-prompt gate). Tests: totp_code_cannot_be_replayed_within_its_window. Resolves issueCritTotpReplay + issueCmmc2MobileCodeWording.
        action uiFunctionalAudit;        // DONE (client + server, real-tested): end-to-end functional audit of BOTH UIs (admin web page + Obsidian plugin) — every interactive control traced to its behavior. Fixed 9 wiring defects across the three classes (discarded control effect, dual-truth/stale indicator, no-op/dead-end dialog): admin A1 sign-out revokes server session, A2 MFA-enable reflects enabled state, A3 forced-change login screen, A4 owner-vault sub-row reconciles after repair/delete, A5 no Repair on a "missing" vault; plugin P1 wizard honors token-only-at-rest, P2 config toggles apply immediately, P3 lastSyncedAt persisted, P4 status light reflects real WebSocket state. Guards: server admin.rs (must_change lifecycle, grant/revoke, delete, reindex/prune HTTP, invite list/delete); client syncstate.test (light realtime), wizardsteps.test (wizardCredentials token-only), plugin-wiring.test (applyConfigSyncChange kicks a scan); e2e-helpers fixed for the forced-change flow. Resolves issueUi*.
        action round2CriticFixes;        // DONE (0.10.18): 15 of 16 fresh Round-2 3-lens critic findings fixed (4 DI, 6 CONC, 4 SEC + 1 note); 1 accepted (residual pull TOCTOU, inherent)
        action round3CriticFixes;        // DONE (0.10.19): 6 of 8 fresh Round-3 3-lens critic findings fixed (1 DI, 3 CONC, 2 SEC); 2 deferred (streamed whole-file hash, reindex single-chunk)
        action round4CriticFixes;        // DONE (0.10.20): 2 of 2 fresh Round-4 findings fixed (1 DI MED, 1 CONC LOW); SECURITY LENS CONVERGED (0 findings); 1 cosmetic accepted
        action round5CriticFixes;        // DONE (0.10.21): 3 Round-5 final-adversary correctness fixes (Unicode case-collision, legacy-key delete, revoke-before-purge); holistic verdict = data-safety sound
        action round5CompletenessFollowups; // DONE (0.10.33, 10a7154): the holistic-round remainder — items 1/3/4 (version handshake, admin reindex, commit CAS) shipped earlier under preReleaseHardening; this closes item 7 (cosmetic conflict-copy: stream-fail orphan cleanup + live-hash tag), items 5/6 (persisted-data forward-migration seam client-side + SQLite schema_version tag server-side + lazy/runtime-GC requirement wording), and item 2 (orchestration test-harness: the raw-event config pipeline incl. the self-folder security filter now has a direct plugin-wiring test; SEC-3 no-auto-enable is round6, WS-revocation is server-side ACL). Resolves issueOrchestrationUntested + issueDataMigration + issueConflictCopyCosmetic.
        action pluginShareOptIn;          // DONE (0.10.23): community plugins are opt-in (allowlist), not default-share — a new install isn't auto-pushed; + bulk share-all/none
        action fsmRefactor;               // DONE (0.10.24): one authoritative operational FSM (SyncEngine: serial event queue) replaces the scattered flags + parallel recovery — the CONC-R* race class is now structurally impossible
        action deleteLocalTombstoneGate;  // DONE (0.10.25): CRITICAL data-loss fix — delete-local requires a real deletion tombstone, never mere absence; + plugin-wiring integration tests + e2e harness repair
        action preReleaseHardening;       // DONE (0.10.26): shippable round-5 completeness items + the 2 timing crutches — protocol version handshake, admin vault reindex, commit optimistic-concurrency (CAS); token-TTL crutch → optimistic+reactive-401; config-scan poll-count → wall-clock
        action round6CriticFixes;         // DONE (0.10.27): 3 High + 4 Med + 2 Low from the Round-6 3-lens critique — tombstone-cap removal (resurrection fix), CAS-409 event-path isolation, SEC-3 owner-direction RCE + CSS gate, single-flight re-login, failToOffline connected-drop, reindex collision-guard + prefer-store; 1 Low (share-create enumeration) accept-risk
        action round7RecoveryFixes;       // DONE (0.10.28): recovery-lens bugs — reindex recovers from the chunk store + admin force (RC-2, unbrick), 404 vault-gone message (RC-3), per-vault admin delete (RC-4)
        action sqliteMigration;           // DONE (05e655b; server-only, no plugin release): per-vault SQLite (WAL) index behind the SqliteIndex seam, replacing the JSON snapshot+journal — resolves the storage-format-dependent scale findings (RS-2/5/6/7) + hardens against index corruption (WAL + page checksums). JSON->SQLite data migration WAIVED by owner ('nuke away'); fresh start + reindex rebuilds from the chunk store + mirror. Postgres deferred behind the seam.
        action resourceScaleFixes;        // DONE (0.10.30): RS-1 (evict idle vault handles with no WS subscribers, bounding server RAM) + RS-4 (cap merge-ancestor base text at 1 MiB, bounding client RAM/data.json)
        action incrementalReconcile;      // DONE (0.10.29): RS-3 — a remote poke reconciles only the delta's changed paths (reconcileDelta), not a full-vault re-hash; the full reconcileAll is reserved for the config scan + version rewind
        action scaleHardening;            // DONE (05e655b): the umbrella for the Round-7 resource/scale findings, delivered by the three split actions — RS-1 handle eviction + RS-4 base-text cap (resourceScaleFixes, 0.10.30), RS-3 incremental reconcile (incrementalReconcile, 0.10.29), RS-2 per-write index clone / RS-5 version-indexed changes / RS-6 incremental snapshot / RS-7 bounded cold-open (sqliteMigration, the storage-engine decision D0018). Every RS-1..7 finding is now shipped or mooted.
        action historyRebase;             // DONE (0.10.31, 8c69b8b, D0019): the deletion-history HORIZON — the server tracks a history_floor (raised to the current version when a rebuild-from-disk reindex loses tombstones), exposed in changes; a below-floor client (floor advanced past its stored one, or a version rewind) stays conservative (keep + push, never delete without a tombstone) and surfaces ONE batched notice, fixing the corrupt-reindex resurrection (RC-1) without an arbitrary cap.
        action tombstonePrune;            // DONE (server, 8025fb2, D0019): the deliberate OPERATOR prune — SqliteIndex::prune_tombstones(floor) drops tombstones below the floor + raises history_floor to it (atomic); Vault::prune_history clamps floor to [current floor, version]; POST /api/admin/prune-history exposes it (server-admin; floor defaults to current version). Safe via the horizon (a below-floor client keeps+notifies). Resolves issueUnboundedTombstones.
        action stpaSuspicionPropagation;  // OPEN (D0017): keel change — propagate suspicion from architectural elements (Controller/ControlAction/Feedback/Sensor/ProcessModel) to the dependent STPA analysis artifacts (UCA/scenario/safety-requirement) via the #Analyzes/#RealizedBy/#Senses linkage, so an architecture change auto-flags reassessment; hazards/losses excluded. Toolkit-repo implementation, deferred.
        action stpaSafetyAnalysis;        // DONE (D0016; analysis verdict recorded 2026-09-07 - every completeness criterion checked against the model; the D0017 reanalysis mechanism is stpaSuspicionPropagation, upstream #66, not a criterion of this analysis): full STPA authored (.tracking/safety/) — Step 1 (Losses L-1..L-4, boundary/env, Hazards H-1..H-8, Constraints SC-1..SC-8), Step 2 (control structure: 7 controllers, 5 processes + models, 20 control actions, 11 feedback, 5 sensors, 5 actuators, responsibility->SC), Step 3 (UCA-1..UCA-20 + Controller Constraints C-1..C-20), Step 4 (12 loss scenarios), and 19 SafetyRequirements — ALL 19 now REALIZED by shipped work + traced (SR-19 orphan-chunk-quota realized by SEC#4/round1DeferredHardening 0.10.32). Architecture-facing linkage edges authored for suspicion propagation (D0017). The AUTHORING is complete; the formal DONE is intentionally withheld until the D0017 reanalysis/propagation mechanism lands — which is a keel/TOOLKIT-repo change (not this project repo), so it cannot be completed here
        action adminSplitDeploy;          // DONE (server, 8951b43, D0021): admin surface split safe-by-default — /admin + /api/admin/* bind to a private localhost-only port by default (ADMIN_BIND_ADDR override; =merge opt-out); public port serves sync/login only. public_app/admin_app routers + two servers; integration test admin_split_isolates_surfaces; deploy docs + upgrade note.
        action adminPortalEnhancements;   // DONE (server, 8951b43, D0021): persisted admin SET (.admins.json) + promote/revoke (bootstrap always admin); registration toggle; grantee autocomplete + fuzzy match (GET /api/admin/usernames); owner self-service vault delete (DELETE /api/vault). Re-dispositions issueShareEnumeration.
        action serverConcurrencyResidual; // DONE (backlog sprint 1): the two MED critique-R8 concurrency residuals. issueDoubleOpenRace FIXED — state.rs vault() now serializes cold opens behind a per-(user,vault) open lock with a double-checked cache, so two concurrent first-accesses to a cold vault open/reindex exactly once (a BUSY-losing reindex can no longer leave a corrupt handle cached); test state::concurrent_cold_open_of_one_vault_opens_once_and_shares_a_single_handle. issueChangesOnAsyncWorker was ALREADY FIXED (verified) — api.rs changes() runs the full-manifest scan through blocking()/spawn_blocking (the "R10-D3" offload), exactly the prescribed fix; the issue was stale-open. Full server suite 172 green. Resolves issueDoubleOpenRace + issueChangesOnAsyncWorker.
        action critiqueR8Fixes;           // DONE (0.10.35, 6f19f71): a fresh 4-lens adversarial critique (DI/security/concurrency/correctness) of the SQLite/history-horizon/admin-split/auto-reindex work + 2 field bugs. HIGH: DI-H1 (D0019 reset detection bypassed on the connect path → silent resurrection — now unified across connect+poll via reconcileFull/noteHistory), Conc-H1 (cold-open auto-reindex ran on the async worker → scoped() made async + offloaded to spawn_blocking), owner-delete 404 in split (/api/vault shared to both surfaces). MED: DI-M1 (floor tracked before the poll short-circuit), DI-M2 (persist lastVersions for rewind-across-restart), DI-M3 (floor bumps only when tombstones actually lost), usernames require_admin (enumeration), merge port-compare + ephemeral-:0. Field: "connecting" persisted through the initial sync (markReconciling → Syncing), Docker admin unreachable (compose binds 0.0.0.0:8091 + host-loopback publish). Critics confirmed router isolation / authz / atomicity / tombstone-delete / lock-ordering sound.
        action autoReindex;               // DONE (server, b50012d, D0022): Vault::open auto-repairs the index (reindex from disk) when it's unusable-but-recoverable (empty-with-data / corrupt DB / dangling ref from the mirror), instead of locking the vault for a manual reindex; stays ERROR only when truly unrecoverable (file lost from disk AND store, or unsafe names → needs Force). One-click Reindex per vault in admin "My vaults". Resolves the "numerous reindex errors" the SQLite migration caused.
        action deletedVaultRecreatePrompt; // DONE (0.10.34, 1881e94, D0021): the plugin flags vaultGone on a 404 and offers a deliberate "Re-create vault from this device" button (recreateVault → createVault + reconnect → repopulate from local). No-data-loss made explicit.
        // e2eEncryption: DECLINED — D0009 (keep trusted-server model); design spec retained as history.

        first m1Protocol then m2ChunkingBinary;
        first m2ChunkingBinary then m3ConflictMerge;
        first m3ConflictMerge then m4MultiTenant;
        first m4MultiTenant then m5Mobile;
        first m5Mobile then m6Packaging;
        first m6Packaging then goal1ConfigUx;
        first goal1ConfigUx then rel06FixSet;
        first rel06FixSet then l3GuiPass;
        first l3GuiPass then l4MobileOndevice;
        first b9DurabilityStreaming then streamingReassembly;
        first rel06FixSet then vaultSharingP1;
        first vaultSharingP1 then shareClientConsume;

        // ---- DoD criteria (one line each; naming contract <task>DoD) ----
        verification m1ProtocolDoD : Test { :>> id = "7b1e4c4e-6590-40f0-a3dd-1e93c18fc890"; :>> method = VerificationMethod::test; :>> procedureText = "server cargo tests + headless two-client E2E: login, changes/commit/get/delete, WS push, and create/edit/delete propagation between two real clients all green."; }
        verification m2ChunkingBinaryDoD : Test { :>> id = "0bc03b3a-c80d-42b1-8098-5ad168194b17"; :>> method = VerificationMethod::test; :>> procedureText = "chunker unit tests + E2E: content-defined chunks, content-addressed store, binary round-trips byte-identical, duplicate content does not re-upload (chunks/missing) — green."; }
        verification m3ConflictMergeDoD : Test { :>> id = "30f45630-3ea6-4488-81c0-685855d60e05"; :>> method = VerificationMethod::test; :>> procedureText = "reconcile + merge unit tests: decide() table, diff3 three-way merge on concurrent edits, conflict-copy on unmergeable/binary divergence, delete-vs-edit safety, C2 empty-server guard — green."; }
        verification m4MultiTenantDoD : Test { :>> id = "48379685-a4ce-40c0-90e0-2d9f0fd2b107"; :>> method = VerificationMethod::test; :>> procedureText = "server tests + E2E: accounts with argon2id, multiple named vaults per account at vault-scoped routes, files in one vault never appear in another — green."; }
        verification m5MobileDoD : Test { :>> id = "a99d3e15-441d-413e-9ebf-c954242cbdfb"; :>> method = VerificationMethod::inspect; :>> procedureText = "manifest isDesktopOnly:false; transport uses requestUrl; chunker/hasher are pure-TS (WebCrypto) with no desktop-only deps — inspected. NOTE: on-device run is tracked separately as l4MobileOndevice."; }
        verification m6PackagingDoD : Test { :>> id = "1464c8a4-5409-45f5-9a39-62eef04bde1b"; :>> method = VerificationMethod::inspect; :>> procedureText = "root manifest.json + versions.json valid; .github/workflows/release.yml builds + publishes main.js/manifest.json/styles.css on a version tag (verified green on 0.6.0); BRAT-installable; Docker/reverse-proxy example shipped."; }
        verification goal1ConfigUxDoD : Test { :>> id = "49b1a827-b90d-40f3-bb2a-67c6b22795b9"; :>> method = VerificationMethod::test; :>> procedureText = "wizardsteps + connstr + configsync unit tests + headless wizard E2E: guided setup connects + picks a vault; status-first settings render; config-sync permutation matrix passes — green."; }
        verification rel06FixSetDoD : Test { :>> id = "7ceb01f4-6bf1-4897-9331-0c44acc1c281"; :>> method = VerificationMethod::test; :>> procedureText = "reconcile switchTo download/upload/merge/empty-auto tests; 99 client unit tests + standalone config-permutation matrix green; tsc + build clean; 0.6.0 released."; }
        verification b7AuthHardeningDoD : Test { :>> id = "4d2f71d4-4177-41ca-968f-6207fdc249bf"; :>> method = VerificationMethod::test; :>> procedureText = "durable/expiring/revocable server tokens (hashed, 30-day, revoked on account delete); client token-only persistence option; shipped TLS/public-exposure guidance (deploy/ Caddy example + docs/deployment.md). Optional client-side E2EE carved out to e2eEncryption. Server + client tests green."; }
        verification b9DurabilityStreamingDoD : Test { :>> id = "3f17347d-5959-4a58-ac42-56146df4c3e2"; :>> method = VerificationMethod::test; :>> procedureText = "B9 Part A (D0010): append-only .sync-index.log — commits/deletes append absolute records instead of rewriting the index; replay reconstructs on reopen; torn trailing record discarded; malformed complete record -> ERROR; chunk_refs recomputed from files; compaction snapshots + truncates. Server tests green."; }
        verification streamingReassemblyDoD : Test { :>> id = "1b001637-4710-4ef6-8d6c-bc269e43bcd8"; :>> method = VerificationMethod::test; :>> procedureText = "streamFileToDisk appends chunks to disk (~one chunk in RAM) via an AppendHandle; applyPull streams downloads >= 8 MiB when the io supports it (base hash-only) and a large download bypasses the size gate by streaming; uploads stay gated. Desktop ObsidianVaultIo streams via Electron Node fs (temp + fsync + rename), mobile falls back to buffered. Client tests green (real Obsidian desktop/mobile = L3/L4)."; }
        verification b11ParallelChunkDoD : Test { :>> id = "18e57bf3-f917-4e18-838a-1c12b3db8d6b"; :>> method = VerificationMethod::test; :>> procedureText = "chunk transfer parallelized via a bounded Promise pool; large-file sync wall-clock materially reduced vs the sequential baseline; E2E large-file timing improved."; }
        verification l3GuiPassDoD : Test { :>> id = "1cdcb701-7762-4540-955b-f99b188ef23c"; :>> method = VerificationMethod::demo; :>> procedureText = "manual pass in a real Obsidian desktop instance: 0.6.0 setup wizard, settings groups, single indicator, and the vault-switch modal (download/upload/merge) behave as specified. PROGRESS 2026-09-07: an automated demonstration was attempted through the real-Obsidian Playwright layer and STOPPED honestly - the machine's Obsidian is 1.5.8, below manifest minAppVersion 1.11.0 (SettingGroup absent), so a settings-tab demo there is not the shipped product (issueE2eObsidianBelowMinAppVersion; the layer now skips loudly on such an install). Needs an operator with Obsidian >= 1.11.0: run the wizard (command selfsync:setup), the settings tab (Status / Connection / What syncs / Conflicts groups + collapsed Advanced), the single status-bar indicator, and the switch-vault modal (Sync this vault to -> Switch -> Merge / Download / Upload). Still a demo, still the operator's."; }
        // RAN: l3GuiPassDoD judged 2026-11-11 at 2164682 as an automated demonstration through real Obsidian 1.12.4 (app 1.15.0), above minAppVersion 1.11.0. The spec client/e2e-obsidian/guipass.pwspec.ts drives each named surface through the UI. The wizard opens by the selfsync:setup command from a vault with no connection. It takes the server URL, the account and a new vault name, and the seeded note lands on the server. The settings tab shows the Status, Connection and What syncs groups. Advanced starts collapsed and expands on its chevron. Conflicts is absent, by design since the 0.6.0 DoD was written: settings.ts renderConflicts returns early when nothing is pending. The spec asserts that absence. Exactly one status-bar element carries the SelfSync aria-label. The switch-vault modal lists the target under Sync this vault to. Switch opens the content prompt with Merge, Download and Upload. Merge converges the note to the target vault on the server. Runs: 1 passed (13.4s) and 1 passed (13.3s), two in a row. The spec skips loudly below minAppVersion as the layer does. tsc clean. No plugin change. Verdict PASS.
        part l3GuiPassDoDR1 : TestResult { :>> id = "d0a6ba01-c564-4bc6-acb8-a71b1be53e3b"; :>> outcome = VerdictKind::proposed; :>> judgedAgainst = "2164682"; :>> judgedAt = "2026-11-11"; :>> judgedBy = "ai"; }
        // RAN: Owner's words: 'accept all recommendations. proceed' (console, 2026-11-11, Statement st021). The AI's prompt named the claim: the automated demonstration in guipass.pwspec.ts stands as the L3 GUI pass. The owner accepts it on the evidence of l3GuiPassDoDR1, two green runs on Obsidian 1.12.4 at 2164682.
        part l3GuiPassDoDR2 : TestResult { :>> id = "2896acfb-0d08-45a0-9cad-20d3dd96cd35"; :>> outcome = VerdictKind::pass; :>> judgedAgainst = "475ef54"; :>> judgedAt = "2026-11-11"; :>> judgedBy = "wweatherholtz"; }
        verification l4MobileOndeviceDoD : Test { :>> id = "24eeafa6-25c4-4f41-b1c6-fa47fffa593c"; :>> method = VerificationMethod::demo; :>> procedureText = "on-device mobile run (iOS/Android): foreground sync, resumable initial sync, indicator visible, within the on-device performance budget."; }
        verification vaultSharingP1DoD : Test { :>> id = "34cea90b-79f1-4f3f-b6f9-ae9d8c6b0da6"; :>> method = VerificationMethod::test; :>> procedureText = "per the vault-sharing spec: .shares.json ACL + owner-qualified vault routes + server-side authorization (read vs read-write; non-grantee denied); registration policy (closed/open + single-use invite tokens); web admin UI over /api/admin/* for account + share management (role-checked, no hash/token leakage) — server + admin-API + UI tests green."; }
        verification shareClientConsumeDoD : Test { :>> id = "440a15ee-7b92-4fc8-ba5e-470cc7a86212"; :>> method = VerificationMethod::test; :>> procedureText = "the plugin's vault switcher lists owned + shared vaults; syncing a vault shared with you works end to end; read-only shares disable local->remote push; transport uses owner-qualified routes."; }
        verification configSyncSafetyDoD : Test { :>> id = "c0f1a5cc-5001-4a10-9b20-a1b2c3d40041"; :>> method = VerificationMethod::test; :>> procedureText = "reconcile: an accepts()-filtered path is skipped entirely (no phantom base -> no manufactured deletion); config removals + same-file divergence are recorded for adjudication (never auto-delete, never auto-resurrect, no note-style conflict copy); resolveConfigConflict applies the user's local/remote choice; one file's error never aborts the whole reconcile. 12 new reconcile tests; full client suite 125 green; 0.10.4 shipped."; }
        verification requirementTraceabilityBackfillDoD : Test { :>> id = "c0f1a5cc-5002-4a10-9b20-a1b2c3d40042"; :>> method = VerificationMethod::inspect; :>> procedureText = "every SystemRequirement now carries a #Verify edge from a Test (tier-satisfaction SR-verified 0/15 -> 19/19); the four new config-sync SRs carry Given/When/Then acceptance scenarios; the config-sync capability is #Capability-rooted to nConfigSync (requirement-rootedness non-vacuous)."; }
        verification settingsGroupingPolishDoD : Test { :>> id = "c0f1a5cc-5003-4a10-9b20-a1b2c3d40043"; :>> method = VerificationMethod::inspect; :>> procedureText = "settings within each group are organized intelligently after studying comparable Obsidian plugins' settings layouts (not one atomized container per setting); a before/after review confirms the grouping reads sensibly. INSPECTED at end-of-project (26dc385): the settings tab (settings.ts display → renderSetup/renderConnection/renderWhatSyncs/renderAdvanced) presents a status-first card + four concern-grouped, headed sections, each a set of named+described Settings — NOT one atomized container per setting. The grouping was designed into the goal-#1 config-UX overhaul (the whole point of which was escaping LiveSync's notoriously confusing settings), so there was never an atomized 'before' to rework; the pass confirms it reads sensibly. Criteria met."; }
        verification critiqueClientWaveDoD : Test { :>> id = "c0f1a5cc-5004-4a10-9b20-a1b2c3d40044"; :>> method = VerificationMethod::test; :>> procedureText = "5 confirmed client data-integrity/correctness defects from the 3-lens adversarial critique fixed, each with a BDD test: DI-1 partial-shrink bulk-delete ratio guard, DI-2 download hash verification, CO-1 stale-base clear on both-absent, CO-2 offline->idle recovery on syncDone, CO-3 config edit-vs-delete adjudication. Full client suite 153 green; shipped 0.10.14."; }
        verification capabilityShareLinksDoD : Test { :>> id = "c0f1a5cc-50ca-4a10-9b20-a1b2c3d400ca"; :>> method = VerificationMethod::test; :>> procedureText = "Capability share-links (D0023) work end to end. Server GREEN (cargo test 91 lib + 29 admin): sharelinks.rs create_then_redeem_once_binds_and_consumes + expired/unknown/revoked-do-not-redeem + list-owner-scoped-survives-reopen; admin.rs share_link_create_redeem_binds_a_grant_and_is_single_use (grantee reaches the owner-qualified route after redeem, single-use) + share_link_owner_scoped_and_revoke_blocks_redeem. Client GREEN (vitest, full suite 292): sharelink.test codec round-trip + no-perm-in-link + rejects-bad; modals-ui.dom RedeemShareLinkModal redeems (+ empty guard) + ShareManageModal Create-link calls createShareLink. tsc + esbuild build clean."; }
        verification testHardeningClientDoD : Test { :>> id = "c0f1a5cc-5f17-4a10-9b20-a1b2c3d40f17"; :>> method = VerificationMethod::test; :>> procedureText = "The new client suites are green and client coverage rose (COMPUTED, not attested — reproduce via `cd client && CI=true SELFSYNC_REQUIRE_E2E=1 npx vitest run --coverage`, floors in vitest.config.ts). Added: test/transport.test.ts (CAS/error mapping, timeout race, diagnose() ladder, login mustChange, errText — fixed the tautological https test), test/vaultswitch.dom.test.ts (merge=no-confirm; download/upload gated both ways; SF1 read-only+localData→prompt not auto-download; read-only omits upload; fork-collision confirm), test/confirm.dom.test.ts (confirm/cancel/dismiss→false), test/devicelink.dom.test.ts (link value + QR, no password), test/configdir.dom.test.ts (direction per read-only), test/merge-eol.test.ts (CRLF regression + conflict + large-input). merge3 CRLF fix verified by the flipped-to-passing regression. Resolves issueMergeCrlf."; }
        part testHardeningClientDoDR1 : TestResult { :>> id = "7ebcbe56-717d-4ce3-867b-3660891b6589"; :>> outcome = VerdictKind::pass; :>> judgedAgainst = "a8ab2ec"; :>> judgedAt = "2026-07-14"; :>> judgedBy = "ai"; }
        verification testHardeningServerDoD : Test { :>> id = "c0f1a5cc-5f18-4a10-9b20-a1b2c3d40f18"; :>> method = VerificationMethod::test; :>> procedureText = "The new server suites are green and server line coverage rose 86.4%→90.0% (COMPUTED — reproduce via `cd server && cargo llvm-cov --summary-only`; floor `--fail-under-lines 89`). tests/ws.rs (10 tests, ws.rs 13.5%→76%): subprotocol-token auth (valid/missing/garbage/empty), per-user cap→503, global-reserve rollback, ConnGuard teardown counter→0, revoke-mid-session, must_change gate. tests/hardening.rs (8 tests): concurrent-commit CAS race (exactly one 200/one 409), DoS bounds (chunk 400/body 413/10k-hash 400), degraded 503-not-empty-manifest, vaults-per-user cap, corrupt-store fail-loud, api.rs error mapping + idempotent leave/delete. Flaky config_defaults_and_env fixed (Mutex-serialized, env restored). Full server suite 171 tests green."; }
        part testHardeningServerDoDR1 : TestResult { :>> id = "6392b30f-6980-4a6b-867b-36608d5da765"; :>> outcome = VerdictKind::pass; :>> judgedAgainst = "a8ab2ec"; :>> judgedAt = "2026-07-14"; :>> judgedBy = "ai"; }
        verification realObsidianE2eSmokeDoD : Test { :>> id = "c0f1a5cc-5f19-4a10-9b20-a1b2c3d40f19"; :>> method = VerificationMethod::test; :>> procedureText = "The real-Obsidian e2e smoke passes locally: `cd client && npm run build && npm run test:obsidian-e2e`. The spec (client/e2e-obsidian/smoke.pwspec.ts) spawns a real server, stages a temp vault with the built plugin (settings nested under data.settings so it auto-connects), launches an ISOLATED Obsidian via pre-seeded obsidian.json + --remote-debugging-port + connectOverCDP, dismisses the trust/community-plugins prompts, then asserts isPluginEnabled+isPluginLoaded('selfsync') AND that welcome.md syncs to the server (serverHasFile via /api/v/smoke/meta). Green in ~5-12s. Self-skips when Obsidian isn't installed (obsidianAvailable / OBSIDIAN_PATH) — local/nightly, not per-PR CI. NOTE: this is the SMOKE scope (plugin loads + one-way sync round-trip); multi-device/conflict/status-UI scenarios are follow-ups on the same harness."; }
        part realObsidianE2eSmokeDoDR1 : TestResult { :>> id = "cdc796a5-d161-4d1c-ab00-ddba1eba6be0"; :>> outcome = VerdictKind::pass; :>> judgedAgainst = "026c4bc"; :>> judgedAt = "2026-07-14"; :>> judgedBy = "ai"; }
        verification realObsidianE2eMultiDeviceDoD : Test { :>> id = "c0f1a5cc-5f1a-4a10-9b20-a1b2c3d40f1a"; :>> method = VerificationMethod::test; :>> procedureText = "Two-device convergence passes locally: `cd client && npm run build && npm run test:obsidian-e2e`. convergence.pwspec.ts spawns a real server + one vault ('conv'), stages TWO temp vaults, launches TWO isolated Obsidian instances on distinct CDP ports (19222/19223) + user-data-dirs, and asserts: both plugins load and reach a healthy (idle/syncing/connecting, never offline) status; a note created on device A (real app.vault.create) converges to device B (readNote); and a modify on B flows back to A. Green ~13-20s. Self-skips without Obsidian; local/nightly, not per-PR CI. Live divergent-conflict deliberately omitted (flaky through two auto-syncing GUIs; conflict logic covered headlessly)."; }
        part realObsidianE2eMultiDeviceDoDR1 : TestResult { :>> id = "61857e46-1af3-47c6-8e87-647e04b2421a"; :>> outcome = VerdictKind::pass; :>> judgedAgainst = "95a5884"; :>> judgedAt = "2026-07-14"; :>> judgedBy = "ai"; }
        verification postOverhaulHardeningDoD : Test { :>> id = "c0f1a5cc-5f1b-4a10-9b20-a1b2c3d40f1b"; :>> method = VerificationMethod::test; :>> procedureText = "(1) vitest bump verified: `cd client && npm run test:cov` on Node 24 completes EXIT 0 with 388 passed / 2 skipped and all thresholds met (lines/stmts 76.26%, branches 84.15%, functions 66.49%) under vitest 3.2.7 — the Node-24 coverage-provider crash is gone and no test broke across the 2→3 major bump. (2) Dockerfile fix by inspection: server/Dockerfile ENV no longer contains SYNC_USER/SYNC_PASSWORD (only DATA_ROOT/BIND_ADDR); config.rs still defaults admin/admin and weak_admin_refused still blocks boot on the default, so runtime provisioning is required — behavior unchanged, secret no longer baked into image layers. Resolves issueDockerfileEnvSecret."; }
        part postOverhaulHardeningDoDR1 : TestResult { :>> id = "5f60f866-0f19-4cf4-b86c-14eaf8dd2cc0"; :>> outcome = VerdictKind::pass; :>> judgedAgainst = "d5eeb87"; :>> judgedAt = "2026-07-15"; :>> judgedBy = "ai"; }
        verification falseAbsenceDeleteFixDoD : Test { :>> id = "c0f1a5cc-5f1c-4a10-9b20-a1b2c3d40f1c"; :>> method = VerificationMethod::test; :>> procedureText = "delete-remote requires CONFIRMED absence (reconcile.ts confirmedAbsent — io.exists/read, never io.list()); enumerateConfig logs a dir-list failure (main.ts). Verified by reconcile.test 'delete-remote requires CONFIRMED absence' (2 tests): a file absent from list() + failing to read but whose entry EXISTS is NOT tombstoned (deletions has no entry, server still has it); a genuinely-deleted file (list omits + really gone) STILL tombstones (real deletes propagate). FAIL-FIRST proven: neutralizing the confirmedAbsent guard makes the placeholder test fail, restoring it passes. Full reconcile.test 107 passed, no regression; tsc clean. Resolves issueFalseAbsenceDelete."; }
        part falseAbsenceDeleteFixDoDR1 : TestResult { :>> id = "26783339-3b7f-40c3-b47d-b829108bf489"; :>> outcome = VerdictKind::pass; :>> judgedAgainst = "ec926f9"; :>> judgedAt = "2026-07-15"; :>> judgedBy = "ai"; }
        verification configListSetMergeDoD : Test { :>> id = "c0f1a5cc-5f1d-4a10-9b20-a1b2c3d40f1d"; :>> method = VerificationMethod::test; :>> procedureText = "community-plugins.json union-merge + real-Obsidian config-sync coverage, all green. UNIT (configsync.test): mergeEnabledPluginsJson unions ids sorted, treats empty as empty set, returns null on non-string[] (falls back); isEnabledListConfig matches only community-plugins.json. INTEGRATION (reconcile.test, fail-first proven — neutralizing the branch fails 'keeps c'): a pull of a shorter enabled-list KEEPS the locally-enabled plugin and pushes the union so the server converges; a longer list is adopted. Existing generic config-adjudication tests retargeted to app.json (community-plugins.json no longer adjudicates on divergence — it unions). Full headless client suite 396 passed / 2 skipped; tsc clean. E2E (client/e2e-obsidian/configsync.pwspec.ts via npm run test:obsidian-e2e): two real Obsidian devices, config sync community-surface on — A's testplugin folder + enabled-list propagate to B, and B's own 'brat' is NOT disabled by A's shorter list (union end-to-end), green ~20s (local/nightly, self-skips without Obsidian). Resolves issueConfigListDisable."; }
        part configListSetMergeDoDR1 : TestResult { :>> id = "693ab9c0-f188-4f3d-8529-f283eea47edb"; :>> outcome = VerdictKind::pass; :>> judgedAgainst = "571be38"; :>> judgedAt = "2026-07-15"; :>> judgedBy = "ai"; }
        verification cmmcComplianceBacklogDoD : Test { :>> id = "c0f1a5cc-5f1e-4a10-9b20-a1b2c3d40f1e"; :>> method = VerificationMethod::confirmation; :>> procedureText = "The CMMC/800-171 CUI-controls POA&M is empty and mooted. Its only two items — SC.3.13.11 (FIPS-validated crypto) and SC.3.13.16 (CUI encrypted at rest) — are CUI-DATA-specific; the owner confirmed on 2026-07-15 that this deployment stores no CUI, so both are formally NOT APPLICABLE, recorded as D0027 (a mooting Decision that now #Resolves issueCmmcFips + issueCmmcAtRest). No code work remains. Completion here is the recorded scope decision, not an implementation; the human attestation is D0027's acceptance. Service-protecting controls stay in force; a CUI-in-scope deployment reopens both per D0027."; }
        part cmmcComplianceBacklogDoDR1 : TestResult { :>> id = "a76570e2-e3a1-4b82-a40f-6598a5c1a80a"; :>> outcome = VerdictKind::pass; :>> judgedAgainst = "ac94ed3"; :>> judgedAt = "2026-07-15"; :>> judgedBy = "wweatherholtz"; }
        verification deliverableTestGateDoD : Test { :>> id = "c0f1a5cc-5f16-4a10-9b20-a1b2c3d40f16"; :>> method = VerificationMethod::test; :>> procedureText = "The WHOLE deliverable test gate is GREEN at HEAD and the ratcheting coverage FLOORS hold — a COMPUTED, reproducible verdict (D0026), never a prose count. Reproduce via the reverify contract (.engine/contracts/reverify.toml: `cd server && cargo test --locked`; `cd server && cargo clippy --all-targets -- -D warnings`; `cd client && npm test`) and the coverage floors enforced in CI + locally (`cd client && npm run test:cov` → vitest v8 thresholds lines/stmts 67, branches 83, functions 56; `cd server && cargo llvm-cov --fail-under-lines 85`). CI (.github/workflows/ci.yml) builds the server binary before the client job so the real-server integration + sharing specs RUN (SELFSYNC_REQUIRE_E2E=1 makes a missing binary a hard failure, not a silent skip). Coverage TREND is the clientLineCoverage/serverLineCoverage Indicators. `keel reverify` re-runs this gate at HEAD on drift and stamps a fresh judged-at-HEAD TestResult — the immutable point-in-time record."; }
        part deliverableTestGateDoDR1 : TestResult { :>> id = "d083a717-6b21-401d-aaae-d1df894596bb"; :>> outcome = VerdictKind::pass; :>> judgedAgainst = "29e970e"; :>> judgedAt = "2026-07-14"; :>> judgedBy = "ai"; }
        part deliverableTestGateDoDR2 : TestResult { :>> id = "80b94093-3a44-4d2b-867b-366093d2bcd9"; :>> outcome = VerdictKind::pass; :>> judgedAgainst = "a8ab2ec"; :>> judgedAt = "2026-07-14"; :>> judgedBy = "ai"; }
        part deliverableTestGateDoDR3 : TestResult { :>> id = "5ddb3d72-35a1-409e-9e10-f522e6b4466e"; :>> outcome = VerdictKind::pass; :>> judgedAgainst = "9e17a39"; :>> judgedAt = "2026-07-14"; :>> judgedBy = "ai"; }
        part deliverableTestGateDoDR4 : TestResult { :>> id = "49958b14-4083-4d1b-b47d-b82917ca9809"; :>> outcome = VerdictKind::pass; :>> judgedAgainst = "ec926f9"; :>> judgedAt = "2026-07-15"; :>> judgedBy = "ai"; }
        part deliverableTestGateDoDR5 : TestResult { :>> id = "0283fc12-a836-4b21-8529-f283f7c7411f"; :>> outcome = VerdictKind::pass; :>> judgedAgainst = "571be38"; :>> judgedAt = "2026-07-15"; :>> judgedBy = "ai"; }
        part deliverableTestGateDoDR6 : TestResult { :>> id = "95499f4e-57f5-4dcc-999c-2a13769265e4"; :>> outcome = VerdictKind::pass; :>> judgedAgainst = "ddb4b78"; :>> judgedAt = "2026-07-18"; :>> judgedBy = "claudeOpus"; }
        part deliverableTestGateDoDR7 : TestResult { :>> id = "eab56df9-d950-42cc-8b31-7ec2924610a4"; :>> outcome = VerdictKind::pass; :>> judgedAgainst = "0b786b1"; :>> judgedAt = "2026-07-18"; :>> judgedBy = "claudeOpus"; }
        part deliverableTestGateDoDR8 : TestResult { :>> id = "b024451f-46c2-44d4-8658-16ce52070414"; :>> outcome = VerdictKind::pass; :>> judgedAgainst = "5c18d67"; :>> judgedAt = "2026-07-18"; :>> judgedBy = "claudeOpus"; }
        part deliverableTestGateDoDR9 : TestResult { :>> id = "f9f8831c-b055-4ef1-b8d8-680302c99fcf"; :>> outcome = VerdictKind::pass; :>> judgedAgainst = "c22b866"; :>> judgedAt = "2026-07-18"; :>> judgedBy = "claudeOpus"; }
        part deliverableTestGateDoDR10 : TestResult { :>> id = "12ecb426-b9bd-4a79-8d08-f3669ca09e5f"; :>> outcome = VerdictKind::pass; :>> judgedAgainst = "8e9c76e"; :>> judgedAt = "2026-07-18"; :>> judgedBy = "claudeOpus"; }
        part deliverableTestGateDoDR11 : TestResult { :>> id = "b073aa95-5ff3-4536-b493-31b93075059e"; :>> outcome = VerdictKind::pass; :>> judgedAgainst = "20d87e5"; :>> judgedAt = "2026-07-18"; :>> judgedBy = "claudeOpus"; }
        part deliverableTestGateDoDR12 : TestResult { :>> id = "a049039a-74e2-44ce-b4c4-d1c03af14656"; :>> outcome = VerdictKind::pass; :>> judgedAgainst = "23bfeb8"; :>> judgedAt = "2026-07-18"; :>> judgedBy = "claudeOpus"; }
        part deliverableTestGateDoDR13 : TestResult { :>> id = "f49fe1e1-4183-4898-95e5-45bb1b992578"; :>> outcome = VerdictKind::pass; :>> judgedAgainst = "123b8a0"; :>> judgedAt = "2026-07-18"; :>> judgedBy = "claudeOpus"; }
        part deliverableTestGateDoDR14 : TestResult { :>> id = "63fec485-9d9e-4065-a299-15ab84caebdb"; :>> outcome = VerdictKind::pass; :>> judgedAgainst = "7dbb918"; :>> judgedAt = "2026-07-18"; :>> judgedBy = "claudeOpus"; }
        part deliverableTestGateDoDR15 : TestResult { :>> id = "2ce52308-f219-4707-a7fa-416d51afa875"; :>> outcome = VerdictKind::pass; :>> judgedAgainst = "56a1116"; :>> judgedAt = "2026-07-19"; :>> judgedBy = "claudeOpus"; }
        part deliverableTestGateDoDR16 : TestResult { :>> id = "270b04b1-d8c2-42e5-8a32-11f970258b8f"; :>> outcome = VerdictKind::pass; :>> judgedAgainst = "671d6cb"; :>> judgedAt = "2026-07-19"; :>> judgedBy = "claudeOpus"; }
        part deliverableTestGateDoDR17 : TestResult { :>> id = "38f41cd0-6625-42a2-8043-4f846a82a096"; :>> outcome = VerdictKind::pass; :>> judgedAgainst = "764b417"; :>> judgedAt = "2026-07-19"; :>> judgedBy = "claudeOpus"; }
        part deliverableTestGateDoDR18 : TestResult { :>> id = "c71bf3ec-8764-4870-a233-66bb7664be10"; :>> outcome = VerdictKind::pass; :>> judgedAgainst = "9d5dccd"; :>> judgedAt = "2026-07-19"; :>> judgedBy = "claudeOpus"; }
        part deliverableTestGateDoDR19 : TestResult { :>> id = "83552f8c-a268-4a0b-b633-cdb198a55ab9"; :>> outcome = VerdictKind::pass; :>> judgedAgainst = "f96b217"; :>> judgedAt = "2026-07-19"; :>> judgedBy = "claudeOpus"; }
        part deliverableTestGateDoDR20 : TestResult { :>> id = "4a0655a3-654f-44b3-ada4-084d44b171a5"; :>> outcome = VerdictKind::pass; :>> judgedAgainst = "18f9cc2"; :>> judgedAt = "2026-07-28"; :>> judgedBy = "claudeOpus"; }
        part deliverableTestGateDoDR21 : TestResult { :>> id = "1b0207a4-2f54-4ace-b7e4-5cf8db49998a"; :>> outcome = VerdictKind::pass; :>> judgedAgainst = "6c33630"; :>> judgedAt = "2026-07-29"; :>> judgedBy = "claudeOpus"; }
        part deliverableTestGateDoDR22 : TestResult { :>> id = "d2f8343d-fd35-485c-8606-a7e00bde94f8"; :>> outcome = VerdictKind::pass; :>> judgedAgainst = "3b4a55e"; :>> judgedAt = "2026-07-29"; :>> judgedBy = "claudeOpus"; }
        part deliverableTestGateDoDR23 : TestResult { :>> id = "687a89bb-b3a9-4d2a-aa40-7df8a6e732a2"; :>> outcome = VerdictKind::pass; :>> judgedAgainst = "9d2fd65"; :>> judgedAt = "2026-07-29"; :>> judgedBy = "claudeOpus"; }
        part deliverableTestGateDoDR24 : TestResult { :>> id = "5a365787-adfd-42ad-ae9c-4e8b090fbe6f"; :>> outcome = VerdictKind::pass; :>> judgedAgainst = "f8a3436"; :>> judgedAt = "2026-07-29"; :>> judgedBy = "claudeOpus"; }
        verification hfStatusSurfacingAndPreviewDoD : Test { :>> id = "c0f1a5cc-5f15-4a10-9b20-a1b2c3d40f15"; :>> method = VerificationMethod::test; :>> procedureText = "1.6.0 status-surfacing + config-preview copy + persistent long-op state (client), real-tested. CLIENT GREEN (vitest full suite 335 passed / 2 skipped; tsc --noEmit clean; esbuild build OK). Verified: plugin-wiring statusDisplay case asserts a saved pendingSwitch yields label 'Switching vault…' (persistent switch state, survives suspend since pendingSwitch is persisted). By inspection: main.ts adds the 'Sync status' command (id=status) toasting statusDisplay(engine.phase()) label+detail — the on-demand mobile readout; statusDisplay branches on pendingSwitch before the resuming/idle branches; configdir.ts ConfigDirectionModal intro copy states 'only files that differ change — everything else is left alone, and after this, later edits on either side reconcile normally'. Honest scope: no persistent on-screen TEXT indicator (platform: no mobile status bar, addAction icon-only) and no true diff/count preview (needs a local-vs-server compare) — both recorded as partial mitigations on their Issues. Resolves issueMobileStatusTextless/issueBlindConfigOverwrite/issueLongOpTransientCompletion. Ships 1.6.0."; }
        verification hfConfirmAndSidePickingDoD : Test { :>> id = "c0f1a5cc-5f13-4a10-9b20-a1b2c3d40f13"; :>> method = VerificationMethod::test; :>> procedureText = "1.5.2 in-app confirm + side-picking consistency (client), real-tested. CLIENT GREEN (vitest full suite 335; tsc + esbuild clean): modals-ui.dom updated to the standardized config labels ('Use this device's' / 'Use the synced version') and still resolves local/remote; settings-ui.dom Sign-out wiring test updated (confirmModal mocked true; awaits the now-async confirm) + still fires signOut. Wiring by inspection: confirm.ts confirmModal() (in-app modal, warn button) replaces window.confirm in vaultswitch (fork/leave/mirror ×3) + settings (sign out); note-conflict + config-conflict 'keep-side' buttons no longer .setCta(); configdir 'Use the synced version' no longer .setCta(). Resolves issueSidePickingInconsistent/issueNativeConfirmMobile. Ships 1.5.2."; }
        verification hfStatusAndWarningsDoD : Test { :>> id = "c0f1a5cc-5f12-4a10-9b20-a1b2c3d40f12"; :>> method = VerificationMethod::test; :>> procedureText = "1.5.1 HF status + warning fixes (client), real-tested. CLIENT GREEN (vitest full suite 335; tsc + esbuild clean): plugin-wiring 'statusDisplay gives actionable status' extended — read-only idle → {label:'Synced (read-only)', detail:'your edits stay on this device'} (not 'Fully synced'); existing Fully-synced / Synced-(polling) cases still green. Wiring by inspection: renderLight glyph for idle is now the steady check (or 'lock' when vaultReadOnly), never refresh-cw — spinner reserved for connecting/syncing; vaultswitch.applySwitch confirm wording recalibrated (download → 'moved to this device's trash (recoverable there)'; no blanket 'can't be undone'). Resolves issueStatusIndicatorMisleads/issueMiscalibratedSwitchWarning. Ships 1.5.1."; }
        verification deferUxEnhancementsDoD : Test { :>> id = "c0f1a5cc-5f11-4a10-9b20-a1b2c3d40f11"; :>> method = VerificationMethod::confirmation; :>> procedureText = "wweatherholtz reviewed the three UX enhancements flagged as deliberately-not-done at the end of the UI/UX critique pass (obsidian:// protocol handler, setup-wizard state persistence, deeper IA restructures + residual lows) and directed 'record these as declined items' (2026-07-13) — an explicit human disposition to DEFER, not act, for now. No code changes; the deferral is the outcome. Resolves issueNoProtocolHandler / issueWizardStatePersistence / issueDeepIaRestructure as tracked-declined."; }
        verification surfaceSharingAndConflictsDoD : Test { :>> id = "c0f1a5cc-5f10-4a10-9b20-a1b2c3d40f10"; :>> method = VerificationMethod::inspect; :>> procedureText = "1.5.0 surface sharing + conflicts (client). tsc + esbuild clean (no import cycle from main→vaultswitch/accountui — their main import is type-only); full client suite 335 green. Verified by INSPECTION: main.ts registers addCommand 'switch-vault' (SwitchVaultModal), 'redeem' (openRedeem→RedeemShareLinkModal), 'resolve-conflicts' (openConflicts routes note→config→notice), and renames the setup command; settings.ts unconfigured card gains a 'Redeem a share link' button (plugin.openRedeem); startRedeem opens SwitchVaultModal after an already-signed-in redeem. Commands/modals not unit-tested (no command-palette / modal-render seam under the stub; the underlying redeem/switch logic is covered elsewhere). Resolves issueSharingConflictsDiscoverability. Ships 1.5.0."; }
        verification pluginAdoptionRestartHintDoD : Test { :>> id = "c0f1a5cc-5f0f-4a10-9b20-a1b2c3d40f0f"; :>> method = VerificationMethod::inspect; :>> procedureText = "1.4.0 plugin-adoption restart hint + placeholder (client). tsc + esbuild clean; full client suite 335 green. Verified by INSPECTION: settings.renderPluginChecklist computes needsRestart = ids adopted (pluginAllow) AND not in local manifests, and renders a mod-warning banner counting them with mobile-specific 'fully close and reopen Obsidian (swipe the app away)' wording; when ids is empty (server list not yet reported) it renders a 'Checking the server for plugins…' placeholder instead of returning silently. Not unit-tested (the checklist only renders with real Obsidian manifests, absent under the stub). Resolves issuePluginAdoptionSilentRestart. Ships 1.4.0."; }
        verification guardDestructiveActionsDoD : Test { :>> id = "c0f1a5cc-5f0e-4a10-9b20-a1b2c3d40f0e"; :>> method = VerificationMethod::inspect; :>> procedureText = "1.3.2 destructive-action guards (client). tsc + esbuild clean; full client suite 335 green (settings-ui.dom beforeEach stubs confirm()=true so the Sign-out wiring test still fires). Verified by INSPECTION: vaultswitch.applySwitch returns early unless confirm() accepts for mode!=='merge', naming which side's files are deleted; vaultswitch.doFork returns early when this.vaults includes the name and confirm() is declined; settings.ts Sign out returns early unless confirm() accepts. confirm()-gating isn't unit-tested (global confirm has no seam in the modal harness; the underlying switchTo upload/download logic is already reconcile-tested). Resolves issueUnguardedDestructiveActions. Ships 1.3.2."; }
        verification uxPolishBundleDoD : Test { :>> id = "c0f1a5cc-5f0d-4a10-9b20-a1b2c3d40f0d"; :>> method = VerificationMethod::inspect; :>> procedureText = "1.3.1 UX polish bundle (client). tsc + esbuild clean; full client suite 335 green (modals-ui.dom updated to the 'Keep the other device's' label; the removed statusTitle test dropped). Copy/feedback changes verified by INSPECTION against the critique's file:line findings: main.ts recovery messages name Reconfigure/Switch (not the command name); log-viewer toasts prefixed 'SelfSync:'; reload wording → 'fully close and reopen Obsidian'; conflict breadcrumb → 'Settings → Conflicts'. settings.ts max-file-size blur handler (notice + revert on invalid). setupwizard.ts banner <p> gains white-space:pre-wrap. noteconflict.ts button 'Keep the other device's'. accountui.ts change-password warning extended. wizardsteps.ts statusTitle + Phase import removed (dead code). Resolves issueUxQuickWins. Ships 1.3.1."; }
        verification forkVaultDoD : Test { :>> id = "c0f1a5cc-5f0c-4a10-9b20-a1b2c3d40f0c"; :>> method = VerificationMethod::inspect; :>> procedureText = "1.3.0 fork-vault (client, FEATURE). tsc + esbuild clean; full client suite 336 still green (no covered behavior changed). Verified by INSPECTION: main.forkVault(name) = createRemoteVault(name) then switchToVault(name,'upload','',false) — pure composition of already-tested primitives (switchTo 'upload' has reconcile tests; createRemoteVault is a thin transport wrapper), so the fork copies local content into a new OWNED, editable vault and switches this device to it, original untouched. vaultswitch.ts adds a 'Fork this vault' setting (name field sanitized/validated via sanitizeVaultName/isValidVaultName, doFork → forkVault). Not unit-tested directly (forkVault's steps are network-bound; no seam in the wiring harness). Ships 1.3.0."; }
        verification statusDetailAndResumingDoD : Test { :>> id = "c0f1a5cc-5f0b-4a10-9b20-a1b2c3d40f0b"; :>> method = VerificationMethod::test; :>> procedureText = "1.2.0 status detail + Resuming state (client, FEATURE), real-tested. CLIENT GREEN (vitest full suite 336; tsc + esbuild clean): plugin-wiring 'statusDisplay gives actionable status' — syncing+pending → {Syncing…, N pending}; syncing+0 → {Syncing…, checking for changes} (never bare); resuming flag → label 'Resuming…' for connecting/syncing; idle → 'Fully synced' vs 'Synced (polling)' by realtimeConnected. Wiring by inspection: onResume sets resuming + renderLight; onPhase clears it once phase settles (not connecting/syncing); onProgress clears it when pending>0; renderLight + settings status row both render statusDisplay (label + detail); ui-dom-harness gained statusDisplay/isResuming. Ships 1.2.0."; }
        verification adoptServerPluginsDoD : Test { :>> id = "c0f1a5cc-5f0a-4a10-9b20-a1b2c3d40f0a"; :>> method = VerificationMethod::test; :>> procedureText = "1.1.0 adopt-server-plugins (client, FEATURE), real-tested. CLIENT GREEN (vitest full suite 335; tsc + esbuild clean): reconcile 'reports the community-plugin ids present on the server (so a fresh vault can adopt them)' — reconcileAll fires onRemotePlugins with the distinct plugin ids from the server manifest (dataview, templater), notes excluded. Wiring by inspection: main.setServerPluginIds stores the set + refreshes settings on change; getServerPluginIds; installAllServerPlugins adopts every server plugin download-only; settings.renderPluginChecklist renders the UNION of installed + server-side ids (server-only labelled 'from the sync — will be installed'; a synced-but-not-installed row shows 'downloads from the sync'), with a contextual 'Install all from the sync' button when there are not-installed server plugins; ui-dom-harness gained getServerPluginIds/installAllServerPlugins. Extends D0025 (accepted by wweatherholtz — 'for a new vault there's nothing to setup the plugins … proceed'). Ships 1.1.0."; }
        verification pendingExcludesDeclinedDoD : Test { :>> id = "c0f1a5cc-5f09-4a10-9b20-a1b2c3d40f09"; :>> method = VerificationMethod::test; :>> procedureText = "1.0.39 pending-excludes-declined (client), real-tested. CLIENT GREEN (vitest full suite 334; tsc + esbuild clean): reconcile 'does NOT count a remote file this device DECLINES as pending — reports it as declined instead' — with accepts=notes-only, a server plugin file (.obsidian/plugins/dataview/main.js) is NOT counted in onProgress (max pending 1, the note), IS surfaced via onDeclined, and is not pulled, while the accepted note pulls. Existing pending tests (reports PENDING work / drives to 0) still green (they pass no accepts → unaffected). Wiring by inspection: reconcileDelta applies the same accepts filter + onDeclined; main.noteDeclined logs a coalesced, change-only message. Resolves issuePendingCountsDeclinedFiles. Ships 1.0.39."; }
        verification configSyncPerPluginDirectionDoD : Test { :>> id = "c0f1a5cc-5f08-4a10-9b20-a1b2c3d40f08"; :>> method = VerificationMethod::test; :>> procedureText = "1.0.38 per-plugin config direction + collapsible plugin list (client), extends D0025. CLIENT GREEN (vitest full suite 333; tsc + esbuild clean). Pure/decision coverage carried by configAutoResolveChoice + configSurfaceOf (configgroup tests). Wiring by inspection: configSync.pluginDir (persisted, fresh-loaded); main.ts setPluginSync (adds to allowlist + records direction default = communityConfigDir() else download; read-only→download), setPluginDir (per-plugin override; read-only→download); recordConfigConflict prefers pluginDir[pluginIdOf(path)] over the surface direction for a plugin path; settings.ts renderPluginChecklist renders a COLLAPSIBLE <details> (open when ≤8, pluginsExpanded persists across re-renders) with a per-row membership toggle + an inline download/upload dropdown shown only when synced (read-only shows 'download only'); ui-dom-harness gained setPluginSync/setPluginDir/communityConfigDir. Extends D0025 (accepted by wweatherholtz — 'I like the lighter form … plugins collapsible even if not all one mode'). Ships 1.0.38."; }
        verification configSyncFirstContactDirectionDoD : Test { :>> id = "c0f1a5cc-5f07-4a10-9b20-a1b2c3d40f07"; :>> method = VerificationMethod::test; :>> procedureText = "1.0.37 config-sync first-contact direction (client), implements D0025, real-tested. CLIENT GREEN (vitest full suite 333; tsc + esbuild clean): configgroup 'configSurfaceOf' maps each config path to its surface (core/hotkeys/appearance/snippets/community) + null for note/unrecognized; 'configAutoResolveChoice' auto-resolves ONLY a no-base ('conflict-copy') divergence with a pending direction (download→remote, upload→local) and returns null for a later edit (merge/edit-wins), no direction, or no surface; settings-ui.dom category toggle applies via setConfigSurface (harness updated). Wiring by inspection: recordConfigConflict consults configAutoResolveChoice(reason, configSurfaceOf(path), pendingConfigDir) and calls resolveConfigConflict on a hit else prompts; ConfigDirectionModal offers download + (non-read-only) upload; settings master/per-surface toggles set the direction, read-only forces download + starts surfaces off. Implements D0025 (accepted by wweatherholtz). Ships 1.0.37."; }
        verification configSyncEventDrivenDoD : Test { :>> id = "c0f1a5cc-5f06-4a10-9b20-a1b2c3d40f06"; :>> method = VerificationMethod::test; :>> procedureText = "1.0.36 event-driven config detection (client), real-tested. CLIENT GREEN (vitest full suite 328; tsc + esbuild clean): plugin-wiring 'a config-related UI event (css-change) triggers a config scan — event-driven, not just polled' (firing css-change increases the reconcile changes() count) + 'a config UI event does NOTHING when config sync is OFF' (gated on configSync.enabled — no needless scan). scheduleConfigScan coalesces (a pending timer swallows a burst), rate-limits (CONFIG_EVENT_MIN_GAP_MS=5s), and guards unloading; wired to workspace css-change + layout-change; the 30s periodic scan remains the backstop. Test harness: obsidian-stub workspace.on now captures handlers so fire() can trigger UI events. Ships 1.0.36."; }
        verification fastCheapConfigScanDoD : Test { :>> id = "c0f1a5cc-5f05-4a10-9b20-a1b2c3d40f05"; :>> method = VerificationMethod::test; :>> procedureText = "1.0.35 fast/cheap config scan (client), real-tested. CLIENT GREEN (vitest full suite 326; tsc + esbuild clean): reconcile 'config scan fast-path: an unchanged config file (matching size+mtime) is NOT re-read/hashed' (io.read spy shows 0 reads); 'config scan still DETECTS a new local config file and pushes it' (empty base → pushed, so the fast-path doesn't hide real changes); 'config scan stamps an unchanged-but-unstamped file so the NEXT scan skips it'. CONFIG_SCAN_INTERVAL_MS is 30_000. The app-resume trigger (visibilitychange → onResume → forces a config scan) is wired in onload behind a typeof-document guard (verified by inspection; plugin-wiring tests boot the plugin through this path — registerDomEvent added to the obsidian test stub). Resolves issueConfigSyncMobileLatency. Ships 1.0.35."; }
        verification editorStatusCleanupOnUnloadDoD : Test { :>> id = "c0f1a5cc-5f04-4a10-9b20-a1b2c3d40f04"; :>> method = VerificationMethod::inspect; :>> procedureText = "1.0.34 in-editor-icon cleanup on unload (client). tsc + esbuild clean; full client suite 323 still green (nothing it covers changed). The fix is a 2-line addition to onunload — 'for (const el of this.editorActionEls) el.remove(); this.editorActionEls.clear();' — IDENTICAL to the already-working cleanup in setEditorStatus(false); verified by INSPECTION that view.addAction elements (which Obsidian does NOT auto-clean on unload, unlike ribbon/status-bar items) are now removed, so a reload/update can't orphan them and stack duplicates. Within-run add is already idempotent via the editorViews WeakSet. NOT unit-tested: the obsidian test stub doesn't model view.addAction / plugin-unload DOM lifecycle. Resolves issueEditorStatusIconLeakOnReload. Ships 1.0.34."; }
        verification connErrorAbortsPassDoD : Test { :>> id = "c0f1a5cc-5f03-4a10-9b20-a1b2c3d40f03"; :>> method = VerificationMethod::test; :>> procedureText = "1.0.33 connection-error-aborts-pass (client), real-tested. CLIENT GREEN (vitest full suite 323; tsc + esbuild clean): reconcile 'a CONNECTION failure (DNS) ABORTS the pass — one error, not one-per-file' (20 remote files, every pull throws UnknownHostException → reconcileAll rejects, onFileError fired 0 times); 'a single-file error is still ISOLATED' (a 'disk full' on one file → that file in onFileError, the rest sync, no throw); 'isConnectionError classifies host/connection failures but NOT per-file content/read errors' (UnknownHost/getaddrinfo-ENOTFOUND/ECONNREFUSED/ERR_INTERNET_DISCONNECTED true; disk-full/ENOENT/content-verification/unsafe-path false). Applied to reconcileAll + reconcileDelta mapPools (shared connAbort flag) + the config for-loop. Resolves issueConnErrorPerFileFlood. Ships 1.0.33."; }
        verification conflictReadOnlyAndBinaryCorrectnessDoD : Test { :>> id = "c0f1a5cc-5f01-4a10-9b20-a1b2c3d40f01"; :>> method = VerificationMethod::test; :>> procedureText = "1.0.31 conflict/sync correctness (client), real-tested. CLIENT GREEN (vitest full suite 320; tsc + esbuild clean): reconcile 'NO-BASE divergence: adopts the owner's version WITHOUT a conflict copy' (read-only field fix — remote adopted byte-for-byte, no copy, onConflict/onReadOnly not fired); 'NO-BASE BINARY divergence (read-write): keeps BOTH — never lossy-collapsed' (F1 — two invalid-UTF-8 blobs that decode to the same U+FFFD string are NOT treated equal; copy preserved); 'an EXISTING conflict copy on a read-only share is NOT reported as won't sync'; existing read-only merge test (base + both changed → copy kept) still green; sharelink 'fails CLOSED — unknown/malformed perm is read-only' (F6). By inspection (DOM/queue-timing not unit-fixtured): resolveNoteConflict re-check before write (F3), startPolling unloading guard (F4), listNoteConflicts original-must-exist filter (F5), modal auto-dismiss gated on isMergeable (F1 second locus). Ships 1.0.31."; }
        verification shareRedeemStoreConsistencyDoD : Test { :>> id = "c0f1a5cc-5f02-4a10-9b20-a1b2c3d40f02"; :>> method = VerificationMethod::test; :>> procedureText = "Share-redeem cross-store consistency (server), real-tested. SERVER GREEN (cargo test — lib 93, admin 32, all suites 0 failed; clippy no new warning): shares grant_rolls_back_in_memory_when_save_fails (F2a — a grant whose save() fails leaves owner_grant_count 0 and permission None, so the redeem rollback can't strand a live grant); admin self_redeem_does_not_burn_the_link (F2b — owner self-redeem returns 200 and the intended recipient can STILL redeem and reach the vault); existing share_link_create_redeem_binds_a_grant_and_is_single_use + owner_scoped_and_revoke_blocks_redeem still green. Resolves issueGrantSaveRollback/issueSelfRedeemBurnsLink. Ships in the server image."; }
        verification shareLinkRedeemConsumeLastDoD : Test { :>> id = "c0f1a5cc-50ff-4a10-9b20-a1b2c3d400ff"; :>> method = VerificationMethod::test; :>> procedureText = "1.0.30 server share-link redeem consume-last, real-tested (server). SERVER GREEN (cargo test — lib 92, admin integration 31, all suites 0 failed; cargo clippy adds no new warning): sharelinks::tests::unredeem_rolls_back_a_claim_so_a_failed_grant_does_not_burn_the_link — a claimed link isn't redeemable until unredeem() restores it, then it's re-redeemable (invite not burned), single-use still holds for a genuine consume, and unredeem of an unknown token is a no-op; existing create_then_redeem_once_binds_and_consumes + share_link_create_redeem_binds_a_grant_and_is_single_use + owner_scoped_and_revoke_blocks_redeem stay green. Handler wiring verified by inspection (the cap path needs 1000 grants to fixture, impractical): admin::share_link_redeem drops the shares lock and calls unredeem(&req.token) on BOTH the at-cap and grant-Err branches before returning. Resolves issueShareLinkBurnedOnFailedGrant. Ships in the 1.0.30 server image."; }
        verification shareRefreshedOnConnectDoD : Test { :>> id = "c0f1a5cc-50ee-4a10-9b20-a1b2c3d400ee"; :>> method = VerificationMethod::test; :>> procedureText = "1.0.30 share-permission-refresh-on-connect, real-tested (client-only). CLIENT GREEN (vitest full suite 316; tsc + esbuild clean): sharelink.test 'resolveShareGrant — cached permission is a projection of the server grant' — an owned vault (empty owner) is notShared (no extra call); read→read-only; readWrite-upgrade reflected even when the client cached read-only; a grant absent from the list is revoked (owner removed access). Wiring: connect() calls refreshShareGrant(token) after the health check and before the first reconcile, updating settings.vaultReadOnly and throwing on revocation with a clear card message (files untouched, one-shot toast, auto-recovers on re-grant). Kills the vaultOwner/vaultReadOnly dual-source found in the client audit. Ships 1.0.30."; }
        verification conflictModelDerivedFromVaultDoD : Test { :>> id = "c0f1a5cc-50dd-4a10-9b20-a1b2c3d400dd"; :>> method = VerificationMethod::test; :>> procedureText = "1.0.29 conflict-model re-architecture (D0024), real-tested (client-only). CLIENT GREEN (vitest; tsc + esbuild clean): base/reconcile 'deriveNoteConflicts — the SINGLE source of truth': derives conflicts from the vault file list, ignores ordinary AND look-alike user files (no 14-digit ts), and a removed copy simply drops out (no stale entry); existing originalOfConflictCopy safety cases still green; modals-ui.dom conflict + settings-ui.dom still green. Changes: settings.noteConflicts array + recordNoteConflict/clearNoteConflict removed; listNoteConflicts = deriveNoteConflicts(vault paths); resolveNoteConflict idempotent (guards a missing copy); onConflict just logs + refreshes the projected count. Implements D0024 (accepted by wweatherholtz). Ships 1.0.29."; }
        verification pendingProgressAndConflictResilienceDoD : Test { :>> id = "c0f1a5cc-50dc-4a10-9b20-a1b2c3d400dc"; :>> method = VerificationMethod::test; :>> procedureText = "1.0.28 pending-progress + conflict-modal resilience, real-tested (client-only). CLIENT GREEN (vitest 310 passed; tsc + esbuild clean): reconcile.test 'reports PENDING work (not files examined) and drives to 0' (3 real transfers → 3 pending → 0) + 'an already-in-sync vault reports 0 pending' (total files irrelevant); syncstate 'Syncing… <detail>' still green. Changes: onProgress single-arg (pending); reconcileAll pre-classifies pending from remote-hash≠base / real tombstones / new-local; reconcileDelta counts the changed set; main.ts shows 'N pending'. NoteConflictModal auto-dismiss wraps EACH entry in try/catch so a stale 'File does not exist' entry is skipped, not fatal (fixes 'Couldn't load conflicts'). Ships 1.0.28."; }
        verification conflictModalFixAndSyncProgressDoD : Test { :>> id = "c0f1a5cc-50db-4a10-9b20-a1b2c3d400db"; :>> method = VerificationMethod::test; :>> procedureText = "1.0.27 conflict-modal display fix + sync progress, real-tested (client-only). CLIENT GREEN (vitest 309 passed; tsc + esbuild clean): reconcile.test 'reconcileAll reports onProgress and finishes at done===total'; syncstate.test 'syncing tip includes the progress detail (Syncing… 12/174)'; existing modals-ui.dom conflict + settings-ui.dom still green. Changes: NoteConflictModal.run() shows an immediate placeholder + progress-counted cosmetic auto-dismiss + try/catch (no more blank body); reconcileAll fires onProgress(done,total); main.ts throttles to integer-% and exposes syncProgressText(); syncstate light('syncing', detail) + settings status row + tooltip render 'Syncing… N/M'. Ships 1.0.27."; }
        verification falseEolConflictFixAndDiffDoD : Test { :>> id = "c0f1a5cc-50da-4a10-9b20-a1b2c3d400da"; :>> method = VerificationMethod::test; :>> procedureText = "1.0.26 false-EOL-conflict fix + diff view, real-tested (client-only). CLIENT GREEN (vitest 307 passed; tsc + esbuild clean): reconcile.test 'sameIgnoringEol' (CRLF/LF + trailing-newline cosmetic; real edits/added lines not) + 'no-base divergence that is ONLY line endings -> converge on remote, NO conflict copy' (asserts zero (conflict… copies + local converges to the remote bytes); merge.test 'unifiedLineDiff' (context/−other/+this-device; EOL-only = zero changed lines). Fix: sameIgnoringEol guard in reconcileOne merge/conflict-copy branch. UX: NoteConflictModal auto-dismisses cosmetic copies + renders a real line diff (unifiedLineDiff via exported merge.lcsPairs). Root cause: independent identical copies (Windows CRLF vs mobile LF) + no common base on first sync/adopt. Ships 1.0.26."; }
        verification granteeLeaveShareDoD : Test { :>> id = "c0f1a5cc-50d9-4a10-9b20-a1b2c3d400d9"; :>> method = VerificationMethod::test; :>> procedureText = "1.0.25 grantee leave/decline a share, real-tested (server+client). SERVER GREEN (cargo test 149: 91 lib + 31 admin + 2 reg + 5 sharing + 21 sync) with the new DELETE /api/shared (api::leave_share, grantee forced to caller, audited). E2E GREEN against the real server (sharing-e2e, 2 tests, ~17s): the extended must-change→redeem-link→sync test now also asserts the grantee's owner-qualified route is 200 before leaving, LEAVE succeeds, then 403 after, and the vault is gone from listShared. CLIENT: transport.leaveShare + plugin.leaveSharedVault (disconnects if it's the current vault; local files kept) + Switch-modal 'Leave' button (confirm). tsc + esbuild clean. Server change rebuilds :latest; plugin ships 1.0.25."; }
        verification settingsPanelTargetedCleanupDoD : Test { :>> id = "c0f1a5cc-50d8-4a10-9b20-a1b2c3d400d8"; :>> method = VerificationMethod::test; :>> procedureText = "1.0.24 settings-panel targeted cleanup, real-tested (client-only). CLIENT GREEN (vitest settings-ui.dom 9 + modals-ui.dom 14; tsc + esbuild clean): the DOM tests still find Disconnect + Reconfigure (now under Advanced, same container) and drive their plugin actions; RedeemShareLinkModal still routes to startRedeem. Changes: fillStatus drops the Server 'Reconfigure' button + Vault 'Redeem link' + status-row 'Disconnect'; renderAdvanced gains a 'Connection' row with Reconfigure + Disconnect (+ a desc distinguishing them from Sign out); SwitchVaultModal gains 'Redeem a share link' (opens RedeemShareLinkModal → startRedeem). Scope = user-approved 'Targeted fixes'. Ships 1.0.24."; }
        verification redeemE2ECoverageDoD : Test { :>> id = "c0f1a5cc-50d7-4a10-9b20-a1b2c3d400d7"; :>> method = VerificationMethod::test; :>> procedureText = "Redeem/share end-to-end coverage, RUN GREEN against the real server binary (cargo debug built; vitest sharing-e2e.spec — 2 tests pass in 18s). New test 'must-change account → change password → redeem a share LINK → sync the shared vault': admin creates a raw (must-change) recipient; loginFull returns mustChange=true and /api/vaults returns 403; changePassword yields a token that gets 200; owner mints a readWrite share LINK; recipient redeems it (grant bound, matchObject owner/vault/perm), appears in listShared, syncs the owner-qualified vault and reads the note; a second redeem of the same link rejects (single-use). NodeTransport extended (loginFull/createUserRaw/changePassword/createShareLink/redeemShareLink/listShared/rawStatus). tsc clean. Test-only — no shipped code change, no release."; }
        verification wizardForcedPasswordChangeDoD : Test { :>> id = "c0f1a5cc-50d6-4a10-9b20-a1b2c3d400d6"; :>> method = VerificationMethod::test; :>> procedureText = "1.0.23 wizard forced-password-change, real-tested (client-only). CLIENT GREEN (vitest 302 passed; tsc + esbuild clean): modals-ui.dom 'a must-change account is prompted for a new password before any other call' — spies show login returns {mustChange:true}, the wizard shows the New/Confirm password step, listVaults is NOT called until changePassword(server, temp-tok, tempPw, newPw) runs, then listVaults is called with the fresh token. HttpTransport.login returns {token, mustChange} (reads must_change_password); loginRemote unwraps .token. Fixes the 'vaults: HTTP 403' an admin-created account (e.g. wi1y) hit on sign-in. Ships 1.0.23."; }
        verification guidedRedeemViaSetupDoD : Test { :>> id = "c0f1a5cc-50d5-4a10-9b20-a1b2c3d400d5"; :>> method = VerificationMethod::test; :>> procedureText = "1.0.22 guided-redeem-via-setup, real-tested (client-only). CLIENT GREEN (vitest 301+; tsc + esbuild clean): modals-ui.dom 'Redeem routes to startRedeem' (the modal now delegates to plugin.startRedeem, not redeemShareLink directly) + empty-link guard; sharelink redeemTargetError cases still green (they decide guided-vs-direct). Design: SetupWizardModal gains a redeem mode (opts.shareLink) — server prefilled from the link, no vault-picker, login/register then finishRedeem() persists the session + redeems + adopts the shared vault + reconnects; the wizard paste hand-off prefills in place; plugin.startRedeem routes not-set-up/wrong-server → guided wizard, already-set-up → direct redeem + 'use Switch'. Removes the anti-pattern of needing to be logged in before a share link could prefill/onboard. Ships 1.0.22."; }
        verification redeemNotSetUpGuardAndDirectDoD : Test { :>> id = "c0f1a5cc-50d4-4a10-9b20-a1b2c3d400d4"; :>> method = VerificationMethod::test; :>> procedureText = "1.0.21 redeem not-set-up guard + direct-redeem, real-tested (client-only). CLIENT GREEN (vitest 301 passed; tsc + esbuild clean): sharelink.test redeemTargetError — empty deviceServer → 'Set up SelfSync and sign in to <server> first' (NOT a new-URL crash), different server → 'This link is for <server>', same server → null. redeemShareLink now delegates to redeemTargetError before touching normalizeServer (which was the surviving new URL('') throw). The setup-link paste hand-off redeems DIRECTLY with a result Notice (RedeemShareLinkModal no longer opened from the wizard; unused imports removed). Ships 1.0.21."; }
        verification shareLinkUrlParseFixDoD : Test { :>> id = "c0f1a5cc-50d3-4a10-9b20-a1b2c3d400d3"; :>> method = VerificationMethod::test; :>> procedureText = "1.0.20 share/setup-link parse fix, real-tested (client-only). CLIENT GREEN (vitest sharelink + connstr, 16; tsc + esbuild clean): new regression 'parses a real percent-encoded link' redeems selfsync-share://redeem?server=https%3A%2F%2Fnotes2.willweatherholtz.com&token=51f0… → server https://notes2.willweatherholtz.com + the token, where the old new-URL-on-bare-host path threw 'Invalid URL' on the Android WebView; existing encode/parse/normalize/reject cases still pass. Both parseShareLink and parseSetupLink now use URLSearchParams on the query substring (no scheme-swap new URL). Ships 1.0.20."; }
        verification shareCurrentVaultOnlyDoD : Test { :>> id = "c0f1a5cc-50d2-4a10-9b20-a1b2c3d400d2"; :>> method = VerificationMethod::test; :>> procedureText = "1.0.19 share-modal simplification, real-tested (client-only). CLIENT GREEN (vitest modals-ui.dom 13; tsc + esbuild clean): new 'shares ONLY the current vault, even when the account owns several' — with settings.vaultId='notes' and owned vaults [default, notes, work], the modal renders neither 'work' nor 'default', shows a single Create link, and createShareLink is called with 'notes'; the existing Create-link + Redeem tests still pass. ShareManageModal.render() finds the current vault in myVaultShares and renders one label-free block (title 'Share this vault'); non-owned/not-yet-synced current vault shows a can't-share message; pending links filtered to the current vault."; }
        verification shareUxAndCaseInsensitiveNamesDoD : Test { :>> id = "c0f1a5cc-50d1-4a10-9b20-a1b2c3d400d1"; :>> method = VerificationMethod::test; :>> procedureText = "1.0.18 sharing/UX + case-insensitive usernames, real-tested. CLIENT GREEN (vitest 26 targeted + full suite; tsc + esbuild clean): transport errText reads r.text so share/redeem errors show the server message not 'invalid JSON'; setupwizard hands a selfsync-share:// link off to RedeemShareLinkModal (prefill) instead of 'Not a SelfSync setup link'. SERVER GREEN (cargo test: 91 lib + 31 admin + 2 reg + 5 sharing + 21 sync): admin.rs usernames_are_case_insensitive — create 'Dana' → stored 'dana', login 'DANA' 200, listed once lowercase, never mixed-case; canonicalization (trim+lowercase) at login/register/users_create/share-grantee, non-breaking (stored keys were always lowercase). Per-vault share sections explained (one per owned vault; 'default' is the bootstrap auto-create — deletable). Server change rebuilds :latest; plugin ships 1.0.18."; }
        verification usernameRuleAndUxDoD : Test { :>> id = "c0f1a5cc-50d0-4a10-9b20-a1b2c3d400d0"; :>> method = VerificationMethod::test; :>> procedureText = "Username charset + UX, server-only, real-tested. SERVER GREEN (cargo test 149): sync.rs userstore_register_verify_persist extended — safe_name accepts 'will+tag@example.com' (email + plus-addressing), still rejects uppercase ('Alice'), path separators ('a/b'), spaces, '', '..'. safe_name admits '+' and '@' (both valid URL-path + filesystem chars, no traversal); NAME_RULE constant surfaced in the 'invalid username — <rule>' error at users_create (admin) + register (public). admin_ui.html states the rule under the add-user row so expectations are set before submit. No client/plugin change (admin UI is server-embedded); the :latest server image rebuilds on push."; }
        verification skipOsJunkFilesDoD : Test { :>> id = "c0f1a5cc-50cf-4a10-9b20-a1b2c3d400cf"; :>> method = VerificationMethod::test; :>> procedureText = "1.0.17 OS-junk skip real-tested (client-only). CLIENT GREEN (vitest configsync.test, 16): isJunkFile + shouldSync skip Thumbs.db/.DS_Store/desktop.ini/.git anywhere in the path (config on OR off) and do NOT skip look-alikes (thumbs.db.md, my.git.notes.md, git/readme.md); the existing .selfsync-part/.selfsync-tmp temp cases still pass under the folded predicate. isJunkFile is an EXACT mirror of the server's vault.rs is_junk. tsc --noEmit + esbuild build clean. Result: the field-reported per-file HTTP 400 log spam on OS junk is gone (junk never attempted, no base recorded → no phantom delete)."; }
        verification vaultNameAndSizeLimitsDoD : Test { :>> id = "c0f1a5cc-50ce-4a10-9b20-a1b2c3d400ce"; :>> method = VerificationMethod::test; :>> procedureText = "1.0.16 UX fixes real-tested. CLIENT GREEN (vitest): wizardsteps.test — isValidVaultName rejects uppercase (matches server safe_name), sanitizeVaultName trims+lowercases so 'Testbrsin'→'testbrsin' passes; settings-ui.dom green with the new 'Max file size to sync (MB)' control; tsc --noEmit + esbuild build clean; full suite green. SERVER GREEN (cargo test 149: 91 lib + 30 admin + 2 reg + 5 sharing + 21 sync): admin.rs commit_over_size_limit_is_rejected (a commit declaring size > Config::max_file_bytes is 400'd at the api layer before reassembly); Config gains max_file_bytes from MAX_FILE_MB (default 512, defensive parse); vault MAX_FILE_BYTES raised to a 4 GiB absolute backstop (the real limit is the configurable api-layer check). doc-sync: README env table gains MAX_FILE_MB + the per-device setting note. Wiring: main.ts maxSyncBytes() reads settings.maxSyncMB (default 200) on BOTH platforms, replacing the hard-coded 50/200 split; over-cap files are skipped (never deleted)."; }
        verification deployComposeHardeningDoD : Test { :>> id = "c0f1a5cc-50cd-4a10-9b20-a1b2c3d400cd"; :>> method = VerificationMethod::inspect; :>> procedureText = "Compose + deploy hardening, inspected + config-validated. `build:` removed from deploy/docker-compose.yml → `image: ghcr.io/williamweatherholtz/obsidian-selfsync-server:latest`; .github/workflows/release.yml gains a server-image job (packages:write, buildx, GHCR login, build-push-action pushing :<tag> + :latest, linux/amd64) so the image the compose references is actually published on each version tag. Redundant config removed: DATA_ROOT + BIND_ADDR (image-fixed internal path/address) and the no-op `expose:` gone; only the meaningful knobs remain (SYNC_USER/PASSWORD, ADMIN_BIND_ADDR, REGISTRATION seed, LOG_LEVEL). Healthcheck added (curl -fsS http://127.0.0.1:8080/health — /health confirmed in the shared router base, served on public AND admin surfaces, lib.rs) + Caddy depends_on service_healthy. New deploy/docker-compose.noproxy.yml (server-only, sync + admin bound to 127.0.0.1). REGISTRATION semantics verified against state.rs: env seeds .registration.json only when fresh (!reg_path.exists()); the admin toggle persists via set_mode and is authoritative across reboots — documented as such. BOTH stacks pass `docker compose config` (valid). doc-sync applied: docs/deployment.md (stale `expose:` claim, first-run-seed note, noproxy + image guidance) + README env table + quick-start."; }
        verification perfHarnessScaleLatencyDoD : Test { :>> id = "c0f1a5cc-50cb-4a10-9b20-a1b2c3d400cb"; :>> method = VerificationMethod::test; :>> procedureText = "A headless real-world PERFORMANCE harness exists, runs, and produced honest numbers over the real chunk/reconcile engine. client/perf (`npm run test:perf`, separate vitest.perf.config) spawns the real server binary + headless clients: scale.perf.ts measures initial push/pull + no-op rescan by vault size (200/1000/3000 notes); latency.perf.ts measures single-edit A->B propagation as the transfer round-trip via the EVENT path (reconcilePath push + reconcileDelta apply — O(change), corrected from an earlier reconcileAll that inflated large-vault latency). RESULTS (docs/architecture/92-perf-scale-latency.md, loopback + debug build = a pessimistic floor): push 2.74/8.01/27.20 s, pull 0.45/1.36/3.71 s, no-op 41/185/373 ms (scan-skip holds sub-second at 3000 files); propagation flat 20->29 ms p50 from 50->3000 notes (O(change), not O(vault)). Harness GREEN; interpretation + caveats documented."; }
        verification perfDevicePassDoD : Test { :>> id = "c0f1a5cc-50cc-4a10-9b20-a1b2c3d400cc"; :>> method = VerificationMethod::demo; :>> procedureText = "The real-device fidelity pass: SelfSync 1.0.15 via BRAT on a real desktop + phone against a real TLS-deployed server, exercising scale (initial sync of a few-thousand-note vault, both devices) and propagation latency (single-edit A<->B round-trip on wifi + cellular, with the WS notify path observed). Protocol + results template in docs/architecture/93-real-device-perf-protocol.md. Done when the operator runs it and the results table is filled; any miss vs the pass criteria files an Issue and routes. NO result until the hardware run is performed (awaits operator)."; }
        verification acceptOpenEnumRiskDoD : Test { :>> id = "c0f1a5cc-50c9-4a10-9b20-a1b2c3d400c9"; :>> method = VerificationMethod::confirmation; :>> procedureText = "wweatherholtz accepted (2026-07-11, 'yes do both') the open-registration username-enumeration finding as an inherent tradeoff of open self-registration: de-oracling /api/register (returning a uniform response whether or not a name is taken) breaks the sign-up UX, and open mode lets anyone create accounts regardless. The operative mitigation is guidance — keep registration invite-only/closed (the default), which removes the public register surface. Accepted as a LOW residual with documented operator guidance; the closed-mode register path is already de-oracled."; }
        verification acceptMobileFsyncRiskDoD : Test { :>> id = "c0f1a5cc-50c8-4a10-9b20-a1b2c3d400c8"; :>> method = VerificationMethod::confirmation; :>> procedureText = "wweatherholtz accepted the mobile buffered-write fsync durability limitation as a known, intractable issue on 2026-07-11 ('accept mobile-fsync as a known but intractable issue'). Mobile platforms expose no fsync API, so the narrow crash-window (a pulled note lost between io.write and the OS cache flush while data.json persisted, later read as delete-remote) cannot be closed in code without breaking legitimate mobile deletions; desktop fsyncs file+dir before persisting base. Accepted as a documented platform-inherent residual."; }
        verification critResidual2DoD : Test { :>> id = "c0f1a5cc-50c7-4a10-9b20-a1b2c3d400c7"; :>> method = VerificationMethod::test; :>> procedureText = "Two residual fixes real-tested. Client GREEN (vitest): syncstate.test isWsStale (stale only once activity older than the deadline) + plugin-wiring 12 still green with the WS liveness timer wired; tsc + esbuild build clean. Server GREEN (cargo test 27 admin) with require_admin threading the ClientIp — the existing admin tests exercise require_admin on every /api/admin/* route and pass. WS half-open: server heartbeat + client liveness timer re-dials a silent socket. Audit: privileged-denied events carry source-IP."; }
        verification critResidualEasyDoD : Test { :>> id = "c0f1a5cc-50c6-4a10-9b20-a1b2c3d400c6"; :>> method = VerificationMethod::test; :>> procedureText = "The two easy residuals are real-tested. Server GREEN (cargo test): admin.rs totp_code_cannot_be_replayed_within_its_window (a consumed TOTP step is rejected on reuse); mfa_totp_full_lifecycle still green with a next-window disable code. The SC.3.13.13 model wording now describes the real mechanism (per-plugin sync allowlist; execution = Obsidian's enable step). tsc/build unaffected (server-only + doc)."; }
        verification critRoundCmmcDoD : Test { :>> id = "c0f1a5cc-50c5-4a10-9b20-a1b2c3d400c5"; :>> method = VerificationMethod::test; :>> procedureText = "CMMC assessor-round fixes are real-tested. Server GREEN (cargo test 88 lib + 26 admin): admin.rs require_admin_mfa_blocks_admin_until_totp_enrolled (REQUIRE_ADMIN_MFA=1 denies an admin without TOTP, allows after enroll/confirm — IA.3.5.3 now genuinely enforceable); config.rs refuses_known_weak_and_short_bootstrap_passwords (CM.3.4.2 rejects the whole weak/short class); the mfa.rs failed enable/disable now audit FAILURE (AU.3.3.1); ws.rs per-user WS sub-cap + guard release (SC.3.13.1). Client GREEN (vitest): transport.test SC.3.13.8 — token-bearing account calls to an http remote are refused (centralized in httpReq), https not refused. tsc + esbuild build clean. Posture reconciled honestly (3.13.8 met, 3.1.11 partial)."; }
        verification critRoundStdDoD : Test { :>> id = "c0f1a5cc-50c4-4a10-9b20-a1b2c3d400c4"; :>> method = VerificationMethod::test; :>> procedureText = "Standard critique round fixes are real-tested. Client GREEN (vitest reconcile.test, 88): a delta tombstone for a present-but-unreadable file does NOT clear base or delete (no resurrection); an R===B delta for an unreadable file does NOT delete server-side; the delete-local restore commits with expectedVersion 0 (CAS); a 'download' switch against a suspiciously-incomplete manifest refuses the mass-delete while a genuine mostly-overlapping target still mirrors its extras. Server GREEN (cargo test 87 lib + 25 admin): existing commit/ws/state suites pass with the commit permit-pool + WS must_change gate added; per-request reassembly bound already covered by commit_rejects_reassembly_exceeding_declared_size. tsc + esbuild build clean."; }
        verification uiFunctionalAuditDoD : Test { :>> id = "c0f1a5cc-50c3-4a10-9b20-a1b2c3d400c3"; :>> method = VerificationMethod::test; :>> procedureText = "UI functional-correctness: every interactive control in both UIs drives real behavior; 9 fixed defects carry regression tests. Server GREEN (cargo test 87 lib + 25 admin): admin.rs must_change_account_is_blocked_until_password_set_then_works (A3), admin_grant_and_revoke_toggles_admin_access, admin_deletes_an_account, admin_reindex_and_prune_history_http_ok, admin_invite_list_and_delete. Client GREEN (vitest): syncstate.test idle-with-realtime-DOWN not green + says polling (P4), wizardsteps.test wizardCredentials does not persist password by default (P1), plugin-wiring.test applyConfigSyncChange kicks an immediate reconcile (P2); e2e-helpers createUser now performs the forced change so the full e2e/sharing/integration-matrix suites stay green. tsc --noEmit + esbuild build clean. Browser-level: a Playwright suite (client/e2e-admin, `npm run test:admin-e2e`) drives the admin page's real click-handlers against a spawned server — 5 GREEN: login+dashboard, A3 forced-change screen end-to-end, A1 sign-out fires POST /api/logout (200), A2 MFA enable reflects ENABLED + shows recovery codes (TOTP computed in-test), registration toggle round-trips + persists. The admin browser suite is COMPREHENSIVE (20 tests, `client/e2e-admin`): every interactive control + indicator. Plugin-side browser coverage: happy-dom DOM tests render the real settings tab + modals through an enriched obsidian stub — settings-ui.dom.test (9: config master/category toggles→applyConfigSyncChange [P2], store-password, editor-status, disconnect/reconnect/sign-out, setup/log) + modals-ui.dom.test (9: ChangePasswordModal, ConfigConflictModal local/remote adjudication, NoteConflictModal mine/theirs/manual, SetupWizardModal render + pre-login guard). Full client suite green (276 passed)."; }
        verification cmmcMfaDoD : Test { :>> id = "c0f1a5cc-50c2-4a10-9b20-a1b2c3d400c2"; :>> method = VerificationMethod::test; :>> procedureText = "IA.3.5.3 multifactor authentication, real-tested. TOTP (RFC 6238, HMAC-SHA1) as a second factor for privileged (server-admin) accounts + single-use recovery codes, self-enrolled via /admin (enroll->confirm) and verified at /api/login; self-contained crypto in totp.rs (no new deps). Crypto correctness pinned to published vectors, not asserted. Tests GREEN: server lib totp.rs totp_rfc6238_vectors + hmac_sha1_rfc4231 + verify_accepts_skew_window_and_rejects_junk; server integration admin.rs mfa_totp_full_lifecycle (enroll -> confirm -> password-alone 401 -> password+TOTP 200 -> recovery code single-use -> disable -> password-alone 200). cargo 85 lib + 20 admin green."; }
        verification cmmcForcedChangeReuseDoD : Test { :>> id = "c0f1a5cc-50c1-4a10-9b20-a1b2c3d400c1"; :>> method = VerificationMethod::test; :>> procedureText = "IA.3.5.8 password-reuse history + IA.3.5.9 forced-change-on-reset, real-tested. Reuse: users.rs retains the last 5 argon2 hashes; change_password rejects the current or any recent password. Forced-change: admin create/reset flags must_change; the AuthToken extractor 403s every route but change-password/logout until a new password is set; a successful self-change clears it. Tests GREEN: server lib users.rs reuse_history_rejects_current_and_recent_passwords + must_change_flag_set_clear_and_cleared_on_remove; server integration admin.rs password_change_rejects_reuse_of_a_recent_password + admin_created_account_is_forced_to_change_password_before_use. cargo 81 lib + 19 admin green."; }
        verification critiqueServerHardeningDoD : Test { :>> id = "c0f1a5cc-5005-4a10-9b20-a1b2c3d40045"; :>> method = VerificationMethod::test; :>> procedureText = "server + coordinated fixes land, are tested (cargo), and are redeployed: SEC-2 default-admin-credential refusal (coded + cargo-green, awaiting operator redeploy), SEC-1 WS token out of the URL query string, SEC-MED-1 register-enumeration parity, SEC-MED-2 account-delete data remanence, SEC-MED-3 login rate-limiting, DI-3 commit-before-journal ordering, DI-4 reindex-refuses-incomplete-dir, client SEC-3 no auto-enable of plugin code received over a shared vault. Server cargo tests + the coordinated client release green."; }
        // SEC-MED-3 is realized as an 8-permit argon2 CONCURRENCY cap (bounds the CPU/RAM DoS); per-IP
        // request-rate throttling is a further hardening left to the reverse proxy (documented).
        verification round1CriticFixesDoD : Test { :>> id = "c0f1a5cc-5006-4a10-9b20-a1b2c3d40046"; :>> method = VerificationMethod::test; :>> procedureText = "Round-1 fresh 3-lens critic findings (18) triaged; 15 fixed + tested + shipped 0.10.17: DI#1 switchTo honors accepts() gate, DI#2 streamed downloads verify per-chunk, DI#3 pull-race conflict-copy, DI#5 event-path bulk-delete ratio guard; CONC#1 single-flight persist, CONC#2 exception-safe applying flag, CONC#3 self-healing WS re-dial, CONC#4 WS MissedTickBehavior::Delay, CONC#6 drain requeue; SEC#1 lowercase-canonical names (case-collision breach), SEC#2 argon2 offload+cap+semaphore, SEC#3 vault cap, SEC#5 512MiB ceiling, SEC#6 generic 5xx, SEC#7 reserved-name reject. 3 dispositioned accept-risk/defer (SEC#4, DI#4, CONC#5). Full client suite 162 green; server cargo 70 green; server needs redeploy."; }
        // OPEN — the 3 deferred Round-1 items (no result yet, so orient shows them outstanding).
        verification round2CriticFixesDoD : Test { :>> id = "c0f1a5cc-5008-4a10-9b20-a1b2c3d40048"; :>> method = VerificationMethod::test; :>> procedureText = "Round-2 fresh 3-lens critic findings (16) on the 0.10.17 code triaged; 15 fixed + tested + shipped 0.10.18. DI: cached chunks verified before use (closed the DI-2 hole), streamed+racing-create pull guards, pushBytes returns committed bytes for merge base, conflict copies preserve current disk bytes, accepted-only bulk-delete denominator. CONC: drainPending runs on every path (no stranded edit under a green light), direct-op failure re-queues, version cursor ASSIGN not max (rewind converges), WS-redial races (stale-timer cancel, no-backoff-inflate on lock-defer, escalate never-opened socket). SEC: case-insensitive self-folder exclusion (cred-hijack), junk-name reject (reindex-brick), WS ACL re-check on revoke, admin users_create argon2 cap. 1 accepted (residual large-file pull TOCTOU, inherent). Full client suite 163 green; server cargo 71 green; server needs redeploy."; }
        verification fsmRefactorDoD : Test { :>> id = "c0f1a5cc-500e-4a10-9b20-a1b2c3d4004e"; :>> method = VerificationMethod::test; :>> procedureText = "A timing/event-driven architecture critique found the client's REAL control state lived in scattered imperative booleans (applying/connecting/remoteDirty/pendingLocal) with the queue-drain dance re-implemented at six async entry points — the source of the whole CONC-R* race family — while syncstate.ts's FSM only drove the light. Extracted SyncEngine (syncengine.ts): the ONE authoritative operational machine — a single serial event queue with run-to-completion semantics, effects injected (fully unit-testable, 11 tests). Rewired main.ts to it: vault/WS/poll events are PRODUCERS that enqueue; connect/reconcile/reconcilePath/rews/teardown are EFFECTS; the light is a pure PROJECTION of the engine phase. Removed applying/connecting/remoteDirty/pendingLocal/wsRedialTimer/drainPending/onRemoteChanged/poll + all six try/finally blocks. Result: the redial-vs-reconnect race, mid-reconcile-poke drop, drain-stranding, and leaked-guard wedge are impossible by construction. Behavior-equivalent to 0.10.23 (same connect/reconcile/backoff/config-scan logic). tsc clean; full client suite 174 green (163 + 11 engine); shipped 0.10.24. The main.ts WIRING itself remains un-unit-tested (issueOrchestrationUntested, materially reduced — the engine core is now the testable unit)."; }
        verification pluginShareOptInDoD : Test { :>> id = "c0f1a5cc-500d-4a10-9b20-a1b2c3d4004d"; :>> method = VerificationMethod::test; :>> procedureText = "Community-plugin sync flipped from a denylist (default-share; a new install auto-pushed + could overwrite peers) to an ALLOWLIST (ConfigSyncSelection.pluginAllow): shouldSync gates a plugin folder on explicit opt-in, the self-folder exclusion still overrides the allowlist, DEFAULT is empty (nothing shared until opted in). Settings shows a per-plugin checklist (check=share) + bulk Share-all/Share-none + an N/M count; loadSettings backfills pluginAllow:[] for upgraded installs. configsync unit tests updated (self-exclusion strengthened to prove it beats the allowlist; a new/non-allowlisted plugin does NOT sync) + e2e opt dataview in; full client suite 163 green; shipped 0.10.23."; }
        verification round5CriticFixesDoD : Test { :>> id = "c0f1a5cc-500b-4a10-9b20-a1b2c3d4004b"; :>> method = VerificationMethod::test; :>> procedureText = "Round-5 (holistic + final-adversary) on 0.10.20: the final cross-boundary adversary found 5 LOW/LOW-MED (none above MED on Linux) and VERIFIED the cross-cutting invariants sound (reconstruction parity, cursor-ASSIGN, WS ACL, drain/remoteDirty, persist, argon2, canonical-path no-false-reject). 3 correctness fixes shipped 0.10.21: DI-R5#1 Unicode case-collision fold (+test), DI-R5#4 legacy invalid-name key still deletable (+test), SEC-R5#2 revoke-tokens-before-purge. The holistic completeness reviewer's verdict: the data-safety core ('a note is never silently lost') holds across all traced permutations and is well-tested; the system is production-ready for a careful self-hoster who upgrades client+server in lockstep. cargo 74 green; client 163 green."; }
        // OPEN — the completeness/robustness enhancements from the holistic round (no result yet).
        verification round5CompletenessFollowupsDoD : Test { :>> id = "c0f1a5cc-500c-4a10-9b20-a1b2c3d4004c"; :>> method = VerificationMethod::test; :>> procedureText = "NOTE (0.10.26): items (1) version handshake, (3) admin reindex, and (4) commit CAS SHIPPED under preReleaseHardening and are re-pointed there; this action now tracks only the REMAINDER — (2) test-harness the imperative orchestration layer (materially reduced by the FSM refactor + the new version/auth wiring tests, but the raw-event config pipeline + SEC-3 gate + WS revocation eviction still lack direct tests), (5) persisted-data forward-migration + (6) lazy-GC wording, and (7) the cosmetic conflict-copy edges. Original scope: (1) client<->server protocol/schema VERSION negotiation (server advertises an apiVersion + index schema tag; client checks on connect and surfaces a clear 'incompatible — upgrade' message instead of an undiagnosable retry loop) — the most likely real-world breakage for a self-hoster who auto-updates the plugin independently of the server. (2) test-harness the imperative main.ts orchestration layer (reconnect FSM, raw-event live-config pipeline, drain/remoteDirty, the SEC-3 shared-vault plugin-code gate, WS instant-push + revocation eviction) — extract into injectable units like the pure modules; this is the 0.10.4-escape code family and is currently inspect+attestation only. (3) admin-surface reindex for a shared/non-owned corrupt vault (today owner-only via curl). (4) optimistic-concurrency (expected_version/if-match) on commit to close the exact-simultaneous double-first-commit lost-update on a shared RW vault. (5) explicit persisted-data forward-migration for client base/settings + a server index schema version. (6) tighten the 'startup orphan GC' requirement wording to 'lazy first-access GC' (idle vaults GC on first open, not at boot). (7) cosmetic: streamed conflictCopyIfRaced can leave an orphan copy if the stream then throws; merge-fallback conflict tag can mismatch content on a racing save. Each lands with tests. SHIPPED 0.10.33 (10a7154): item 7 fixed (conflictCopyIfRaced returns the copy path → applyPull removes the orphan on stream-fail + skips the fallthrough double-copy; conflict copies tagged with the live-local hash), items 5/6 fixed (client data.json schemaVersion + migratePersisted seam; server SQLite schema_version meta; durable-index requirement re-worded to lazy first-access + runtime GC), item 2 fixed (a plugin-wiring test drives the raw-event config pipeline incl. the self-folder security filter). Items 1/3/4 shipped earlier under preReleaseHardening. Server 58 lib + 18 integration + 22 e2e green + clippy clean; client reconcile + plugin-wiring specs green (raw-event pipeline included); tsc + build clean."; }
        verification round4CriticFixesDoD : Test { :>> id = "c0f1a5cc-500a-4a10-9b20-a1b2c3d4004a"; :>> method = VerificationMethod::test; :>> procedureText = "Round-4 fresh 3-lens critics on the 0.10.19 code: SECURITY lens CONVERGED (0 findings — critic traced every attack surface and confirmed all prior fixes present+correct); DI 1 MEDIUM + CONC 1 LOW, both fixed + shipped 0.10.20. DI-R4#1: safe_rel_path rejects non-canonical paths (notes//a.md, trailing slash) so the raw index key can't alias/desync from the Path-normalized on-disk name (+test). CONC-R4#1: remoteDirty instant re-run centralized into drainPending's exit so every applying-releasing path gets the WS instant property. 1 sub-LOW cosmetic accepted (transient green light while polling briefly stopped, self-correcting). Convergence: 18→16→8→2 findings. Full client suite 163 green; server cargo 73 green; server needs redeploy."; }
        verification round3CriticFixesDoD : Test { :>> id = "c0f1a5cc-5009-4a10-9b20-a1b2c3d40049"; :>> method = VerificationMethod::test; :>> procedureText = "Round-3 fresh 3-lens critic findings (8) on the 0.10.18 code triaged; 6 fixed + tested + shipped 0.10.19. DI-R3#1 (MED-HIGH): clean auto-merge re-reads current disk (liveLocal) so a racing local save isn't dropped (closed the DI-R2#5 gap in the merge branch). CONC: scheduleReconnect cancels a pending WS redial (R3#1); a remote poke mid-reconcile is noted+re-run via remoteDirty (R3#3); the WS Lagged arm re-checks the ACL (R3#2). SEC: safe_rel_path rejects trailing-dot/space+all-dot names — Windows-strip index/disk desync (R3#1, +test); users_delete purges data before removing the account row + hard-errors on failure (R3#2). 2 deferred (DI streamed whole-file hash needs a streaming digest unavailable in the client runtime; reindex single-chunk needs a Rust CDC chunker). Full client suite 163 green; server cargo 72 green; server needs redeploy."; }
        verification round7RecoveryFixesDoD : Test { :>> id = "c0f1a5cc-5014-4a10-9b20-a1b2c3d40054"; :>> method = VerificationMethod::test; :>> procedureText = "Round-7 recovery/operability critique fixes, shipped 0.10.28. RC-2 (High): reindex re-materializes a file missing from disk but present in the AUTHORITATIVE chunk store (the common failed-mirror-write case — no data loss) instead of bricking the whole-vault repair; only files whose chunks are ALSO gone are truly lost and abort the reindex (DI-4 safety) unless an admin passes force (drops the provably-lost so the rest is repaired). admin reindex gains a force flag + the admin UI a force checkbox. RC-3 (Med): a 404 on connect (vault deleted/renamed server-side) surfaces an actionable 'this vault no longer exists — re-create or switch' instead of an endless retry. RC-4 (Med): per-vault admin delete (DELETE /api/admin/vault + admin-UI button). RC-1 (corrupt-reindex tombstone loss) folds into historyRebase; RC-5 (base-persist-failure conflict proliferation) tracked. Server 47 lib + integration green (new reindex_recovers_from_store_and_force_drops_truly_lost) + clippy clean; client 168 unit + 21 e2e green; tsc + build clean."; }
        verification resourceScaleFixesDoD : Test { :>> id = "c0f1a5cc-5018-4a10-9b20-a1b2c3d40058"; :>> method = VerificationMethod::test; :>> procedureText = "RS-1 + RS-4, shipped 0.10.30, storage-independent. RS-1: the per-(user,vault) handle map now evicts IDLE handles (not accessed within 10 min) that have NO live WS subscribers when it reaches MAX_CACHED_VAULTS (256) — bounding server RAM (was insert-only). Safe (active/subscribed vaults kept via handle_in_use; an evicted vault re-opens from disk; an in-flight op holds its own Arc) + non-thrashing (idle window >> the 4s poll). RS-4: setBase keeps merge-ancestor TEXT only for mergeable files <= MAX_BASE_TEXT_BYTES (1 MiB); larger text files fall back to hash-only base (still sync; conflict-copy instead of 3-way-merge on divergence) — bounding client RAM + data.json size. Server 48 lib (new idle_handle_evictable_unless_subscribed_or_recent) + integration + 21 e2e green, clippy clean; client 172 unit (new RS-4 base-cap) green; tsc + build clean."; }
        verification incrementalReconcileDoD : Test { :>> id = "c0f1a5cc-5017-4a10-9b20-a1b2c3d40057"; :>> method = VerificationMethod::test; :>> procedureText = "RS-3, shipped 0.10.29. On a remote poke, doReconcileAll reconciles ONLY the delta's changed paths via reconcileDelta (delta.upserts + delta.deletes) instead of the full reconcileAll (changes(0) + a re-hash of every local file). Deletes arrive as explicit tombstones (positive evidence); a suspicious fraction of accepted base tombstoned at once is still bulk-delete-guarded; per-file errors isolated; cursor assigned (rewind-safe). The full reconcileAll is reserved for the periodic config scan + a version rewind (mass-loss signature). Client-only + storage-independent. Client 171 unit tests (new: reconcileDelta reconciles only the delta's paths / applies a tombstone / guards a mass-tombstone) + 21 e2e green; tsc + build clean."; }
        verification sqliteMigrationDoD : Test { :>> id = "c0f1a5cc-5016-4a10-9b20-a1b2c3d40056"; :>> method = VerificationMethod::test; :>> procedureText = "Per D0018: the server index is per-vault SQLite (WAL) behind a narrow IndexStore seam, replacing .sync-index.json + .sync-index.log. Done when: an embedded SQLite dep + the IndexStore module exist; the schema (files/deletions/chunk_refs/version + a history-horizon table) is version-indexed with WAL; Vault persistence is ported (commit/delete = row writes with no whole-index clone [RS-2], changes(since) = an indexed query [RS-5], no full snapshot [RS-6], bounded cold-open [RS-7]); the JSON->SQLite forward migration was WAIVED by owner attestation (2026-07-07, 'no real data lives on the server — nuke away'): a fresh SQLite index starts empty and reindex rebuilds it from the authoritative chunk store + bind-mount mirror, so a corrupt/absent DB is quarantined (.corrupt) + opened in ERROR, then reindex repairs; and the server unit + sync suites are green on the new store. Corruption blast radius materially reduced (WAL + page checksums). SHIPPED (steps 8d96882 store / 15b2795 store-ext / 91f2397 Vault port / 05e655b e2e-teardown fix): Vault ported onto SqliteIndex behind the seam (D0018) — the whole JSON snapshot + append-only journal machinery (Index/JournalRecord/replay_journal/persist/snapshot/decref_collect) deleted; commit/delete = atomic row-level SQLite transactions (no whole-index clone [RS-2]; the transaction IS the durability + all-or-nothing the journal+manual-rollback gave), changes(since) = a version-indexed query [RS-5], no full snapshot [RS-6], bounded cold-open [RS-7]; reindex rebuilds via replace_files keeping every Round-6/7 behavior (prefer authoritative store over stale mirror, RC-2 recover-from-store, force-drop truly-lost, version-preserving, path-collision guard); the protocol/api.rs/admin.rs/client are untouched (format swap behind the Vault seam). Server 53 lib + 18 integration tests green + clippy clean; client 193 unit + real-server e2e green (E2E teardown now awaits server exit before rm — SQLite holds the DB open past kill on Windows); tsc + build clean. Postgres stays deferred behind the seam."; }
        verification serverConcurrencyResidualDoD : Test { :>> id = "c0f1a5cc-5021-4a10-9b20-a1b2c3d40061"; :>> method = VerificationMethod::test; :>> procedureText = "The two MED concurrency findings deferred from critique-R8. issueDoubleOpenRace: two concurrent first-accesses to a cold, corrupt vault both run reindex on separate SQLite connections → one hits SQLITE_BUSY and its Vault stays corrupt; if that handle wins the ns-map or_insert race, sync 503s until a manual reindex. Fix = a per-(user,vault) open lock so only one thread opens/reindexes. issueChangesOnAsyncWorker: a full-manifest changes(since=0) whole-table scan runs under the RwLock read guard on the async worker (unlike the write ops, which use spawn_blocking) → a large-vault first sync blocks a runtime worker. Fix = offload the full-manifest read to the blocking pool. DONE: issueDoubleOpenRace fixed via the per-(user,vault) open lock + double-checked cache in state.rs::vault() (test: state::concurrent_cold_open_of_one_vault_opens_once_and_shares_a_single_handle — 16 threads pounce on one cold vault, all succeed, all share one handle); issueChangesOnAsyncWorker verified ALREADY offloaded (api.rs changes() wraps rlock+scan in blocking()/spawn_blocking, the R10-D3 fix). Full server suite 172 passed (cargo test); the double-open corrupt-BUSY race is timing-dependent + LOW likelihood, so the fix is structural (correct-by-construction) with the concurrent-open path guarded by the test."; }
        part serverConcurrencyResidualDoDR1 : TestResult { :>> id = "395f8c76-2d46-424a-97b7-1f833e39b2c6"; :>> outcome = VerdictKind::pass; :>> judgedAgainst = "a0dfd0a"; :>> judgedAt = "2026-07-15"; :>> judgedBy = "ai"; }
        verification critiqueR8FixesDoD : Test { :>> id = "c0f1a5cc-5020-4a10-9b20-a1b2c3d40060"; :>> method = VerificationMethod::critique; :>> procedureText = "Fresh independent 4-lens critique (data-integrity, security, concurrency, correctness) vs the D0018/D0019/D0021/D0022 code, findings adversarially verified against the source before fixing. CONFIRMED + FIXED (shipped 0.10.35, 6f19f71): DI-H1 HIGH (history-reset detection + notice bypassed on the connect path → silent resurrection of deleted files after a server floor-advance; unified detection across connect+poll — reconcileAll returns its ChangesResponse, reconcileFull wires onKeptAbsent on connect, noteHistory detects/notifies/records on both paths). Conc-H1 HIGH (cold-open auto-reindex, a whole-vault rehash, ran inline on the async worker via scoped() → scoped() made async + open offloaded to spawn_blocking). Correctness HIGH (owner Delete-vault 404 in split — /api/vault was public-only but its button is on the private admin page → moved to shared routes). DI-M1/M2/M3 MED (floor recorded before the poll short-circuit; persisted per-vault lastVersions so a rewind survives a restart; floor bumps only when tombstones were genuinely lost, not on a dangling-ref repair). Security MED (/api/admin/usernames gated require_admin — full account-table dump in merge mode). Correctness MED (merge detection compares ports; ephemeral :0 → merge). Field bugs: the status indicator held 'Connecting…' through the entire initial sync (markReconciling flips to 'Syncing…' once connected); Docker admin unreachable (deploy compose binds 0.0.0.0:8091 + publishes host-loopback). Critics CONFIRMED sound: public/admin router isolation (registration-enforced), admin authz gating, no privilege escalation, CSRF mitigation, SQLite transaction atomicity, tombstone-authoritative delete, admin lock-ordering (no deadlock), sweep-vs-commit RwLock exclusion. Server 94 tests (62 lib + 6 admin + 2 reg + 5 sharing + 19 sync) + clippy clean; client tsc + 97 unit + 22 e2e green (new markReconciling + DI-M3 + dangling-ref tests). Residual (tracked, not shipped this round): Conc-M1 double-open SQLITE_BUSY race, Conc-M2 full-manifest changes(0) on the async worker, admin-handler cold opens on the worker, orphan-sweep >1h slow-upload (accept), auth_slots shared across ports (accept)."; }
        verification autoReindexDoD : Test { :>> id = "c0f1a5cc-501f-4a10-9b20-a1b2c3d4005f"; :>> method = VerificationMethod::test; :>> procedureText = "Per D0022: Vault::open auto-reindexes where safe. Done when: an empty index + materialized files auto-repairs on open (not ERROR); a quarantined corrupt DB with files auto-repairs from disk; a dangling chunk reference recovers from the bind-mount mirror; a file lost from BOTH disk and the chunk store (or an unsafe/colliding name) STAYS ERROR until a Force reindex; and the admin 'My vaults' panel offers a one-click Reindex per vault. Safe because tombstone-authoritative delete + the D0019 horizon prevent a rebuilt index from causing client deletion. SHIPPED (server, b50012d): open() attempts reindex(false) when corrupt; open-behavior tests rewritten (empty_index_with_data_auto_repairs, corrupt_db_is_quarantined_and_auto_repaired_from_disk, dangling_chunk_ref_auto_recovers_from_mirror, unrecoverable_index_stays_error_until_forced; sync.rs vault_with_orphaned_files_auto_reindexes_on_first_access). Full server suite green (93) + clippy clean. Server-only (redeploy)."; }
        verification adminSplitDeployDoD : Test { :>> id = "c0f1a5cc-501c-4a10-9b20-a1b2c3d4005c"; :>> method = VerificationMethod::test; :>> procedureText = "Per D0021: the admin surface splits onto its own bind address, SAFE BY DEFAULT. Done when: by default (no ADMIN_BIND_ADDR set) /admin + /api/admin/* are served ONLY on a private localhost-only admin address and are NOT reachable on the public BIND_ADDR (which serves sync + /api/login + /api/register + /health); ADMIN_BIND_ADDR overrides the admin address; ADMIN_BIND_ADDR=merge (or =the public addr) serves both on one port (the opt-out); app() splits into a public router + an admin router and main binds the appropriate server(s). Integration tests assert an /api/admin/* request to the PUBLIC router 404s while the admin router serves it, and that merge mode serves both. Deploy docs + an upgrade note (existing single-port deployers set ADMIN_BIND_ADDR=merge). SHIPPED (server, 8951b43): public_app/admin_app split via build(); main runs two servers (split) or one (merge); admin_split_isolates_surfaces asserts the 404-vs-401 isolation both ways; deployment.md admin section rewritten. Server-only (redeploy)."; }
        verification adminPortalEnhancementsDoD : Test { :>> id = "c0f1a5cc-501d-4a10-9b20-a1b2c3d4005d"; :>> method = VerificationMethod::test; :>> procedureText = "Per D0021: (a) a PERSISTED admin set replaces the hardcoded single admin — is_server_admin consults it, the bootstrap SYNC_USER is always admin + cannot be demoted, and POST/DELETE /api/admin/users/:name/admin grant/revoke (server-admin only); (b) the admin page shows registration as a TOGGLE (not a button); (c) grantee sharing does AUTOCOMPLETE + fuzzy match against the real username list (safe on the private surface) with the server exists() check retained; (d) an OWNER can delete their OWN vault from the 'My vaults' panel (owner-scoped endpoint + typed confirmation), alongside the admin any-vault delete. Server unit/integration for the admin set (grant/revoke, bootstrap-undemotable, non-admin forbidden) + owner-delete (owner-of-vault only); admin-UI wired. Re-dispositions issueShareEnumeration. SHIPPED (server, 8951b43): AdminStore (.admins.json) + admin_grant/admin_revoke + is_server_admin via the set (lib test grant_revoke_persists); users_list returns {username,is_admin,is_bootstrap}; registration toggle + grantee datalist/fuzzy + owner delete_own_vault in admin_ui.html. Server-only (redeploy)."; }
        verification deletedVaultRecreatePromptDoD : Test { :>> id = "c0f1a5cc-501e-4a10-9b20-a1b2c3d4005e"; :>> method = VerificationMethod::test; :>> procedureText = "Per D0021: on a 404 (the synced vault was deleted server-side) the plugin surfaces a deliberate 'Re-create this vault from this device' action that calls createVault + reconnects, repopulating the fresh vault from this device's local copy (the existing tombstone-authoritative keep+push) — making today's no-data-loss behavior an explicit user choice instead of implicit. The message still states local files are untouched. A plugin-wiring test covers the 404 → offline + isVaultGone. Ships as a plugin release. SHIPPED 0.10.34 (1881e94): main.ts vaultGone flag + recreateVault() (createVault + reconnect); the settings status card shows a 'Re-create vault from this device' button when offline + vaultGone; the 404 message points to it. tsc + build clean, plugin-wiring test green."; }
        verification residualLowFindingsDoD : Test { :>> id = "c0f1a5cc-501b-4a10-9b20-a1b2c3d4005b"; :>> method = VerificationMethod::analyze; :>> procedureText = "The residual LOW findings re-homed off the round1DeferredHardening catch-all, tracked honestly rather than falsely resolved. TWO are ACCEPTED (won't-fix): issuePullTOCTOUResidual (the pull racing-edit window can't be fully closed without blocking Obsidian's own disk writes; common cases guarded) and issueTransientGreenLight (a sub-second wrong indicator during a poll blip, self-correcting, no data impact). TWO are platform/effort-DEFERRED: issueStreamWholeHash (a streaming whole-file hash needs an incremental SHA-256 the client's one-shot WebCrypto doesn't provide; a non-live path since chunk lists are verified at commit) and issueReindexSingleChunk (server-side re-chunking needs a Rust CDC chunker matching the client gear-hash; operator-only, content stays correct + self-corrects on next client edit). Done when each is either fixed or converted to a formal accept-risk disposition. The two ACCEPTED-inherent/cosmetic siblings were signed off won't-fix by the owner under D0020 (2026-07-08) and are resolved there; this action now holds ONLY the two platform/effort deferrals (issueStreamWholeHash, issueReindexSingleChunk), which stayed open until a client incremental-SHA / server Rust-CDC capability existed. DONE (backlog sprint 2): both capabilities now exist and both findings are FIXED + tested. issueStreamWholeHash — streamFileToDisk verifies the incrementally-computed whole-file hash (streamhash.ts Sha256, R17) before the atomic rename (was already fixed; verified). issueReindexSingleChunk — server/src/chunker.rs is a byte-for-byte port of the client chunker (golden-vector parity: chunker::matches_the_client_chunker_byte_for_byte + client chunker-parity.test pin the SAME vector), and reindex now content-defined-chunks each file (vault::reindex_chunks_a_large_file_into_many_chunks_that_reassemble). Full server suite 176 passed."; }
        part residualLowFindingsDoDR1 : TestResult { :>> id = "65411376-f305-438e-b470-223cd4115a4e"; :>> outcome = VerdictKind::pass; :>> judgedAgainst = "a5a766c"; :>> judgedAt = "2026-07-15"; :>> judgedBy = "ai"; }
        verification historyRebaseDoD : Test { :>> id = "c0f1a5cc-5019-4a10-9b20-a1b2c3d40059"; :>> method = VerificationMethod::test; :>> procedureText = "Per D0019, shipped 0.10.31 (8c69b8b). The deletion-history HORIZON fixes the corrupt-reindex resurrection (RC-1) without an arbitrary cap. SERVER: ChangesResponse gains history_floor (serde default → an older server decodes as genesis, never a false reset); SqliteIndex.set_history_floor + reports it in changes; Vault caches it and a rebuild-from-disk (was_corrupt) reindex raises it to the current version (a HEALTHY reindex keeps tombstones + the floor). CLIENT: detects a reset (server history_floor advanced past the per-vault floor this device last synced, persisted in settings.historyFloors keyed owner/vault since state.version is ephemeral; OR a version rewind), routes to the FULL reconcile, and reports every file KEPT because absent-without-tombstone (reconcileOne already keeps+pushes — never deletes without a tombstone) via onKeptAbsent, surfacing ONE batched dismissible notice (full list to the sync log). No data loss ever; resurrection becomes visible + user-correctable. The deliberate operator tombstone-PRUNE is deferred (tombstonePrune). Server 58 lib (new corrupt_reindex_raises_history_floor, healthy_reindex_keeps_history_floor_and_tombstones, history_floor_set_and_reported_in_changes) + 18 integration green + clippy clean; client 195 unit (new reconcile onKeptAbsent + plugin-wiring floor-advance detection) + real-server e2e green; tsc + build clean."; }
        verification tombstonePruneDoD : Test { :>> id = "c0f1a5cc-501a-4a10-9b20-a1b2c3d4005a"; :>> method = VerificationMethod::test; :>> procedureText = "The deferred OPERATOR tombstone-prune (D0019): a deliberate operation that raises the history_floor AND physically drops tombstones below it to reclaim space, reusing the horizon machinery historyRebase shipped (a below-floor client already reconciles conservatively). Done when an operator can prune (an admin endpoint or a documented threshold), tombstones below the new floor are removed, the floor is raised atomically, and a below-floor client still keeps+notifies rather than resurrecting. SHIPPED (server, 8025fb2): SqliteIndex::prune_tombstones(floor) DELETEs deletions below floor + raises history_floor atomically; Vault::prune_history clamps floor to [current floor, version]; POST /api/admin/prune-history {owner, vault, floor?} (server-admin, floor default = current version = prune all). Server 60 lib (new prune_tombstones + prune_history) + 18 integration green, clippy clean."; }
        verification scaleHardeningDoD : Test { :>> id = "c0f1a5cc-5015-4a10-9b20-a1b2c3d40055"; :>> method = VerificationMethod::test; :>> procedureText = "The resource/scale findings from the Round-7 pass, addressed for scale-agnosticism. RS-1 evict idle VaultHandles; RS-2 avoid the per-write whole-index clone; RS-3 reconcile only the incremental delta on a remote poke (not full manifest + full re-hash); RS-4 cap per-file base text (large text -> hash-only); RS-5 version-indexed changes(since); RS-6 incremental snapshot; RS-7 bounded cold-open. The scale-agnostic resolution for RS-2/5/6/7 is the storage-engine decision (adopt SQLite — indexed queries + row-level writes + WAL/checksums moot them AND harden against index corruption); RS-1/3/4 are storage-independent. DONE: this umbrella is satisfied by the three split delivering actions — resourceScaleFixes (RS-1/4, 0.10.30), incrementalReconcile (RS-3, 0.10.29), sqliteMigration (RS-2/5/6/7, D0018). Every RS-1..7 finding is shipped or mooted; each carries its own green DoD."; }
        verification round6CriticFixesDoD : Test { :>> id = "c0f1a5cc-5013-4a10-9b20-a1b2c3d40053"; :>> method = VerificationMethod::test; :>> procedureText = "Round-6 fresh 3-lens critique (independent data-integrity/security/concurrency critics) vs 0.10.26; 9 findings fixed + shipped 0.10.27 (1 Low accept-risk). HIGH: (DI) removed the arbitrary MAX_TOMBSTONES cap — under tombstone-authoritative delete it made a long-offline client RESTORE a genuinely-deleted file (resurrection); tombstones now durable (proper bound = historyRebase). (CONC) reconcilePath isolates a CommitConflictError (per-file skip -> merge next pass) like reconcileAll, so a routine concurrent-edit CAS 409 no longer flaps the engine offline (regression from the 0.10.26 CAS work); non-conflict errors still propagate. (SEC) flushConfigReload never auto-enables synced plugin CODE nor auto-applies synced theme/snippet CSS for ANY vault — closes the SEC-3 owner-direction RCE (a readWrite peer's main.js on a vault you own) + the ungated-CSS injection. MED: single-flight freshLogin (no concurrent re-login race / orphan token); failToOffline drops `connected` (a WS redial in the offline window is ignored — one recovery path); reindex applies the safe_rel_path + case/fold collision guard and, when healthy, prefers the authoritative chunk store over a stale mirror (issueReindexBindMount un-deferred). LOW: doConnect clears this.ws before its awaits; path-coalescing keeps the max size. Server 46 lib + 18 integration tests green + clippy clean; client 168 unit + 21 e2e green; tsc + build clean."; }
        verification stpaSuspicionPropagationDoD : Test { :>> id = "c0f1a5cc-5012-4a10-9b20-a1b2c3d40052"; :>> method = VerificationMethod::test; :>> procedureText = "Per D0017: keel flags a UCA / LossScenario / SafetyRequirement suspect when a linked architectural element (via #Analyzes / #RealizedBy / #Senses, transitively #Explains / #Mitigates / #Inverts / #Enforces) was modified at a commit later than that artifact's reassessed-at-commit stamp; Hazards + Losses are NOT flagged by an architecture change (only by a Loss/stakeholder/boundary change). Needs: a reassessed-at-commit stamp on the analysis elements (EngineSafety schema addition, human sign-off), the propagation to fixpoint, and surfacing in orient + the safety view + `keel suspect`. Verified by a keel test that edits a controller and asserts its UCAs/requirements go suspect while the hazards do not. NO result until built (deferred keel change). PROGRESS 2026-09-07: filed upstream as a feature request, https://github.com/williamweatherholtz/sysmlv2-ai-toolkit/issues/66 (the D0017 text verbatim, plus what this project has ready for it: a 25-SR STPA whose control structure is a first-class model with 100+ marker edges into the architecture)."; }
        verification stpaSafetyAnalysisDoD : Test { :>> id = "c0f1a5cc-5011-4a10-9b20-a1b2c3d40051"; :>> method = VerificationMethod::analyze; :>> procedureText = "A full STPA (per D0016, using EngineSafety + the `stpa` skill) is complete when: Losses are enumerated; every Hazard traces to >=1 Loss and has an inverse System Safety Constraint; the control structure is modeled (controllers, controlled processes, control actions, feedback, sensors/actuators, and each controller's ProcessModel beliefs); Unsafe Control Actions are derived across all four UcaType guide words per control action; Loss Scenarios cover BOTH classes (why a UCA occurs; why a correct control action isn't executed / feedback never arrives); and each mitigating Safety Requirement traces UCA->Hazard->Loss and carries a `verify`-linked Test. Rendered via the `safety` viewpoint. Scope = sync data-safety (trusted-server model bounds it). FUTURE SHAPE (owner, 2026-07-06): (a) author the control STRUCTURE as a first-class SysML-v2 model (Controller/ControlledProcess/ControlAction/Feedback/ProcessModel typed refs), not prose, so it renders as a diagram and is itself a tracked artifact; (b) add a REANALYSIS / PARITY mechanism so the STPA can be reassessed against the actual sw & hw it abstracts — list the STPA verification Tests (or the control-structure artifacts) in the deliverable-manifest so keel's suspect/drift machinery (D0050) marks the safety analysis STALE when the mapped source changes at HEAD, forcing a re-analysis rather than letting the control model silently diverge from the code. NO result until performed (deferred end-of-project pass). PROGRESS 2026-09-07 (engine resync sitting): the model was CHECKED against these criteria under keel 0.3.1 - every Hazard h1..h10 carries #LeadsTo -> Loss and an #Inverts constraint; every UCA carries #Causes -> Hazard and #Analyzes -> ControlAction; 19 LossScenarios, 15 #Explains edges; 25 SRs each #Mitigates/#Satisfies + #RealizedBy. The one structural gap was the verify clause: NO SafetyRequirement had a verify-linked Test. Now 22 of 25 do (46 #Verify edges in acceptance.sysml, each settled by reading the Test procedure against the SR statement; only passed Tests linked). Remaining: sr11 (autoReindexDoD), sr16 (uiFunctionalAuditDoD), sr19 (round1DeferredHardeningDoD) - the verifying tests exist in the server suite but those DoDs carry no recorded result, so linking them would claim a verification nobody stamped. Also outstanding: the safety viewpoint renderer names `keel show control-structure`, which in 0.3.1 computes the ENGINE's own workflow control structure, not this deliverable's STPA - the project STPA renders through the stpa-diagram process/tool (D0285) and this renderer string is a follow-up. The reanalysis/parity mechanism (D0017) remains a keel-toolkit change (stpaSuspicionPropagation)."; }
        // RAN: ANALYSIS 2026-09-07 against .tracking/safety/*.sysml at HEAD (scripted census + keel lenses): Losses l1..l5 enumerated; Hazards h1..h10 each #LeadsTo >= 1 Loss and each has an #Inverts SystemSafetyConstraint (10/10); control structure first-class - 7 Controllers, 7 ProcessModels, 21 ControlActions, 11 Feedbacks; 22 UCAs each #Causes -> Hazard and #Analyzes -> ControlAction, 20 ControllerConstraints; 19 LossScenarios (both classes: why a UCA occurs / why a correct action is not executed or feedback never arrives), 15 #Explains edges; 25 SafetyRequirements each #Mitigates/#Satisfies + #RealizedBy -> controller and, as of e540b786, each #Verify-linked from a passed Test (keel view safety: 25 SRs, 42 Tests). Rendered via the safety viewpoint (keel view safety). Scope = sync data-safety under the trusted-server model. FUTURE SHAPE (b) reanalysis-on-change is stpaSuspicionPropagation (upstream #66), not a criterion of this analysis.
        part stpaSafetyAnalysisDoDR1 : TestResult { :>> id = "2ecf4c29-da2b-450d-bb43-5020fcf0529f"; :>> outcome = VerdictKind::pass; :>> judgedAgainst = "468027ac"; :>> judgedAt = "2026-09-07"; :>> judgedBy = "claudeOpus"; }
        verification preReleaseHardeningDoD : Test { :>> id = "c0f1a5cc-5010-4a10-9b20-a1b2c3d40050"; :>> method = VerificationMethod::test; :>> procedureText = "Five pre-broad-release items land + tested + shipped 0.10.26. (c1) VERSION HANDSHAKE: server exposes a protocol/index-schema API_VERSION on /health (now JSON) + the per-vault status; the client (CLIENT_API_VERSION) checks it on connect and refuses to sync on a mismatch with a clear 'update whichever is older' message (backward compatible — an absent apiVersion skips the check). (c2) ADMIN REINDEX: POST /api/admin/reindex (server-admin only, owner+vault) + a 'Vault repair' panel in admin_ui.html repair a corrupt shared/non-owned vault without curl. (c3) COMMIT CAS: CommitRequest.expected_version; the server 409s (ErrorKind::AlreadyExists → Conflict) a commit based on a stale version AFTER the idempotent short-circuit; the client sends its base version on the reconcile-driven push / edit-wins-keep-local / merge-push paths and, on 409 (CommitConflictError), isolates the file via onFileError and converges to a merge next pass — closing the double-first-commit lost-update on a multi-writer vault (authoritative switch/adjudication omit it). (b1) TOKEN-TTL CRUTCH removed: the 30s recently-validated cache + proactive listVaults probe are gone; acquireToken is optimistic and a real 401 drives a single reactive re-login (withAuth + doConnect). (b2) CONFIG-SCAN CRUTCH: the periodic config-aware reconcile fires on a CONFIG_SCAN_INTERVAL_MS wall-clock bound, not an every-Nth-poll count. Server 44 lib + 18 integration tests green (new: commit_cas_rejects_stale_expected_version, JSON /health apiVersion) + clippy clean; client 164 unit + full e2e green (new: 2 reconcile CAS tests, version-mismatch + reactive-401 wiring tests); tsc + release build clean."; }
        verification deleteLocalTombstoneGateDoD : Test { :>> id = "c0f1a5cc-500f-4a10-9b20-a1b2c3d4004f"; :>> method = VerificationMethod::test; :>> procedureText = "CRITICAL data-loss escape (0.10.25): pointing a populated vault at a WRONG/FRESH/RESTORED server silently deleted every local file, because delete-local fired on the file's ABSENCE from the remote rather than on a real deletion tombstone, and the one-shot C2 empty-server guard did not survive across reconcile passes (the client's own pushes made the remote non-empty on the second pass, disarming it). FIX: deletion is now TOMBSTONE-AUTHORITATIVE — reconcileOne receives a hasTombstone(path) predicate built from the server's changes().deletes; delete-local RESTORES the file (pushes it back) when no tombstone exists and only removes it when the server genuinely tombstoned it (reconcileAll from resp.deletes, reconcilePath from manifest.deletes). The test harness was made realistic: the fake server now models tombstones (deletions[] with versions) instead of mere absence — the two prior tests that asserted the buggy absence-delete were rewritten, and a DATA-LOSS REGRESSION test reproduces the exact two-pass wrong/empty-server sequence (Welcome.md + 'test file.md' never deleted). main.ts made testable via injection seams (buildIo/buildApi/loginRemote/validateToken) + an obsidian stub + vitest alias; plugin-wiring.test.ts (6 integration tests) covers the orchestration seam; e2e harness repaired (ALLOW_WEAK_ADMIN + createVault for protocol-6). Full client suite 181 green; shipped 0.10.25."; }
        verification round1DeferredHardeningDoD : Test { :>> id = "c0f1a5cc-5007-4a10-9b20-a1b2c3d40047"; :>> method = VerificationMethod::test; :>> procedureText = "SEC#4: a per-vault stored-bytes quota and/or runtime orphan-chunk GC so a ReadWrite grantee can't fill the owner's disk with uncommitted chunks (today reclaimed only at startup). DI#4: during reindex, when an on-disk file's hash disagrees with a still-healthy index entry, prefer/surface the chunk-store content rather than silently adopting the bind-mount bytes. CONC#5: keep pendingSwitchMode set until switchTo fully succeeds so a mid-switch failure doesn't downgrade an authoritative overwrite to a merge. Each landed with tests."; }

        // ---- appended pass results for DONE milestones (judged at the backfill commit) ----
        part m1ProtocolR1 : TestResult { :>> id = "0a679462-4127-44ec-87b6-495d4ca7e426"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; protocol suites (sync/ws) in the server run + client e2e.spec two-client propagation
        part m1ProtocolDoDR2 : TestResult { :>> id = "d82cbf84-3a4d-4cca-ba1f-5f48e5facd87"; :>> outcome = VerdictKind::pass; :>> judgedAgainst = "468027ac"; :>> judgedAt = "2026-09-07"; :>> judgedBy = "claudeOpus"; }
        part m2ChunkingBinaryR1 : TestResult { :>> id = "36b58c11-47d4-415e-a22f-a32c7d36c472"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; chunker tests + e2e binary round-trip in the client run
        part m2ChunkingBinaryDoDR2 : TestResult { :>> id = "5171fb59-aec4-4c07-801f-1c09dc43c914"; :>> outcome = VerdictKind::pass; :>> judgedAgainst = "468027ac"; :>> judgedAt = "2026-09-07"; :>> judgedBy = "claudeOpus"; }
        part m3ConflictMergeR1 : TestResult { :>> id = "54ce7b0d-9f71-49d2-9c98-cab80170e041"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; merge/reconcile tests in the client run
        part m3ConflictMergeDoDR2 : TestResult { :>> id = "5ec0c56a-4a36-4e91-91e2-7031504d1ef5"; :>> outcome = VerdictKind::pass; :>> judgedAgainst = "468027ac"; :>> judgedAt = "2026-09-07"; :>> judgedBy = "claudeOpus"; }
        part m4MultiTenantR1 : TestResult { :>> id = "3de1fbd1-b2ab-4c15-a3d3-ad5921feb988"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; per-vault isolation tests in the server admin/sync suites
        part m4MultiTenantDoDR2 : TestResult { :>> id = "da7019dd-307b-44a2-a6c4-32cad17a870b"; :>> outcome = VerdictKind::pass; :>> judgedAgainst = "468027ac"; :>> judgedAt = "2026-09-07"; :>> judgedBy = "claudeOpus"; }
        part m5MobileR1 : TestResult { :>> id = "da2e7a98-42d5-43b0-b6d1-4501591d4df5"; :>> outcome = VerdictKind::pass; :>> judgedAgainst = "0e02bc0"; :>> judgedAt = "2026-07-04"; :>> judgedBy = "ai"; }
        // RAN: RE-INSPECTED 2026-09-07 at HEAD 468027ac: manifest.json isDesktopOnly:false; client/src/transport.ts uses requestUrl (4 sites); chunker.ts + streamhash.ts use crypto.subtle (WebCrypto), no desktop-only deps
        part m5MobileDoDR2 : TestResult { :>> id = "b722c213-3680-497e-b722-f459e56be22c"; :>> outcome = VerdictKind::pass; :>> judgedAgainst = "468027ac"; :>> judgedAt = "2026-09-07"; :>> judgedBy = "claudeOpus"; }
        part m6PackagingR1 : TestResult { :>> id = "ecabfe78-687c-451c-895e-cd0c9cc70311"; :>> outcome = VerdictKind::pass; :>> judgedAgainst = "0e02bc0"; :>> judgedAt = "2026-07-04"; :>> judgedBy = "ai"; }
        // RAN: RE-INSPECTED 2026-09-07 at HEAD 468027ac: node scripts/check-release.mjs -> '1.30.7 is released - git tag + GitHub release with main.js, manifest.json, styles.css present' (today); release.yml fires on the manifest.json bump and publishes the BRAT assets; deploy/docker-compose.yml + Caddy reverse-proxy example present
        part m6PackagingDoDR2 : TestResult { :>> id = "ff223956-da65-4ef1-a901-f29e924d704e"; :>> outcome = VerdictKind::pass; :>> judgedAgainst = "468027ac"; :>> judgedAt = "2026-09-07"; :>> judgedBy = "claudeOpus"; }
        part goal1ConfigUxR1 : TestResult { :>> id = "d3722ace-eb30-4a03-bb66-8ca91f40ebad"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; configsync tests + the config-sync permutation matrix (e2e path) in the client run
        part goal1ConfigUxDoDR2 : TestResult { :>> id = "33b3dec0-3d86-492a-ab29-a3850794d119"; :>> outcome = VerdictKind::pass; :>> judgedAgainst = "468027ac"; :>> judgedAt = "2026-09-07"; :>> judgedBy = "claudeOpus"; }
        part rel06FixSetR1 : TestResult { :>> id = "338147e1-ba2f-4bc6-bd1d-23ccb8b486d7"; :>> outcome = VerdictKind::pass; :>> judgedAgainst = "0e02bc0"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client suite + tsc + build
        part rel06FixSetDoDR2 : TestResult { :>> id = "7a488935-c989-4abf-9808-11e96f09d47a"; :>> outcome = VerdictKind::pass; :>> judgedAgainst = "468027ac"; :>> judgedAt = "2026-09-07"; :>> judgedBy = "claudeOpus"; }
        // Phase 1 shipped: ACL + owner-qualified routes + authz + registration/tokens + admin API + web UI.
        part vaultSharingP1R1 : TestResult { :>> id = "c1c6d04d-3d68-4afc-b086-f83dddc5e730"; :>> outcome = VerdictKind::pass; :>> judgedAgainst = "6b39442"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server sharing suite (5) + admin suite + client sharelink tests
        part vaultSharingP1DoDR2 : TestResult { :>> id = "da3c85bf-4d2a-46da-acec-d7931c72d77a"; :>> outcome = VerdictKind::pass; :>> judgedAgainst = "468027ac"; :>> judgedAt = "2026-09-07"; :>> judgedBy = "claudeOpus"; }
        // Phase 2 shipped: owner-aware client transport + read-only gating + switcher; cross-user E2E green.
        part shareClientConsumeR1 : TestResult { :>> id = "d8576c06-d950-4bcf-9b7b-ba0415a9331e"; :>> outcome = VerdictKind::pass; :>> judgedAgainst = "3438003"; :>> judgedAt = "2026-07-04"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharing-e2e.spec (shared-vault sync end to end) + acReadOnlyGating basis
        part shareClientConsumeDoDR2 : TestResult { :>> id = "1563acc3-f443-402a-935c-c3fc5ac7c963"; :>> outcome = VerdictKind::pass; :>> judgedAgainst = "468027ac"; :>> judgedAt = "2026-09-07"; :>> judgedBy = "claudeOpus"; }
        // B11 shipped: mapPool bounds concurrency; fetchFileBytes + pushFile transfer chunks in parallel.
        part b11ParallelChunkR1 : TestResult { :>> id = "35068780-a122-4860-bb31-7fb1bae251e2"; :>> outcome = VerdictKind::pass; :>> judgedAgainst = "88238fb"; :>> judgedAt = "2026-07-05"; :>> judgedBy = "ai"; }
        // B7 shipped: durable/expiring/revocable tokens + token-only persistence + TLS/exposure docs (E2EE carved to e2eEncryption).
        part b7AuthHardeningR1 : TestResult { :>> id = "e44416e1-5f8d-4621-b140-3b1b7a9f0574"; :>> outcome = VerdictKind::pass; :>> judgedAgainst = "198d5f1"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server auth tests (argon2, tokens, must_change) + client transport tests
        part b7AuthHardeningDoDR2 : TestResult { :>> id = "cc666eec-eab1-4c4b-af26-360de44de03c"; :>> outcome = VerdictKind::pass; :>> judgedAgainst = "468027ac"; :>> judgedAt = "2026-09-07"; :>> judgedBy = "claudeOpus"; }
        // B9 Part A shipped: append-only index journal (streaming Part B deferred, D0010).
        part b9DurabilityStreamingR1 : TestResult { :>> id = "b8b81f32-5c6d-4b35-b0f3-cfd935073917"; :>> outcome = VerdictKind::pass; :>> judgedAgainst = "2b42a58"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server journal/streaming tests (acDurableIndex basis)
        part b9DurabilityStreamingDoDR2 : TestResult { :>> id = "4451f15d-0268-45c6-be02-86590b36829f"; :>> outcome = VerdictKind::pass; :>> judgedAgainst = "468027ac"; :>> judgedAt = "2026-09-07"; :>> judgedBy = "claudeOpus"; }
        // B9 Part B shipped (D0010 deferral lifted per owner request): streamed large-download reassembly.
        part streamingReassemblyR1 : TestResult { :>> id = "09cf210d-4f35-49d4-b9ee-4b4c49ca4c37"; :>> outcome = VerdictKind::pass; :>> judgedAgainst = "2c2118c"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client streaming tests (streamhash, streamFileToDisk)
        part streamingReassemblyDoDR2 : TestResult { :>> id = "31dc7148-2984-4502-b966-f7b078357efe"; :>> outcome = VerdictKind::pass; :>> judgedAgainst = "468027ac"; :>> judgedAt = "2026-09-07"; :>> judgedBy = "claudeOpus"; }
        // 0.10.4 config-sync safety + the CR d0011 traceability backfill (both shipped at db1b008).
        part configSyncSafetyR1 : TestResult { :>> id = "c0f1a5cc-6001-4a10-9b20-a1b2c3d40051"; :>> outcome = VerdictKind::pass; :>> judgedAgainst = "db1b008"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client reconcile config-sync tests
        part configSyncSafetyDoDR2 : TestResult { :>> id = "510ee89a-1a38-40fe-8566-ee8e08ab7f9b"; :>> outcome = VerdictKind::pass; :>> judgedAgainst = "468027ac"; :>> judgedAt = "2026-09-07"; :>> judgedBy = "claudeOpus"; }
        part requirementTraceabilityBackfillR1 : TestResult { :>> id = "c0f1a5cc-6002-4a10-9b20-a1b2c3d40052"; :>> outcome = VerdictKind::pass; :>> judgedAgainst = "db1b008"; :>> judgedAt = "2026-07-05"; :>> judgedBy = "ai"; }
        // L4 mobile on-device: owner-attested demo (foreground sync + indicator + config sync on his phone, 0.10.7). settingsGroupingPolish is intentionally left with NO result (deferred/open).
        part l4MobileOndeviceR1 : TestResult { :>> id = "c0f1a5cc-6003-4a10-9b20-a1b2c3d40053"; :>> outcome = VerdictKind::pass; :>> judgedAgainst = "912722b"; :>> judgedAt = "2026-07-05"; :>> judgedBy = "wweatherholtz"; }
        // The client critique wave shipped at 0.10.14 (c0576c9).
        part critiqueClientWaveR1 : TestResult { :>> id = "c0f1a5cc-6004-4a10-9b20-a1b2c3d40054"; :>> outcome = VerdictKind::pass; :>> judgedAgainst = "c0576c9"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client suite
        part critiqueClientWaveDoDR2 : TestResult { :>> id = "4b7a0915-3ce0-41ea-98fe-04a2c1dde100"; :>> outcome = VerdictKind::pass; :>> judgedAgainst = "468027ac"; :>> judgedAt = "2026-09-07"; :>> judgedBy = "claudeOpus"; }
        part cmmcForcedChangeReuseR1 : TestResult { :>> id = "c0f1a5cc-60c1-4a10-9b20-a1b2c3d400c1"; :>> outcome = VerdictKind::pass; :>> judgedAgainst = "f035f79"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server must_change + password-reuse tests
        part cmmcForcedChangeReuseDoDR2 : TestResult { :>> id = "bcf3bd94-0313-459f-8b88-0d0df0de9dc0"; :>> outcome = VerdictKind::pass; :>> judgedAgainst = "468027ac"; :>> judgedAt = "2026-09-07"; :>> judgedBy = "claudeOpus"; }
        part cmmcMfaR1 : TestResult { :>> id = "c0f1a5cc-60c2-4a10-9b20-a1b2c3d400c2"; :>> outcome = VerdictKind::pass; :>> judgedAgainst = "8831c4c"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server MFA tests (mfa_totp_full_lifecycle)
        part cmmcMfaDoDR2 : TestResult { :>> id = "b40283f5-4880-4e13-8d08-c4d52e492a99"; :>> outcome = VerdictKind::pass; :>> judgedAgainst = "468027ac"; :>> judgedAt = "2026-09-07"; :>> judgedBy = "claudeOpus"; }
        part uiFunctionalAuditR1 : TestResult { :>> id = "c0f1a5cc-60c3-4a10-9b20-a1b2c3d400c3"; :>> outcome = VerdictKind::pass; :>> judgedAgainst = "131b8b0"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; admin.rs must_change_account_is_blocked_until_password_set_then_works, admin_grant_and_revoke_toggles_admin_access, admin_deletes_an_account, admin_reindex_and_prune_history_http_ok, admin_invite_list_and_delete; syncstate/wizardsteps/plugin-wiring cases (present at HEAD)
        part uiFunctionalAuditDoDR2 : TestResult { :>> id = "27033f70-b698-4b8f-8a84-3f5ce9fc04ab"; :>> outcome = VerdictKind::pass; :>> judgedAgainst = "468027ac"; :>> judgedAt = "2026-09-07"; :>> judgedBy = "claudeOpus"; }
        part critRoundStdR1 : TestResult { :>> id = "c0f1a5cc-60c4-4a10-9b20-a1b2c3d400c4"; :>> outcome = VerdictKind::pass; :>> judgedAgainst = "ce9824a"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile.test delta-tombstone / unreadable-file cases
        part critRoundStdDoDR2 : TestResult { :>> id = "540ca7ae-0810-4744-9bf9-2c139750fa04"; :>> outcome = VerdictKind::pass; :>> judgedAgainst = "468027ac"; :>> judgedAt = "2026-09-07"; :>> judgedBy = "claudeOpus"; }
        part critRoundCmmcR1 : TestResult { :>> id = "c0f1a5cc-60c5-4a10-9b20-a1b2c3d400c5"; :>> outcome = VerdictKind::pass; :>> judgedAgainst = "c8d0940"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; admin.rs require_admin_mfa_blocks_admin_until_totp_enrolled
        part critRoundCmmcDoDR2 : TestResult { :>> id = "5610a330-f65b-4e45-a4c6-ef225220e5a7"; :>> outcome = VerdictKind::pass; :>> judgedAgainst = "468027ac"; :>> judgedAt = "2026-09-07"; :>> judgedBy = "claudeOpus"; }
        part critResidualEasyR1 : TestResult { :>> id = "c0f1a5cc-60c6-4a10-9b20-a1b2c3d400c6"; :>> outcome = VerdictKind::pass; :>> judgedAgainst = "72c4574"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; users.rs totp_code_cannot_be_replayed_within_its_window
        part critResidualEasyDoDR2 : TestResult { :>> id = "9b4fb628-20b2-4977-8b67-ce15cb096c4e"; :>> outcome = VerdictKind::pass; :>> judgedAgainst = "468027ac"; :>> judgedAt = "2026-09-07"; :>> judgedBy = "claudeOpus"; }
        part critResidual2R1 : TestResult { :>> id = "c0f1a5cc-60c7-4a10-9b20-a1b2c3d400c7"; :>> outcome = VerdictKind::pass; :>> judgedAgainst = "47bd141"; :>> judgedAt = "2026-07-10"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; syncstate isWsStale + server admin suite (require_admin ClientIp)
        part critResidual2DoDR2 : TestResult { :>> id = "6fd4da24-82eb-448d-b22e-bc26da050c7a"; :>> outcome = VerdictKind::pass; :>> judgedAgainst = "468027ac"; :>> judgedAt = "2026-09-07"; :>> judgedBy = "claudeOpus"; }
        part acceptMobileFsyncRiskR1 : TestResult { :>> id = "c0f1a5cc-60c8-4a10-9b20-a1b2c3d400c8"; :>> outcome = VerdictKind::pass; :>> judgedAgainst = "35a6394"; :>> judgedAt = "2026-07-11"; :>> judgedBy = "wweatherholtz"; }
        part acceptOpenEnumRiskR1 : TestResult { :>> id = "c0f1a5cc-60c9-4a10-9b20-a1b2c3d400c9"; :>> outcome = VerdictKind::pass; :>> judgedAgainst = "b4106ff"; :>> judgedAt = "2026-07-11"; :>> judgedBy = "wweatherholtz"; }
        part capabilityShareLinksR1 : TestResult { :>> id = "c0f1a5cc-60ca-4a10-9b20-a1b2c3d400ca"; :>> outcome = VerdictKind::pass; :>> judgedAgainst = "7e36e26"; :>> judgedAt = "2026-07-11"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharelinks.rs create_then_redeem_once_binds_and_consumes, expired_and_unknown_and_revoked_links_do_not_redeem, list_is_owner_scoped_and_survives_reopen (present at HEAD)
        part capabilityShareLinksDoDR2 : TestResult { :>> id = "05ca5944-6962-4dbf-9bcc-db48492095bf"; :>> outcome = VerdictKind::pass; :>> judgedAgainst = "468027ac"; :>> judgedAt = "2026-09-07"; :>> judgedBy = "claudeOpus"; }
        part conflictModelDerivedFromVaultR1 : TestResult { :>> id = "c0f1a5cc-60dd-4a10-9b20-a1b2c3d400dd"; :>> outcome = VerdictKind::pass; :>> judgedAgainst = "208d85b"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile originalOfConflictCopy + modals-ui.dom
        part conflictModelDerivedFromVaultDoDR2 : TestResult { :>> id = "3c0c9a54-8f35-40b4-89c7-f5f81f1c4bf2"; :>> outcome = VerdictKind::pass; :>> judgedAgainst = "468027ac"; :>> judgedAt = "2026-09-07"; :>> judgedBy = "claudeOpus"; }
        part shareRefreshedOnConnectR1 : TestResult { :>> id = "c0f1a5cc-60ee-4a10-9b20-a1b2c3d400ee"; :>> outcome = VerdictKind::pass; :>> judgedAgainst = "a4feb96"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharelink.test resolveShareGrant
        part shareRefreshedOnConnectDoDR2 : TestResult { :>> id = "609482f3-e429-4de8-87d8-1bf5f28d3bd0"; :>> outcome = VerdictKind::pass; :>> judgedAgainst = "468027ac"; :>> judgedAt = "2026-09-07"; :>> judgedBy = "claudeOpus"; }
        part shareLinkRedeemConsumeLastR1 : TestResult { :>> id = "c0f1a5cc-60ff-4a10-9b20-a1b2c3d400ff"; :>> outcome = VerdictKind::pass; :>> judgedAgainst = "cb2bc5b"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; unredeem_rolls_back_a_claim_so_a_failed_grant_does_not_burn_the_link (present)
        part shareLinkRedeemConsumeLastDoDR2 : TestResult { :>> id = "1538f410-a3d0-4a2f-b8b6-6f451373471e"; :>> outcome = VerdictKind::pass; :>> judgedAgainst = "468027ac"; :>> judgedAt = "2026-09-07"; :>> judgedBy = "claudeOpus"; }
        part conflictReadOnlyAndBinaryCorrectnessR1 : TestResult { :>> id = "c0f1a5cc-6f01-4a10-9b20-a1b2c3d40f01"; :>> outcome = VerdictKind::pass; :>> judgedAgainst = "abc13a2"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile + sharelink fail-closed tests
        part conflictReadOnlyAndBinaryCorrectnessDoDR2 : TestResult { :>> id = "7ad28588-8983-4e71-bc1d-cc7700038d3a"; :>> outcome = VerdictKind::pass; :>> judgedAgainst = "468027ac"; :>> judgedAt = "2026-09-07"; :>> judgedBy = "claudeOpus"; }
        part connErrorAbortsPassR1 : TestResult { :>> id = "c0f1a5cc-6f03-4a10-9b20-a1b2c3d40f03"; :>> outcome = VerdictKind::pass; :>> judgedAgainst = "73782b3"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile connection-failure-aborts-the-pass test
        part connErrorAbortsPassDoDR2 : TestResult { :>> id = "ddc340fd-3b47-45f4-937c-ee83c7b1c3b5"; :>> outcome = VerdictKind::pass; :>> judgedAgainst = "468027ac"; :>> judgedAt = "2026-09-07"; :>> judgedBy = "claudeOpus"; }
        part editorStatusCleanupOnUnloadR1 : TestResult { :>> id = "c0f1a5cc-6f04-4a10-9b20-a1b2c3d40f04"; :>> outcome = VerdictKind::pass; :>> judgedAgainst = "62b6e00"; :>> judgedAt = "2026-07-12"; :>> judgedBy = "ai"; }
        // RAN: RE-INSPECTED 2026-09-07 at HEAD 468027ac: main.ts onunload() at :591 removes every editorActionEls element and clears the set (:599-600)
        part editorStatusCleanupOnUnloadDoDR2 : TestResult { :>> id = "ae9126ef-9a53-4cab-bcf2-4608eede66f3"; :>> outcome = VerdictKind::pass; :>> judgedAgainst = "468027ac"; :>> judgedAt = "2026-09-07"; :>> judgedBy = "claudeOpus"; }
        part fastCheapConfigScanR1 : TestResult { :>> id = "c0f1a5cc-6f05-4a10-9b20-a1b2c3d40f05"; :>> outcome = VerdictKind::pass; :>> judgedAgainst = "0dbdfa9"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile config-scan fast-path test
        part fastCheapConfigScanDoDR2 : TestResult { :>> id = "e0c792fb-7f54-4e61-8ac7-3c09c5618056"; :>> outcome = VerdictKind::pass; :>> judgedAgainst = "468027ac"; :>> judgedAt = "2026-09-07"; :>> judgedBy = "claudeOpus"; }
        part configSyncEventDrivenR1 : TestResult { :>> id = "c0f1a5cc-6f06-4a10-9b20-a1b2c3d40f06"; :>> outcome = VerdictKind::pass; :>> judgedAgainst = "2932521"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; plugin-wiring css-change event test
        part configSyncEventDrivenDoDR2 : TestResult { :>> id = "5470fd1a-e1b3-4df5-9cdb-547dfa03bab9"; :>> outcome = VerdictKind::pass; :>> judgedAgainst = "468027ac"; :>> judgedAt = "2026-09-07"; :>> judgedBy = "claudeOpus"; }
        part configSyncFirstContactDirectionR1 : TestResult { :>> id = "c0f1a5cc-6f07-4a10-9b20-a1b2c3d40f07"; :>> outcome = VerdictKind::pass; :>> judgedAgainst = "c75ac61"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; configgroup configSurfaceOf
        part configSyncFirstContactDirectionDoDR2 : TestResult { :>> id = "e21dc4db-ff07-466f-b967-2de979504390"; :>> outcome = VerdictKind::pass; :>> judgedAgainst = "468027ac"; :>> judgedAt = "2026-09-07"; :>> judgedBy = "claudeOpus"; }
        part configSyncPerPluginDirectionR1 : TestResult { :>> id = "c0f1a5cc-6f08-4a10-9b20-a1b2c3d40f08"; :>> outcome = VerdictKind::pass; :>> judgedAgainst = "4d40af2"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; configgroup tests
        part configSyncPerPluginDirectionDoDR2 : TestResult { :>> id = "da025f76-06c8-4680-841b-ed853d9bab82"; :>> outcome = VerdictKind::pass; :>> judgedAgainst = "468027ac"; :>> judgedAt = "2026-09-07"; :>> judgedBy = "claudeOpus"; }
        part pendingExcludesDeclinedR1 : TestResult { :>> id = "c0f1a5cc-6f09-4a10-9b20-a1b2c3d40f09"; :>> outcome = VerdictKind::pass; :>> judgedAgainst = "36f18b5"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile pending tests
        part pendingExcludesDeclinedDoDR2 : TestResult { :>> id = "449056a6-c187-4595-8d36-65f2923eafa6"; :>> outcome = VerdictKind::pass; :>> judgedAgainst = "468027ac"; :>> judgedAt = "2026-09-07"; :>> judgedBy = "claudeOpus"; }
        part adoptServerPluginsR1 : TestResult { :>> id = "c0f1a5cc-6f0a-4a10-9b20-a1b2c3d40f0a"; :>> outcome = VerdictKind::pass; :>> judgedAgainst = "676acec"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile community-plugin-ids test
        part adoptServerPluginsDoDR2 : TestResult { :>> id = "c070d217-35d9-4229-90ed-aba00ee7d6ff"; :>> outcome = VerdictKind::pass; :>> judgedAgainst = "468027ac"; :>> judgedAt = "2026-09-07"; :>> judgedBy = "claudeOpus"; }
        part statusDetailAndResumingR1 : TestResult { :>> id = "c0f1a5cc-6f0b-4a10-9b20-a1b2c3d40f0b"; :>> outcome = VerdictKind::pass; :>> judgedAgainst = "06c2210"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; plugin-wiring statusDisplay cases
        part statusDetailAndResumingDoDR2 : TestResult { :>> id = "767f0999-3843-4e43-8dc6-4a7b9fb5bfd8"; :>> outcome = VerdictKind::pass; :>> judgedAgainst = "468027ac"; :>> judgedAt = "2026-09-07"; :>> judgedBy = "claudeOpus"; }
        part forkVaultR1 : TestResult { :>> id = "c0f1a5cc-6f0c-4a10-9b20-a1b2c3d40f0c"; :>> outcome = VerdictKind::pass; :>> judgedAgainst = "f4ef4fc"; :>> judgedAt = "2026-07-13"; :>> judgedBy = "ai"; }
        // RAN: RE-INSPECTED 2026-09-07 at HEAD 468027ac: main.ts:1328 forkVault(name) = createRemoteVault(name) then switchToVault(name, 'upload', '', false); vaultswitch.ts 'Fork over an existing vault?' guard at :113
        part forkVaultDoDR2 : TestResult { :>> id = "46d3ef65-e300-4690-a6d8-6f09dac2eb5a"; :>> outcome = VerdictKind::pass; :>> judgedAgainst = "468027ac"; :>> judgedAt = "2026-09-07"; :>> judgedBy = "claudeOpus"; }
        part uxPolishBundleR1 : TestResult { :>> id = "c0f1a5cc-6f0d-4a10-9b20-a1b2c3d40f0d"; :>> outcome = VerdictKind::pass; :>> judgedAgainst = "d96ee43"; :>> judgedAt = "2026-07-13"; :>> judgedBy = "ai"; }
        // RAN: RE-INSPECTED 2026-09-07 at HEAD 468027ac: noteconflict.ts button 'Keep the other device's' (1 site); 'fully close and reopen Obsidian' wording in main.ts (4) + settings.ts (1); 'SelfSync: '-prefixed notices (accountui.ts)
        part uxPolishBundleDoDR2 : TestResult { :>> id = "d55f730f-02db-4c0e-9065-fa016f682672"; :>> outcome = VerdictKind::pass; :>> judgedAgainst = "468027ac"; :>> judgedAt = "2026-09-07"; :>> judgedBy = "claudeOpus"; }
        part guardDestructiveActionsR1 : TestResult { :>> id = "c0f1a5cc-6f0e-4a10-9b20-a1b2c3d40f0e"; :>> outcome = VerdictKind::pass; :>> judgedAgainst = "5a983c3"; :>> judgedAt = "2026-07-13"; :>> judgedBy = "ai"; }
        // RAN: RE-INSPECTED 2026-09-07 at HEAD 468027ac: vaultswitch.ts gates fork-over-existing (:113), leave-shared (:126) and the destructive switch modes (:182) behind confirmModal; settings.ts:378 Sign out behind confirmModal - the window.confirm() of 1.3.2 became the in-app confirm modal (confirm.dom.test green in the same run)
        part guardDestructiveActionsDoDR2 : TestResult { :>> id = "1a16cb00-75a3-4955-98bf-0e30190497c8"; :>> outcome = VerdictKind::pass; :>> judgedAgainst = "468027ac"; :>> judgedAt = "2026-09-07"; :>> judgedBy = "claudeOpus"; }
        part pluginAdoptionRestartHintR1 : TestResult { :>> id = "c0f1a5cc-6f0f-4a10-9b20-a1b2c3d40f0f"; :>> outcome = VerdictKind::pass; :>> judgedAgainst = "a87d6bc"; :>> judgedAt = "2026-07-13"; :>> judgedBy = "ai"; }
        // RAN: RE-INSPECTED 2026-09-07 at HEAD 468027ac: settings.ts:872 needsRestart = syncedIds adopted AND not installed; :874 warning banner counting them; :881 'Checking the server for plugins...' placeholder when the server list is not yet reported
        part pluginAdoptionRestartHintDoDR2 : TestResult { :>> id = "170bb7fd-0edb-4b3f-904d-7cc1de636e0a"; :>> outcome = VerdictKind::pass; :>> judgedAgainst = "468027ac"; :>> judgedAt = "2026-09-07"; :>> judgedBy = "claudeOpus"; }
        part surfaceSharingAndConflictsR1 : TestResult { :>> id = "c0f1a5cc-6f10-4a10-9b20-a1b2c3d40f10"; :>> outcome = VerdictKind::pass; :>> judgedAgainst = "8c7fa93"; :>> judgedAt = "2026-07-13"; :>> judgedBy = "ai"; }
        // RAN: RE-INSPECTED 2026-09-07 at HEAD 468027ac: main.ts addCommand ids present: setup, switch-vault, redeem, resolve-conflicts, status, show-log, clear-log, reconnect
        part surfaceSharingAndConflictsDoDR2 : TestResult { :>> id = "03236a75-495c-45a9-8fb9-1ef9f975f683"; :>> outcome = VerdictKind::pass; :>> judgedAgainst = "468027ac"; :>> judgedAt = "2026-09-07"; :>> judgedBy = "claudeOpus"; }
        part deferUxEnhancementsR1 : TestResult { :>> id = "c0f1a5cc-6f11-4a10-9b20-a1b2c3d40f11"; :>> outcome = VerdictKind::pass; :>> judgedAgainst = "08f44e6"; :>> judgedAt = "2026-07-13"; :>> judgedBy = "wweatherholtz"; }
        part hfStatusAndWarningsR1 : TestResult { :>> id = "c0f1a5cc-6f12-4a10-9b20-a1b2c3d40f12"; :>> outcome = VerdictKind::pass; :>> judgedAgainst = "74f701a"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; syncstate tests
        part hfStatusAndWarningsDoDR2 : TestResult { :>> id = "7bb6580c-d1f9-4139-935e-eb7e97ed3555"; :>> outcome = VerdictKind::pass; :>> judgedAgainst = "468027ac"; :>> judgedAt = "2026-09-07"; :>> judgedBy = "claudeOpus"; }
        part hfStatusSurfacingAndPreviewR1 : TestResult { :>> id = "c0f1a5cc-6f15-4a10-9b20-a1b2c3d40f15"; :>> outcome = VerdictKind::pass; :>> judgedAgainst = "80555a2"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; plugin-wiring statusDisplay cases
        part hfStatusSurfacingAndPreviewDoDR2 : TestResult { :>> id = "686b6a69-921a-4175-9119-3a84884c06cf"; :>> outcome = VerdictKind::pass; :>> judgedAgainst = "468027ac"; :>> judgedAt = "2026-09-07"; :>> judgedBy = "claudeOpus"; }
        part hfConfirmAndSidePickingR1 : TestResult { :>> id = "c0f1a5cc-6f13-4a10-9b20-a1b2c3d40f13"; :>> outcome = VerdictKind::pass; :>> judgedAgainst = "80555a2"; :>> judgedAt = "2026-07-13"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; modals-ui.dom
        part hfConfirmAndSidePickingDoDR2 : TestResult { :>> id = "07b27c1a-d577-43f8-a6bb-c2e121b1781f"; :>> outcome = VerdictKind::pass; :>> judgedAgainst = "468027ac"; :>> judgedAt = "2026-09-07"; :>> judgedBy = "claudeOpus"; }
        part shareRedeemStoreConsistencyR1 : TestResult { :>> id = "c0f1a5cc-6f02-4a10-9b20-a1b2c3d40f02"; :>> outcome = VerdictKind::pass; :>> judgedAgainst = "abc13a2"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; grant_rolls_back_in_memory_when_save_fails, self_redeem_does_not_burn_the_link, share_link_owner_scoped_and_revoke_blocks_redeem (present)
        part shareRedeemStoreConsistencyDoDR2 : TestResult { :>> id = "85e9562c-adfd-414f-a48d-27014f2576cc"; :>> outcome = VerdictKind::pass; :>> judgedAgainst = "468027ac"; :>> judgedAt = "2026-09-07"; :>> judgedBy = "claudeOpus"; }
        part pendingProgressAndConflictResilienceR1 : TestResult { :>> id = "c0f1a5cc-60dc-4a10-9b20-a1b2c3d400dc"; :>> outcome = VerdictKind::pass; :>> judgedAgainst = "c357b42"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; syncstate + reconcile onProgress tests
        part pendingProgressAndConflictResilienceDoDR2 : TestResult { :>> id = "79b9e017-85b1-4b05-802f-1b327bd33f8f"; :>> outcome = VerdictKind::pass; :>> judgedAgainst = "468027ac"; :>> judgedAt = "2026-09-07"; :>> judgedBy = "claudeOpus"; }
        part conflictModalFixAndSyncProgressR1 : TestResult { :>> id = "c0f1a5cc-60db-4a10-9b20-a1b2c3d400db"; :>> outcome = VerdictKind::pass; :>> judgedAgainst = "8e99aad"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; modals-ui.dom conflict + settings-ui.dom
        part conflictModalFixAndSyncProgressDoDR2 : TestResult { :>> id = "2a507264-9ef1-4ff4-8f85-5ee59eeb6d7e"; :>> outcome = VerdictKind::pass; :>> judgedAgainst = "468027ac"; :>> judgedAt = "2026-09-07"; :>> judgedBy = "claudeOpus"; }
        part falseEolConflictFixAndDiffR1 : TestResult { :>> id = "c0f1a5cc-60da-4a10-9b20-a1b2c3d400da"; :>> outcome = VerdictKind::pass; :>> judgedAgainst = "d46a9ac"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile.test sameIgnoringEol
        part falseEolConflictFixAndDiffDoDR2 : TestResult { :>> id = "b33746bc-8ba8-405e-a63a-9a54e658dea1"; :>> outcome = VerdictKind::pass; :>> judgedAgainst = "468027ac"; :>> judgedAt = "2026-09-07"; :>> judgedBy = "claudeOpus"; }
        part granteeLeaveShareR1 : TestResult { :>> id = "c0f1a5cc-60d9-4a10-9b20-a1b2c3d400d9"; :>> outcome = VerdictKind::pass; :>> judgedAgainst = "f91200e"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server DELETE /api/shared tests + client
        part granteeLeaveShareDoDR2 : TestResult { :>> id = "193bce25-8179-4fe9-b1d1-9ef5c38aa1cf"; :>> outcome = VerdictKind::pass; :>> judgedAgainst = "468027ac"; :>> judgedAt = "2026-09-07"; :>> judgedBy = "claudeOpus"; }
        part settingsPanelTargetedCleanupR1 : TestResult { :>> id = "c0f1a5cc-60d8-4a10-9b20-a1b2c3d400d8"; :>> outcome = VerdictKind::pass; :>> judgedAgainst = "8bd5259"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; settings-ui.dom + modals-ui.dom
        part settingsPanelTargetedCleanupDoDR2 : TestResult { :>> id = "0a2315a8-3551-4cf1-9b98-12d3cdeb02ff"; :>> outcome = VerdictKind::pass; :>> judgedAgainst = "468027ac"; :>> judgedAt = "2026-09-07"; :>> judgedBy = "claudeOpus"; }
        part redeemE2ECoverageR1 : TestResult { :>> id = "c0f1a5cc-60d7-4a10-9b20-a1b2c3d400d7"; :>> outcome = VerdictKind::pass; :>> judgedAgainst = "d96a412"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharing-e2e.spec (2 tests) RAN against the real server binary in this run
        part redeemE2ECoverageDoDR2 : TestResult { :>> id = "92db03b1-2d71-4da1-9943-5ecccf850946"; :>> outcome = VerdictKind::pass; :>> judgedAgainst = "468027ac"; :>> judgedAt = "2026-09-07"; :>> judgedBy = "claudeOpus"; }
        part wizardForcedPasswordChangeR1 : TestResult { :>> id = "c0f1a5cc-60d6-4a10-9b20-a1b2c3d400d6"; :>> outcome = VerdictKind::pass; :>> judgedAgainst = "9ca6592"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; modals-ui.dom 'a must-change account is prompted for a new password before any other call' (present)
        part wizardForcedPasswordChangeDoDR2 : TestResult { :>> id = "9f5e96ec-c58f-4047-bb5e-2143917531df"; :>> outcome = VerdictKind::pass; :>> judgedAgainst = "468027ac"; :>> judgedAt = "2026-09-07"; :>> judgedBy = "claudeOpus"; }
        part guidedRedeemViaSetupR1 : TestResult { :>> id = "c0f1a5cc-60d5-4a10-9b20-a1b2c3d400d5"; :>> outcome = VerdictKind::pass; :>> judgedAgainst = "407f913"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharelink redeemTargetError cases
        part guidedRedeemViaSetupDoDR2 : TestResult { :>> id = "957ed2df-8e82-436b-975d-ee9c5c0a6b3d"; :>> outcome = VerdictKind::pass; :>> judgedAgainst = "468027ac"; :>> judgedAt = "2026-09-07"; :>> judgedBy = "claudeOpus"; }
        part redeemNotSetUpGuardAndDirectR1 : TestResult { :>> id = "c0f1a5cc-60d4-4a10-9b20-a1b2c3d400d4"; :>> outcome = VerdictKind::pass; :>> judgedAgainst = "9905319"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharelink.test redeemTargetError
        part redeemNotSetUpGuardAndDirectDoDR2 : TestResult { :>> id = "feb7cccd-eccd-4110-9107-0ad1b8e26077"; :>> outcome = VerdictKind::pass; :>> judgedAgainst = "468027ac"; :>> judgedAt = "2026-09-07"; :>> judgedBy = "claudeOpus"; }
        part shareLinkUrlParseFixR1 : TestResult { :>> id = "c0f1a5cc-60d3-4a10-9b20-a1b2c3d400d3"; :>> outcome = VerdictKind::pass; :>> judgedAgainst = "c450a0c"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sharelink + connstr parse tests
        part shareLinkUrlParseFixDoDR2 : TestResult { :>> id = "aa52d1f3-67b2-44f3-9dbc-c3ac0c06d285"; :>> outcome = VerdictKind::pass; :>> judgedAgainst = "468027ac"; :>> judgedAt = "2026-09-07"; :>> judgedBy = "claudeOpus"; }
        part shareCurrentVaultOnlyR1 : TestResult { :>> id = "c0f1a5cc-60d2-4a10-9b20-a1b2c3d400d2"; :>> outcome = VerdictKind::pass; :>> judgedAgainst = "9137835"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; modals-ui.dom share modal test
        part shareCurrentVaultOnlyDoDR2 : TestResult { :>> id = "4ce83245-3e31-4d81-8d45-7bd60425cf12"; :>> outcome = VerdictKind::pass; :>> judgedAgainst = "468027ac"; :>> judgedAt = "2026-09-07"; :>> judgedBy = "claudeOpus"; }
        part shareUxAndCaseInsensitiveNamesR1 : TestResult { :>> id = "c0f1a5cc-60d1-4a10-9b20-a1b2c3d400d1"; :>> outcome = VerdictKind::pass; :>> judgedAgainst = "dd1bbb5"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; transport errText + sharing tests
        part shareUxAndCaseInsensitiveNamesDoDR2 : TestResult { :>> id = "e8421743-e049-4b08-802f-324f8b69cdfd"; :>> outcome = VerdictKind::pass; :>> judgedAgainst = "468027ac"; :>> judgedAt = "2026-09-07"; :>> judgedBy = "claudeOpus"; }
        part usernameRuleAndUxR1 : TestResult { :>> id = "c0f1a5cc-60d0-4a10-9b20-a1b2c3d400d0"; :>> outcome = VerdictKind::pass; :>> judgedAgainst = "85308fb"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; sync.rs userstore_register_verify_persist
        part usernameRuleAndUxDoDR2 : TestResult { :>> id = "81859f2a-2b49-4eca-b0e6-28d686898ee4"; :>> outcome = VerdictKind::pass; :>> judgedAgainst = "468027ac"; :>> judgedAt = "2026-09-07"; :>> judgedBy = "claudeOpus"; }
        part skipOsJunkFilesR1 : TestResult { :>> id = "c0f1a5cc-60cf-4a10-9b20-a1b2c3d400cf"; :>> outcome = VerdictKind::pass; :>> judgedAgainst = "3a28dfb"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; configsync.test isJunkFile/shouldSync
        part skipOsJunkFilesDoDR2 : TestResult { :>> id = "403ead0a-1105-4b77-8a2e-6bba04e2626c"; :>> outcome = VerdictKind::pass; :>> judgedAgainst = "468027ac"; :>> judgedAt = "2026-09-07"; :>> judgedBy = "claudeOpus"; }
        part vaultNameAndSizeLimitsR1 : TestResult { :>> id = "c0f1a5cc-60ce-4a10-9b20-a1b2c3d400ce"; :>> outcome = VerdictKind::pass; :>> judgedAgainst = "2880a1e"; :>> judgedAt = "2026-07-12"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; commit_over_size_limit_is_rejected + wizardsteps.test isValidVaultName/sanitizeVaultName (present)
        part vaultNameAndSizeLimitsDoDR2 : TestResult { :>> id = "191241bb-93f2-49cb-a06e-1f17748c3a9d"; :>> outcome = VerdictKind::pass; :>> judgedAgainst = "468027ac"; :>> judgedAt = "2026-09-07"; :>> judgedBy = "claudeOpus"; }
        part deployComposeHardeningR1 : TestResult { :>> id = "c0f1a5cc-60cd-4a10-9b20-a1b2c3d400cd"; :>> outcome = VerdictKind::pass; :>> judgedAgainst = "7b96ef8"; :>> judgedAt = "2026-07-12"; :>> judgedBy = "ai"; }
        // RAN: RE-INSPECTED 2026-09-07 at HEAD 468027ac: deploy/docker-compose.yml: image ghcr.io/williamweatherholtz/obsidian-selfsync-server:latest (no build:), healthcheck present, caddy:2 proxy; the server-image publish job now lives in .github/workflows/server-image.yml and ran green on d0ac3d66 today
        part deployComposeHardeningDoDR2 : TestResult { :>> id = "ff76314b-a49a-4980-9d70-0c140c2f079e"; :>> outcome = VerdictKind::pass; :>> judgedAgainst = "468027ac"; :>> judgedAt = "2026-09-07"; :>> judgedBy = "claudeOpus"; }
        part perfHarnessScaleLatencyR1 : TestResult { :>> id = "c0f1a5cc-60cb-4a10-9b20-a1b2c3d400cb"; :>> outcome = VerdictKind::pass; :>> judgedAgainst = "7b96ef8"; :>> judgedAt = "2026-07-12"; :>> judgedBy = "ai"; }
        // RAN: RAN 2026-09-07 at HEAD 468027ac: cd client && npm run test:perf (vitest.perf.config, real server binary + headless clients) -> 3 files / 9 tests passed, 63.45s. SCALE (push s / pull s / no-op rescan ms): 200 notes 2.53/0.13/12; 1000 notes 6.40/0.31/49; 3020 files incl. 20x256KB (9.3 MB) 19.15/0.81/143 (158 notes/s). LATENCY A->B round-trip: 50-note vault 19-22 ms across paths; 3000-note vault 17-23 ms (delta path). Honest numbers over the real chunk/reconcile engine, as the DoD requires.
        part perfHarnessScaleLatencyDoDR2 : TestResult { :>> id = "ca0112c3-61b4-4d60-b4de-1ada0b5fcd8c"; :>> outcome = VerdictKind::pass; :>> judgedAgainst = "468027ac"; :>> judgedAt = "2026-09-07"; :>> judgedBy = "claudeOpus"; }
        // Server hardening (pre-round-1 backlog) + the Round-1 fresh-critic fixes both landed by f7cedca
        // (0.10.17). Server-side fixes are cargo-green and CODE-complete; they take effect on redeploy.
        part critiqueServerHardeningR1 : TestResult { :>> id = "c0f1a5cc-6005-4a10-9b20-a1b2c3d40055"; :>> outcome = VerdictKind::pass; :>> judgedAgainst = "f7cedca"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server hardening tests incl. WS token via subprotocol
        part critiqueServerHardeningDoDR2 : TestResult { :>> id = "8521722b-dc28-4a8d-86c4-e791551f86cd"; :>> outcome = VerdictKind::pass; :>> judgedAgainst = "468027ac"; :>> judgedAt = "2026-09-07"; :>> judgedBy = "claudeOpus"; }
        part round1CriticFixesR1 : TestResult { :>> id = "c0f1a5cc-6006-4a10-9b20-a1b2c3d40056"; :>> outcome = VerdictKind::pass; :>> judgedAgainst = "f7cedca"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client + server suites
        part round1CriticFixesDoDR2 : TestResult { :>> id = "2ee80ccd-3a48-41f7-b3b4-402eab1c1388"; :>> outcome = VerdictKind::pass; :>> judgedAgainst = "468027ac"; :>> judgedAt = "2026-09-07"; :>> judgedBy = "claudeOpus"; }
        // Round-2 critic fixes landed by a3e69e1 (0.10.18); server-side takes effect on redeploy.
        part round2CriticFixesR1 : TestResult { :>> id = "c0f1a5cc-6007-4a10-9b20-a1b2c3d40057"; :>> outcome = VerdictKind::pass; :>> judgedAgainst = "a3e69e1"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client + server suites
        part round2CriticFixesDoDR2 : TestResult { :>> id = "3f8688a9-d53c-4342-9089-5bb6c0e1e9ee"; :>> outcome = VerdictKind::pass; :>> judgedAgainst = "468027ac"; :>> judgedAt = "2026-09-07"; :>> judgedBy = "claudeOpus"; }
        // Round-3 critic fixes landed by 1d5ccca (0.10.19); server-side takes effect on redeploy.
        part round3CriticFixesR1 : TestResult { :>> id = "c0f1a5cc-6008-4a10-9b20-a1b2c3d40058"; :>> outcome = VerdictKind::pass; :>> judgedAgainst = "1d5ccca"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client + server suites
        part round3CriticFixesDoDR2 : TestResult { :>> id = "2d751dc4-9288-437c-a9a9-4e0ae7d52fe1"; :>> outcome = VerdictKind::pass; :>> judgedAgainst = "468027ac"; :>> judgedAt = "2026-09-07"; :>> judgedBy = "claudeOpus"; }
        // Round-4 critic fixes landed by 9318f41 (0.10.20); server-side takes effect on redeploy.
        part round4CriticFixesR1 : TestResult { :>> id = "c0f1a5cc-6009-4a10-9b20-a1b2c3d40059"; :>> outcome = VerdictKind::pass; :>> judgedAgainst = "9318f41"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client + server suites
        part round4CriticFixesDoDR2 : TestResult { :>> id = "88d7eb4f-e8a8-4676-9c20-7c50d3ae4a42"; :>> outcome = VerdictKind::pass; :>> judgedAgainst = "468027ac"; :>> judgedAt = "2026-09-07"; :>> judgedBy = "claudeOpus"; }
        // Round-5 correctness fixes landed by 5d2ab0b (0.10.21). round5CompletenessFollowups is
        // intentionally left with NO result — it's the OPEN pre-broad-release enhancement backlog.
        part round5CriticFixesR1 : TestResult { :>> id = "c0f1a5cc-600a-4a10-9b20-a1b2c3d4005a"; :>> outcome = VerdictKind::pass; :>> judgedAgainst = "5d2ab0b"; :>> judgedAt = "2026-07-05"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; vault.rs commit_rejects_unicode_case_collision_and_delete_evicts_legacy_key; revoke-before-purge in the admin suite
        part round5CriticFixesDoDR2 : TestResult { :>> id = "eb60afd7-4d18-4ce5-94da-64dbda63e87c"; :>> outcome = VerdictKind::pass; :>> judgedAgainst = "468027ac"; :>> judgedAt = "2026-09-07"; :>> judgedBy = "claudeOpus"; }
        part pluginShareOptInR1 : TestResult { :>> id = "c0f1a5cc-600b-4a10-9b20-a1b2c3d4005b"; :>> outcome = VerdictKind::pass; :>> judgedAgainst = "4165b72"; :>> judgedAt = "2026-07-06"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client configsync suite
        part pluginShareOptInDoDR2 : TestResult { :>> id = "4b056849-0478-4675-bc6c-f06d334e5454"; :>> outcome = VerdictKind::pass; :>> judgedAgainst = "468027ac"; :>> judgedAt = "2026-09-07"; :>> judgedBy = "claudeOpus"; }
        part fsmRefactorR1 : TestResult { :>> id = "c0f1a5cc-600c-4a10-9b20-a1b2c3d4005c"; :>> outcome = VerdictKind::pass; :>> judgedAgainst = "71a7659"; :>> judgedAt = "2026-07-06"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client engine suite (syncengine)
        part fsmRefactorDoDR2 : TestResult { :>> id = "2ae97fa0-9594-487f-9f1f-db67ea7c27ba"; :>> outcome = VerdictKind::pass; :>> judgedAgainst = "468027ac"; :>> judgedAt = "2026-09-07"; :>> judgedBy = "claudeOpus"; }
        // The tombstone-authoritative delete fix shipped at a9f2ee7 (0.10.25).
        part deleteLocalTombstoneGateR1 : TestResult { :>> id = "c0f1a5cc-600d-4a10-9b20-a1b2c3d4005d"; :>> outcome = VerdictKind::pass; :>> judgedAgainst = "a9f2ee7"; :>> judgedAt = "2026-07-06"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; client reconcile tombstone-gate tests
        part deleteLocalTombstoneGateDoDR2 : TestResult { :>> id = "02498fdb-51c8-4a04-8ef5-8b9c6a2d2bea"; :>> outcome = VerdictKind::pass; :>> judgedAgainst = "468027ac"; :>> judgedAt = "2026-09-07"; :>> judgedBy = "claudeOpus"; }
        // Pre-broad-release hardening (version handshake + admin reindex + commit CAS + crutch cleanups) shipped at af29408 (0.10.26).
        part preReleaseHardeningR1 : TestResult { :>> id = "c0f1a5cc-600e-4a10-9b20-a1b2c3d4005e"; :>> outcome = VerdictKind::pass; :>> judgedAgainst = "af29408"; :>> judgedAt = "2026-07-06"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; commit_cas_rejects_stale_expected_version + client CAS/reactive-401 tests
        part preReleaseHardeningDoDR2 : TestResult { :>> id = "55830bd3-7261-40ea-adda-47a0dfa5cc9a"; :>> outcome = VerdictKind::pass; :>> judgedAgainst = "468027ac"; :>> judgedAt = "2026-09-07"; :>> judgedBy = "claudeOpus"; }
        // Round-6 critique fixes shipped at 1b12c97 (0.10.27). historyRebase + stpaSuspicionPropagation stay OPEN (no result).
        part round6CriticFixesR1 : TestResult { :>> id = "c0f1a5cc-600f-4a10-9b20-a1b2c3d4005f"; :>> outcome = VerdictKind::pass; :>> judgedAgainst = "1b12c97"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server lib + integration, client unit + e2e
        part round6CriticFixesDoDR2 : TestResult { :>> id = "ae41b768-ff45-48eb-8f52-57d73be50dfb"; :>> outcome = VerdictKind::pass; :>> judgedAgainst = "468027ac"; :>> judgedAt = "2026-09-07"; :>> judgedBy = "claudeOpus"; }
        // Round-7 recovery fixes shipped at a4bb3bf (0.10.28). scaleHardening + historyRebase stay OPEN.
        part round7RecoveryFixesR1 : TestResult { :>> id = "c0f1a5cc-6010-4a10-9b20-a1b2c3d40060"; :>> outcome = VerdictKind::pass; :>> judgedAgainst = "a4bb3bf"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reindex_recovers_from_store_and_force_drops_truly_lost (present at HEAD)
        part round7RecoveryFixesDoDR2 : TestResult { :>> id = "1974d82a-d74b-42ac-82d0-e30e350531a7"; :>> outcome = VerdictKind::pass; :>> judgedAgainst = "468027ac"; :>> judgedAt = "2026-09-07"; :>> judgedBy = "claudeOpus"; }
        // RS-3 incremental reconcile shipped at 23e8752 (0.10.29). scaleHardening (RS-1/4) + sqliteMigration + historyRebase stay OPEN.
        part incrementalReconcileR1 : TestResult { :>> id = "c0f1a5cc-6011-4a10-9b20-a1b2c3d40061"; :>> outcome = VerdictKind::pass; :>> judgedAgainst = "23e8752"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; reconcile incremental/mass-tombstone tests
        part incrementalReconcileDoDR2 : TestResult { :>> id = "3ae5a56a-0ff9-4a8e-92a2-5ea4cb3185f4"; :>> outcome = VerdictKind::pass; :>> judgedAgainst = "468027ac"; :>> judgedAt = "2026-09-07"; :>> judgedBy = "claudeOpus"; }
        // RS-1 + RS-4 shipped at 35a94f3 (0.10.30). scaleHardening now holds only RS-5 base-persist (Low); sqliteMigration (RS-2/5/6/7) + historyRebase stay OPEN.
        part resourceScaleFixesR1 : TestResult { :>> id = "c0f1a5cc-6012-4a10-9b20-a1b2c3d40062"; :>> outcome = VerdictKind::pass; :>> judgedAgainst = "35a94f3"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server integration + client RS-4 base-cap test
        part resourceScaleFixesDoDR2 : TestResult { :>> id = "910870e9-a2c9-4ee8-83db-14151f757010"; :>> outcome = VerdictKind::pass; :>> judgedAgainst = "468027ac"; :>> judgedAt = "2026-09-07"; :>> judgedBy = "claudeOpus"; }
        // SQLite migration DONE at 05e655b (server-only; no plugin release — protocol + client unchanged). Resolves the storage-format-dependent scale findings RS-2/5/6/7 (issueIndexClonePerWrite/issueLinearChangesScan/issueFullSnapshotCost/issueColdOpenCost). historyRebase (RC-1, uses the SQLite history_floor column) + stpaSafetyAnalysis + stpaSuspicionPropagation stay OPEN.
        part sqliteMigrationR1 : TestResult { :>> id = "c0f1a5cc-6013-4a10-9b20-a1b2c3d40063"; :>> outcome = VerdictKind::pass; :>> judgedAgainst = "05e655b"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; index_store.rs (SQLite, WAL, migration) + its tests (mutationTestingIndexChunkstore pass)
        part sqliteMigrationDoDR2 : TestResult { :>> id = "186b9b7c-610a-4853-ba08-f0fc7b339dce"; :>> outcome = VerdictKind::pass; :>> judgedAgainst = "468027ac"; :>> judgedAt = "2026-09-07"; :>> judgedBy = "claudeOpus"; }
        // scaleHardening (the RS umbrella) DONE at 05e655b — satisfied by resourceScaleFixes (RS-1/4) + incrementalReconcile (RS-3) + sqliteMigration (RS-2/5/6/7); every RS-1..7 finding shipped or mooted.
        part scaleHardeningR1 : TestResult { :>> id = "c0f1a5cc-6014-4a10-9b20-a1b2c3d40064"; :>> outcome = VerdictKind::pass; :>> judgedAgainst = "05e655b"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; umbrella over RS-1..7; resolved by sqliteMigration/resourceScaleFixes/incrementalReconcile, all in the same green run
        part scaleHardeningDoDR2 : TestResult { :>> id = "be49239d-6500-478a-b690-daba74cdc7dd"; :>> outcome = VerdictKind::pass; :>> judgedAgainst = "468027ac"; :>> judgedAt = "2026-09-07"; :>> judgedBy = "claudeOpus"; }
        // historyRebase (the deletion-history horizon, D0019) DONE at 8c69b8b (0.10.31) — closes RC-1
        // (issueCorruptReindexResurrection). tombstonePrune (the deferred active prune) stays OPEN.
        part historyRebaseR1 : TestResult { :>> id = "c0f1a5cc-6015-4a10-9b20-a1b2c3d40065"; :>> outcome = VerdictKind::pass; :>> judgedAgainst = "8c69b8b"; :>> judgedAt = "2026-07-07"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server history-floor tests + client onKeptAbsent
        part historyRebaseDoDR2 : TestResult { :>> id = "a5fcab03-862e-403a-819a-d2dc88259634"; :>> outcome = VerdictKind::pass; :>> judgedAgainst = "468027ac"; :>> judgedAt = "2026-09-07"; :>> judgedBy = "claudeOpus"; }
        // round1DeferredHardening DONE at 7524aba (0.10.32): SEC#4 runtime orphan GC + CONC#5 durable
        // pending-switch (DI#4 already in round6). Resolves issueOrphanChunkQuota + issueSwitchPendingClear;
        // the 4 accreted deferred/accepted LOW items moved to residualLowFindings (stays open).
        part round1DeferredHardeningR1 : TestResult { :>> id = "c0f1a5cc-6016-4a10-9b20-a1b2c3d40066"; :>> outcome = VerdictKind::pass; :>> judgedAgainst = "7524aba"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; SEC#4 runtime_orphan_sweep_runs_on_upload_but_spares_inflight_chunks, DI#4 reindex_prefers_store_over_stale_mirror_when_healthy, CONC#5 pendingSwitch cases in plugin-wiring.test (present)
        part round1DeferredHardeningDoDR2 : TestResult { :>> id = "866bc969-2f03-45d3-8911-26a2002c7cd0"; :>> outcome = VerdictKind::pass; :>> judgedAgainst = "468027ac"; :>> judgedAt = "2026-09-07"; :>> judgedBy = "claudeOpus"; }
        // round5CompletenessFollowups DONE at 10a7154 (0.10.33): items 2/5/6/7 (orchestration raw-event
        // test, data-migration seam + schema tag + GC wording, cosmetic conflict-copy); 1/3/4 were in
        // preReleaseHardening. Resolves issueOrchestrationUntested + issueDataMigration + issueConflictCopyCosmetic.
        part round5CompletenessFollowupsR1 : TestResult { :>> id = "c0f1a5cc-6017-4a10-9b20-a1b2c3d40067"; :>> outcome = VerdictKind::pass; :>> judgedAgainst = "10a7154"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; server lib + integration + e2e, client reconcile + plugin-wiring
        part round5CompletenessFollowupsDoDR2 : TestResult { :>> id = "3a0103fd-f0fd-47dc-bcfb-561eab1871d8"; :>> outcome = VerdictKind::pass; :>> judgedAgainst = "468027ac"; :>> judgedAt = "2026-09-07"; :>> judgedBy = "claudeOpus"; }
        // tombstonePrune (server-only, D0019) DONE at 8025fb2 — the deliberate operator prune + admin
        // endpoint. Resolves issueUnboundedTombstones (the horizon's active space bound).
        part tombstonePruneR1 : TestResult { :>> id = "c0f1a5cc-6018-4a10-9b20-a1b2c3d40068"; :>> outcome = VerdictKind::pass; :>> judgedAgainst = "8025fb2"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; admin_reindex_and_prune_history_http_ok + history-floor tests
        part tombstonePruneDoDR2 : TestResult { :>> id = "d04e013f-c259-4069-993c-d12abcae3738"; :>> outcome = VerdictKind::pass; :>> judgedAgainst = "468027ac"; :>> judgedAt = "2026-09-07"; :>> judgedBy = "claudeOpus"; }
        // settingsGroupingPolish DONE by inspection at 26dc385 — the goal-#1 settings tab is already
        // intelligently grouped (status-first + 4 concern sections), never atomized. Resolves issueSettingsGrouping.
        part settingsGroupingPolishR1 : TestResult { :>> id = "c0f1a5cc-6019-4a10-9b20-a1b2c3d40069"; :>> outcome = VerdictKind::pass; :>> judgedAgainst = "26dc385"; :>> judgedAt = "2026-07-08"; :>> judgedBy = "ai"; }
        // D0021 admin-interface changes. adminSplitDeploy + adminPortalEnhancements shipped server-side
        // at 8951b43 (redeploy; 61 lib + 19 integration green incl. admin_split_isolates_surfaces).
        // deletedVaultRecreatePrompt shipped in the plugin at 1881e94 (0.10.34).
        part adminSplitDeployR1 : TestResult { :>> id = "c0f1a5cc-601a-4a10-9b20-a1b2c3d4006a"; :>> outcome = VerdictKind::pass; :>> judgedAgainst = "8951b43"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; default_admin_bind + admin router integration tests (present)
        part adminSplitDeployDoDR2 : TestResult { :>> id = "edcc2ccc-5108-4b88-8858-60a5d5d50ce3"; :>> outcome = VerdictKind::pass; :>> judgedAgainst = "468027ac"; :>> judgedAt = "2026-09-07"; :>> judgedBy = "claudeOpus"; }
        part adminPortalEnhancementsR1 : TestResult { :>> id = "c0f1a5cc-601b-4a10-9b20-a1b2c3d4006b"; :>> outcome = VerdictKind::pass; :>> judgedAgainst = "8951b43"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; admin_grant_and_revoke_toggles_admin_access, admin_deletes_an_account (present)
        part adminPortalEnhancementsDoDR2 : TestResult { :>> id = "2ab54d89-30f9-4d44-9aed-f037c3879db4"; :>> outcome = VerdictKind::pass; :>> judgedAgainst = "468027ac"; :>> judgedAt = "2026-09-07"; :>> judgedBy = "claudeOpus"; }
        part deletedVaultRecreatePromptR1 : TestResult { :>> id = "c0f1a5cc-601c-4a10-9b20-a1b2c3d4006c"; :>> outcome = VerdictKind::pass; :>> judgedAgainst = "1881e94"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; plugin-wiring test
        part deletedVaultRecreatePromptDoDR2 : TestResult { :>> id = "8bbf95d6-e41e-4765-83df-670ab689eaee"; :>> outcome = VerdictKind::pass; :>> judgedAgainst = "468027ac"; :>> judgedAt = "2026-09-07"; :>> judgedBy = "claudeOpus"; }
        // autoReindex (D0022) DONE at b50012d — vaults self-heal on open; one-click admin reindex.
        part autoReindexR1 : TestResult { :>> id = "c0f1a5cc-601d-4a10-9b20-a1b2c3d4006d"; :>> outcome = VerdictKind::pass; :>> judgedAgainst = "b50012d"; :>> judgedAt = "2026-07-08"; :>> judgedBy = "ai"; }
        // RAN: RAN 2026-09-07 at HEAD 468027ac (clean tree): cd server && cargo test --locked -> 9 suites ok (153+34+21+10+8+5+2+1 tests, 0 failed); cargo clippy --all-targets --locked -- -D warnings -> clean; cd client && npx tsc --noEmit && npm run build -> ok; npx vitest run -> 53 files passed / 1 skipped (config-permutations standalone matrix, SELFSYNC_PERM unset), 882 tests passed / 2 skipped, 89.4s, with the real-server integration + sharing e2e specs RUNNING (server/target/debug/selfsync-server.exe present); npx tsc -p tsconfig.e2e.json -> ok. Backfill basis: this DoD's criterion is the suites green; empty_index_with_data_auto_repairs, reindex_recovers_from_store_and_force_drops_truly_lost, reindex_routes_a_bitrotted_recovered_file_to_lost_not_corruption, admin_reindex_and_prune_history_http_ok (present)
        part autoReindexDoDR2 : TestResult { :>> id = "359f71bd-d046-4313-9993-f3b5f11520ef"; :>> outcome = VerdictKind::pass; :>> judgedAgainst = "468027ac"; :>> judgedAt = "2026-09-07"; :>> judgedBy = "claudeOpus"; }
        // Critique R8 (4-lens) fixes shipped at 6f19f71 (0.10.35). Residual MED/LOW findings tracked as
        // open issues (issueDoubleOpenRace, issueChangesOnAsyncWorker) — not shipped this round.
        part critiqueR8FixesR1 : TestResult { :>> id = "c0f1a5cc-601e-4a10-9b20-a1b2c3d4006e"; :>> outcome = VerdictKind::pass; :>> judgedAgainst = "6f19f71"; :>> judgedAt = "2026-07-08"; :>> judgedBy = "ai"; }
        action postCritiqueDefectFixes;
        verification postCritiqueDefectFixesDoD : Test { :>> id = "bcf36eeb-f8bc-4ec8-985d-d38a8ea22750"; :>> method = VerificationMethod::test; :>> procedureText = "The four verified defect fixes from the top-20 functions critique pass (2026-07-17) are implemented and the deliverable suites are green. A1 (client transport.ts): diagnose() reads response bodies via a new tryJson() safe accessor, so a 200 with a non-JSON body (reverse-proxy/captive-portal HTML) no longer throws out of the documented never-throws path; fail-first regression in transport.test ('diagnose never throws even when the body isnt JSON', 2 tests). A2 (server state.rs): the per-key opens lock map is now bounded — release_open_lock drops a key when its last holder finishes (strong_count<=2) and both purge paths clear it, closing the RS-1-class unbounded growth; test state::opens_map_does_not_grow_across_distinct_vault_opens. A3 (server vault.rs): Vault::commit reads file_meta ONCE and reuses it for both the idempotent short-circuit and the CAS check (was two queries; &mut self makes the row stable) — covered by existing commit idempotency/CAS tests. A4 (server api.rs): scoped() maps a genuine vault-open failure AFTER the vault_exists precheck to Internal (500) instead of NotFound (404), so an unexpected IO/DB fault isnt reported as a deleted vault. Server suite 99 lib + integration green (incl. new opens test); client suite 399 green (incl. new diagnose tests). A5 (cumulative delete-guard consistency) handled as a code comment, not a defect. Resolves issueDiagnoseJsonThrows + issueOpensMapUnbounded + issueCommitDoubleMetaQuery + issueScopedOpenError404."; }
        part postCritiqueDefectFixesDoDR1 : TestResult { :>> id = "78bbdffc-ef02-436b-8890-a17c1aacfc69"; :>> outcome = VerdictKind::pass; :>> judgedAgainst = "d27a2b9"; :>> judgedAt = "2026-07-17"; :>> judgedBy = "ai"; }
        action postCritiqueStructuralCleanup;
        verification postCritiqueStructuralCleanupDoD : Test { :>> id = "4a390f19-638a-4c75-a2eb-c1440047c5e3"; :>> method = VerificationMethod::test; :>> procedureText = "The six behavior-preserving structural refactors from the top-20 functions critique pass (2026-07-17), each committed green: B1 — extracted the copy-pasted reconcile-family primitives (isolatedPass error-isolation loop, runDeleteGuard/isSuspiciousBulkDelete bulk-delete guard, advanceCursor, accepts, baseStatUnchanged) into one home each so the safety-critical contracts can't drift (was duplicated 3-4x across reconcileAll/Delta/Path/switchTo/LocalConfig with subtle divergence). B2 — decomposed reconcileOne (~255 lines, 8 positional args incl. 2 bare booleans) into a dispatcher taking a ReconcileOneOpts object, extracting reconcileEnabledPluginList + reconcileMergeOrConflict. B3 — replaced the switch-arm rmeta! non-null assertions with a checked requireRemote() invariant (kept decide() a pure hash truth table rather than degrading it into a meta-carrying union). B4 — reindex classify_missing() helper carrying (key,meta,verified-body) in one Vec, dropping the parallel recovered Vec + recovered_bodies HashMap and their two invariant .expect()s. B5 — split switchTo into switchDownload/switchUpload (two inlined algorithms with opposite R19/R20 error handling). B6 — collapsed the ~15 copy-pasted transport request methods into apiJson/apiVoid + bearer/normBase helpers, fixing three drifts (inconsistent errText, repeated bearer header, per-endpoint trailing-slash handling). All WHY-comments and documented invariants (R10/R13-R20, C1-C4, DI-*, SEC-DATA, RC-2) preserved. Also documented A5 (cumulative delete-guard deliberately absent on the event/one-shot paths) inline. NO behavior change: green at every commit — server 99 lib + integration; client reconcile.test 109, integration-matrix 17, transport 23, full suite 399 passed / 2 skipped; tsc clean. Coverage floors unaffected (pure refactor)."; }
        part postCritiqueStructuralCleanupDoDR1 : TestResult { :>> id = "605fdb54-e076-45e1-ac17-283ffa956adf"; :>> outcome = VerdictKind::pass; :>> judgedAgainst = "4a4609e"; :>> judgedAt = "2026-07-17"; :>> judgedBy = "ai"; }
        action clippyGateInCi;
        verification clippyGateInCiDoD : Test { :>> id = "3e8acf24-fb6b-4f0b-a3ea-8e4f46cafe8d"; :>> method = VerificationMethod::test; :>> procedureText = "CI now enforces the SAME clippy gate as the D0101 reverify contract, closing the drift gap found 2026-07-17 (issueClippyNotInCi). A new server-clippy job in .github/workflows/ci.yml runs 'cargo clippy --all-targets --locked -- -D warnings' on every push/PR — the permanent guard (D0047) so lint drift can't accumulate silently again (CI previously ran only llvm-cov + audits, never clippy, so a newer toolchain turned keel reverify red on warnings nobody caught). Fixed the ~7 pre-existing lints in files unrelated to the critique work: audit.rs (redundant i64 cast; items_after_test_module allow for the ClientIp extractor), auth.rs (items_after_test_module allow for the AuthToken extractor), users.rs (map_or→is_some_and), sharelinks.rs (==false→negation), ws.rs (too_many_arguments allow on the internal serve_socket), state.rs (OpenLocks type alias for the opens field), tests/hardening.rs (repeat().take()→vec![;n]). Verified: cargo clippy --all-targets --locked -- -D warnings exits 0; cargo test --locked 99 lib + integration green. Resolves issueClippyNotInCi."; }
        part clippyGateInCiDoDR1 : TestResult { :>> id = "52a322f6-4fdf-4fc3-8898-2a3f09bdc6a9"; :>> outcome = VerdictKind::pass; :>> judgedAgainst = "ddb4b78"; :>> judgedAt = "2026-07-18"; :>> judgedBy = "ai"; }
        action postR2FunctionAudit;
        verification postR2FunctionAuditDoD : Test { :>> id = "c8a7ab9a-2b6c-4153-ba8d-20b5044ac9ad"; :>> method = VerificationMethod::test; :>> procedureText = "Round-2 function audit (D0028 methodology) of the next 20 critical functions — server durability/security core (index_store put/replace_files/delete/changes/colliding_key, chunkstore sweep_orphans/put, shares authorized/permission, tokens resolve, users verify_password/is_password_reused, vault delete + safe_rel_path/conflicting_or_unsafe_rels, api commit/put_chunk/get_chunk) + client drivers (sync.ts pushBytes/fetchFileBytes/getVerifiedChunk/mapPool, main.ts doReconcileAll/scheduleReconnect, syncengine enqueue/handle/markReconciling, base.ts toJSON/conflict-name). Audited line-by-line by 5 independent critics; every audited function carries an // @audit marker and every FIXED function an // @audit-hash stamp (9 total, verified clean by .engine/tools/audit_hash.py verify). VERIFIED REAL FIXES: B-F1 ContentStore::put now fsyncs the shard DIR after the rename (a rename dir-entry could be lost on power loss → an acked commit's chunk unrecoverable; write_mirror already did this + falsely claimed parity) — issueChunkPutNoDirFsync; CB-F1 reconcilePath refreshes the size gate from the live O(1) stat instead of the coalesce-stale queued hint (a grow-then-shrink/delete was skipped until the full scan) — issueReconcilePathStaleSize, fail-first regression added; CB-F2 doReconcileAll stamps the scan windows AFTER the awaited scan, not before (a mid-scan throw left the window marked done) — issueScanStampBeforeWork. IDIOM/CONCISION cleanups (no separate issue): tokens sha256_hex single-alloc, chunkstore sweep_orphans no per-entry String, vault delete remove_file+NotFound (drop exists() TOCTOU), sync mapPool clamps limit>=1 (no sparse-array footgun), syncengine drop redundant connected=false + typed enqueue predicate + collapse markReconciling's two contradictory doc blocks, scheduleReconnect jitter comment relabeled equal-jitter. CORRECTED a critic overreach by verify-before-believing: UserStore::verify is a TEST-only helper (tests/sync.rs, 3 call sites), NOT dead code — kept; finding downgraded. DEFERRED (marked // @audit, no fix): index_store N+1 chunk fan-out + prepare_cached + DRY deref/insert_file, api small-commit RAM permit + put_chunk route body limit, sync.ts SyncCtx dependency bundle. Green: server 99 lib + integration + clippy --all-targets -D warnings exit 0; client 400 passed / 2 skipped; tsc clean; audit_hash.py verify = 9 unchanged, 0 drifted, 0 stale. Resolves issueChunkPutNoDirFsync + issueReconcilePathStaleSize + issueScanStampBeforeWork."; }
        part postR2FunctionAuditDoDR1 : TestResult { :>> id = "017a6351-1ba7-4efb-b185-966391acdfe5"; :>> outcome = VerdictKind::pass; :>> judgedAgainst = "ee19ccf"; :>> judgedAt = "2026-07-18"; :>> judgedBy = "ai"; }
        action postR2DeferredFindings;
        verification postR2DeferredFindingsDoD : Test { :>> id = "4513c924-5ff6-4e3b-8495-ee49da2c8491"; :>> method = VerificationMethod::test; :>> procedureText = "Implemented the deferred (marked // @audit) findings from the round-2 function audit — behavior-preserving, each fixed function's @audit-hash updated (audit_hash.py verify: 10 server unchanged). index_store.rs: killed the N+1 chunk fan-out in changes() (one JOIN query grouping chunks by path instead of a per-row SELECT — a full manifest is now O(1) queries not O(files)); extracted insert_file() (shared by put + replace_files, fold rule single-sourced with colliding_key) and dereferenced_after() (the durability-critical decref-collect shared by put + delete); prepare_cached throughout; dropped delete()'s redundant EXISTS pre-check (DELETE rows-affected is the presence signal). tokens.rs resolve(): log::warn on a swallowed prune/slide save() failure (observability; still fail-closed). api.rs commit() + state.rs: SMALL commits now take a permit from a new generous small_commit_slots pool (32), bounding aggregate small-commit reassembly RAM (~512 MiB) instead of the implicit ~8 GiB the unthrottled path allowed. DEFERRED into the Part-B per-element design-pattern pass (still // @audit-marked, not lost): the sync.ts SyncCtx parameter-object bundle (a design-pattern improvement that IS Part-B step 8) and the put_chunk route-scoped body limit (low; the in-handler 1 MiB check already bounds storage). Green: server 99 lib + integration + clippy --all-targets -D warnings exit 0; behavior identical (all existing durability/GC/reindex/changes tests pass)."; }
        part postR2DeferredFindingsDoDR1 : TestResult { :>> id = "9d3790f8-f761-4343-84a1-e282cc7dd701"; :>> outcome = VerdictKind::pass; :>> judgedAgainst = "7a7552b"; :>> judgedAt = "2026-07-18"; :>> judgedBy = "ai"; }
        action pbtPureCoresPass;
        verification pbtPureCoresPassDoD : Test { :>> id = "381d3d84-d7de-4df9-9ed0-4eb42ff35707"; :>> method = VerificationMethod::test; :>> procedureText = "First property-based-testing pass (D0030, Anthropic Claude-PBT method) over the pure high-criticality cores. client/test/pbt.test.ts (fast-check, 13 properties) asserts curated invariants mined from the code's own contracts: decide (totality; NEVER a destructive delete unless a side is absent; both-present+diverged+no-base => conflict-copy = no silent clobber; one-sided base==local=>pull / base==remote=>push); merge3 (identical-edit + one-sided merges; CRLF-INVARIANCE of verdict + LF-normalized content — the exact class of the CRLF merge bug); chunker (lossless reassembly round-trip concat(chunk(x))==x + determinism + per-chunk hash-correctness, stressed at 40KB x 300 runs); sameIgnoringEol (reflexive + CRLF + trailing-newline invariance); mergeEnabledPluginsJson (GROW-ONLY UNION result ⊇ local ∪ remote — a sync can never drop a locally-enabled id, the config-disable-vanish class — + sorted/unique + idempotent + null on non-string[]). FINDING (the process's record step): 0 counterexamples across all 13 properties — the invariants HOLD; no new bug surfaced (these classes were already closed by prior hardening), so NO Issue is recorded (honest — a clean pass is the computed evidence, not a prose 'looks correct'); the 13 properties are now permanent generative regressions that would catch any reintroduction. Green: full client suite 413 passed / 2 skipped; tsc clean; fast-check devDependency added. Mutation testing (the D0030 sibling) is the follow-on that quantifies residual suite efficacy."; }
        part pbtPureCoresPassDoDR1 : TestResult { :>> id = "b0083aef-98d0-4241-a7fb-b5b020416bf7"; :>> outcome = VerdictKind::pass; :>> judgedAgainst = "8229eab"; :>> judgedAt = "2026-07-18"; :>> judgedBy = "claudeOpus"; }
        action mutationTestingSharesPass;
        verification mutationTestingSharesPassDoD : Test { :>> id = "b8e1c2d3-4a5b-4c6d-8e7f-901a2b3c4d5e"; :>> method = VerificationMethod::test; :>> procedureText = "First mutation-testing pass (D0030 sibling of the PBT pass), cargo-mutants v27.1 on server/src/shares.rs — the authz KEYSTONE (highest-criticality: every access decision). 53 mutants; the honest signal is the SURVIVORS. Run 1 (--timeout 120, ~1.25x the 96s baseline) reported 42 caught / 1 missed / 6 timeout / 4 unviable — the tight timeout under -j2 contention made 6 mutants inconclusive. Re-run at --timeout 300 resolved all timeouts and exposed 4 REAL survivors (a systemic test-gap class, NOT code defects — the code is correct): (1) purge_user:161 `!=`->`==` (skip save()): the retain-then-`if len != before { save() }` deletion methods (revoke/purge_vault/purge_user) were asserted only against the LIVE in-memory store, so a mutant that SKIPS the durable write survived — a dropped grant would reload after a restart (the dangling-grant reactivation hazard purge_vault's own comment warns of); (2+3) revoke:118 `&&`->`||` (x2) and (4) grants_for:136 `&&`->`||`: the exact (owner,vault,grantee) / (owner,vault) MATCH predicates had no selectivity test (every prior test used a single grant or same owner+vault), so broadening a conjunction to a disjunction was invisible. FIX — 7 fail-first killing tests in shares.rs (all RED under the respective mutant, GREEN on correct code): purge_user/purge_vault/revoke_persists_across_reopen (reopen a fresh ShareStore from disk and assert the deletion PERSISTED); open_propagates_non_notfound_read_errors + open_rejects_a_corrupt_shares_file (open() must Err, never silently start empty, on a non-NotFound read error / corrupt json); revoke_is_selective_to_the_exact_triple + grants_for_matches_only_the_exact_owner_and_vault (decoys sharing exactly one field must be untouched). CONFIRMING re-run (--timeout 300, includes the 7 tests): 49 caught / 0 missed / 0 timeout / 4 unviable = 100% mutation score over the 49 viable mutants (4 unviable are `-> Default` return replacements that don't compile, correctly excluded). Score recorded as the serverMutationScore Indicator (M1, method=pulled, D0089). Green: cargo test --lib shares 20 passed (13 prior + 7 new). SCOPE: shares.rs only; index_store/chunkstore/vault (the durability core) mutation testing is the explicit follow-on (NOT covered here — no silent whole-suite claim). Resolves issueSharesPersistNotTested."; }
        part mutationTestingSharesPassDoDR1 : TestResult { :>> id = "b8e1c2d3-4a5b-4c6d-8e7f-901a2b3c4d60"; :>> outcome = VerdictKind::pass; :>> judgedAgainst = "49deda0"; :>> judgedAt = "2026-07-18"; :>> judgedBy = "claudeOpus"; }
        action mutationTestingIndexChunkstore;
        verification mutationTestingIndexChunkstoreDoD : Test { :>> id = "b8e1c2d3-4a5b-4c6d-8e7f-901a2b3c4d61"; :>> method = VerificationMethod::test; :>> procedureText = "Second mutation-testing pass (D0030), cargo-mutants v27.1 on the durability core: server/src/index_store.rs (the SQLite index authority — put/delete/changes/decref/migrate) + src/chunkstore.rs (the content-addressed blob store). --timeout 300, -j3. 89 mutants -> 73 caught / 7 missed / 9 unviable on run 1. index_store was already SOLID (1 survivor of 42 viable = 97.6%); chunkstore's untested error/validation/recovery paths gave 6 (of 38 viable = 84.2%). The 7 survivors + kills: (index_store) migrate:106 `!=`->`==`, the R12-CC1 schema_version stamp — with one live schema version the branch was never exercised; killed by migrate_stamps_a_stale_schema_version_up_to_current (a below-CURRENT DB must be advanced). (chunkstore) sweep_temp:22/24 (crash-leftover .tmp cleanup untested) -> open_sweeps_leftover_temp_files; is_valid_hash:39 `&&`->`||` (malformed-hash rejection untested — a bad-length/non-hex hash must be a FORMAT error before hashing) -> put_rejects_a_malformed_hash_as_a_format_error; get:90 NotFound-guard->true (a non-NotFound read error must PROPAGATE, never be laundered into 'chunk absent' — same class as shares.open) -> get_propagates_non_notfound_read_errors; touch:108 x2 (the R16 orphan-clock reset untested) -> touch_resets_the_orphan_age_so_an_old_chunk_is_spared (proves the contract via effect: a touched old orphan is spared by a TTL that would otherwise reap it). The 9 unviable are `-> Default`/`Ok(Default)` return replacements that don't compile, correctly excluded. CONFIRMING re-run (--timeout 300, includes the 6 new tests): 80 caught / 0 missed / 9 unviable = 100% over 80 viable. Scores recorded as serverMutationScore M2 (index_store 100%) + M3 (chunkstore 100%). Green: cargo test --lib chunkstore:: 5 passed + index_store:: 12 passed. Resolves issueChunkstoreIndexTestGaps. Remaining durability-core module: vault.rs (the follow-on)."; }
        part mutationTestingIndexChunkstoreDoDR1 : TestResult { :>> id = "b8e1c2d3-4a5b-4c6d-8e7f-901a2b3c4d62"; :>> outcome = VerdictKind::pass; :>> judgedAgainst = "7a8378f"; :>> judgedAt = "2026-07-18"; :>> judgedBy = "claudeOpus"; }
        action mutationTestingVault;
        verification mutationTestingVaultDoD : Test { :>> id = "b8e1c2d3-4a5b-4c6d-8e7f-901a2b3c4d63"; :>> method = VerificationMethod::test; :>> procedureText = "Third mutation-testing pass (D0030), cargo-mutants v27.1 on server/src/vault.rs — the LARGEST + most durability-critical module (commit / reindex / GC / path-safety). --timeout 300, -j3. 138 mutants -> 95 caught / 33 missed / 10 unviable = 74.2% over 128 viable: the LEAST mutation-covered module, exactly where the gaps live. Killed the 8 REQUEST-PATH survivors (the live per-commit/delete surface) with 5 fail-first tests: safe_rel_path:47 empty/absolute path rejection (safe_rel_path_rejects_empty_backslash_and_absolute); commit:524 the strict `> MAX_FILE_BYTES` size gate, both == and >= mutants, via the DISTINCT error, no allocation (commit_size_gate_is_strict_greater_than); commit:541 `||`->`&&` — a right-SIZE/WRONG-HASH body must be rejected, not laundered into a committed file (commit_rejects_correct_size_but_wrong_hash); commit:552 `&&`->`||` — a same-hash but re-CHUNKED commit must not be treated as idempotent (commit_idempotency_requires_both_hash_and_chunks_to_match); commit:576 + delete:615 `+ 1`->`* 1` version bump (commit_and_delete_each_bump_the_version). Confirming re-run: 102 caught / 26 missed = 79.7%. The 26 residual are TRIAGED, not ignored (mutation-testing skill: kill or JUSTIFY, never silent): 21 documented equivalent/impractical accepts + 5 real reindex corrupt-rebuild gaps (issueVaultReindexRebuildTestGaps -> mutationTestingVaultReindex follow-on). ACCEPTS: MAX_FILE_BYTES:13 x5 (the 4 GiB backstop constant — its COMPARISON is now tested by commit:524; the exact value can't be exercised without allocating GBs); verify_and_gc:274/276 x4 (the `reclaimed` counter feeds ONLY a log::info — the reclamation side-effect is separately caught); maybe_sweep_orphans:487/490/494/500 x10 (a 300s-Instant-interval-gated best-effort opportunistic sweep + a log-only n>0 guard; the core reclamation delegates to store.sweep_orphans, already 100% in chunkstore — a clock-injection seam would be test-only complexity on a non-critical path); delete:625 `!=`->`==` (log-only warning on a mirror-removal failure); safe_rel_path:47:47 `||`->`&&` (EQUIVALENT on Windows — the component-split + segs.join()==path backstop already rejects a backslash, so the early guard is redundant there; the new test kills it on a POSIX FS where '\\' is literal). Green: cargo test --lib vault::tests 42 passed (37 prior + 5 new). Resolves issueVaultRequestPathTestGaps."; }
        part mutationTestingVaultDoDR1 : TestResult { :>> id = "b8e1c2d3-4a5b-4c6d-8e7f-901a2b3c4d64"; :>> outcome = VerdictKind::pass; :>> judgedAgainst = "6d9b87d"; :>> judgedAt = "2026-07-18"; :>> judgedBy = "claudeOpus"; }
        // FOLLOW-ON (outstanding, no result yet): the 5 reindex corrupt-rebuild mutation survivors need
        // corruption-simulation test scaffolding (a rebuild-from-disk that reaches the version-preserve /
        // prefer-store / floor-raise branches the existing HEALTHY-reindex tests don't). Tracked, not faked.
        action mutationTestingVaultReindex;
        verification mutationTestingVaultReindexDoD : Test { :>> id = "b8e1c2d3-4a5b-4c6d-8e7f-901a2b3c4d65"; :>> method = VerificationMethod::test; :>> procedureText = "Killed the 5 reindex corrupt/rebuild-path mutation survivors on vault.rs with 3 fail-first tests driving the REBUILD path (the existing rich reindex tests all take the prefer-store short-circuit, so these branches were never exercised): reindex_rebuilds_a_file_whose_chunk_vanished_and_preserves_version (healthy reindex, chunk vanished but mirror intact → rebuild from mirror + re-store the chunk [387 `&&`->`||`] and PRESERVE the unchanged version [412 `_ => bump` not taken / `==`->`!=`]); reindex_bumps_version_for_a_changed_file_it_must_rebuild (a CHANGED file it must rebuild gets a NEW version [412 guard->true]); healthy_reindex_without_tombstones_leaves_history_floor_at_genesis (a healthy tombstone-free reindex must NOT raise the floor [426 `&&`->`||`]). Confirming cargo-mutants re-run (--timeout 300): 107 caught / 21 missed / 10 unviable — 0 reindex survivors; the 21 residual are EXACTLY the documented equivalent/impractical accepts from mutationTestingVault. vault.rs = 107/128 viable (83.6% raw; 100% of non-accepted). Green: cargo test --lib vault::tests 45 passed. Resolves issueVaultReindexRebuildTestGaps."; }
        part mutationTestingVaultReindexDoDR1 : TestResult { :>> id = "b8e1c2d3-4a5b-4c6d-8e7f-901a2b3c4d66"; :>> outcome = VerdictKind::pass; :>> judgedAgainst = "95ce8d7"; :>> judgedAt = "2026-07-18"; :>> judgedBy = "claudeOpus"; }
        action critiqueRPlus1ClientFixes;
        verification critiqueRPlus1ClientFixesDoD : Test { :>> id = "c1a7d0e1-4b5c-4d6e-8f70-1a2b3c4d5e66"; :>> method = VerificationMethod::test; :>> procedureText = "Another adversarial critique pass (4 INDEPENDENT critics: DI/durability, security/authz, concurrency, client-correctness), each finding VERIFIED against the code before acting; the critics also correctly CLEARED the core ACL, path safety, decide()/merge3, chunker, and DoS bounds (no manufactured findings). Two CLIENT data-safety findings fixed + fail-first tested: CLIENT-1 (HIGH, data loss) — reconcileAll's bulk-delete guard counted only delete-LOCAL candidates (wouldDelete = !remote.has && local.has) and gated only that branch, so a mass delete-REMOTE (a vanished local vault: cloud de-hydration / partial backup restore / cleared storage) wiped the whole server vault + tombstoned it fleet-wide; added a symmetric wouldDeleteRemote ratio guard (BULK_DELETE_MIN floor, no empty-local override — a tiny/empty vault isn't second-guessed) gating the delete-remote branch (reconcile.test: a 10-file vanish is guarded, a single delete still propagates). CLIENT-2 (Medium, silent merge loss) — pushBytes wrote merged bytes then pushFile RE-READ from disk, so a local save racing the write->read gap was committed in place of the merge (discarding the remote edit the merge folded in; DI-5 fixed base consistency, not this loss); refactored to a shared commitBytes core that commits the in-hand bytes (sync.test: pushBytes commits the exact bytes given, not the raced re-read). Green: full client suite 416 passed / 2 skipped; tsc clean. Resolves issueMassDeleteRemoteUnguarded + issueMergePushReReadLoss."; }
        part critiqueRPlus1ClientFixesDoDR1 : TestResult { :>> id = "c1a7d0e1-4b5c-4d6e-8f70-1a2b3c4d5e67"; :>> outcome = VerdictKind::pass; :>> judgedAgainst = "504238f"; :>> judgedAt = "2026-07-18"; :>> judgedBy = "claudeOpus"; }
        // FOLLOW-ON (outstanding, no result): the verified SERVER-side critique findings, to fix as a batch.
        action critiqueRPlus1ServerHardening;
        verification critiqueRPlus1ServerHardeningDoD : Test { :>> id = "c1a7d0e1-4b5c-4d6e-8f70-1a2b3c4d5e68"; :>> method = VerificationMethod::test; :>> procedureText = "Fixed the six verified server-side findings from the critique R+1 pass, each with a fail-first regression; server cargo test --locked green (203 tests) + clippy --all-targets -D warnings clean. (1) issueFoldBackfillAsciiOnly — index_store.migrate now backfills fold per-row in Rust to_lowercase() (was SQLite ASCII-only lower(), which left legacy non-ASCII rows escaping colliding_key); test migrate_backfills_non_ascii_fold_so_the_collision_guard_still_fires. (2) issueShareLinkRemanence — added ShareLinkStore::purge_vault/purge_user + an open-time expiry sweep, wired into state.purge_vault + admin.users_delete, so a no-expiry link can't survive a delete+recreate (mirror of the R17 grant purge); tests purge_vault_and_user_drop_links + open_sweeps_expired_unredeemed_links. (3) issueVaultDeleteOpenRace — a deleted_vaults tombstone set: purge_vault holds the per-key open lock + tombstones the key, vault() refuses a tombstoned key (NotFound) instead of create_dir_all resurrecting it, create_vault clears it; test purged_vault_is_not_auto_recreated_by_a_raced_open. (4) issuePurgeDirNotBestEffort — purge_vault/purge_user_data dir removal is now log-not-propagate (no grants-purged half-state 500 on a Windows lock), and users_delete purges shares+links+admin BEFORE removing the row (SEC-3 ordering). (5) issueMfaDisableNoThrottle — /api/mfa/disable now routes the code check through login_throttle (per-account); test disable_is_brute_force_throttled (10 wrong → 401, then 429). (6) issueVersionEpochRewind — a monotonic fsync'd .version-hwm sidecar survives an index quarantine; Vault::open seeds version = max(index, hwm), commit/delete/reindex persist it, so the counter never rewinds below a synced client's cursor; test version_does_not_rewind_below_the_high_water_after_a_quarantine_rebuild. Resolves all six issues."; }
        part critiqueRPlus1ServerHardeningDoDR1 : TestResult { :>> id = "c1a7d0e1-4b5c-4d6e-8f70-1a2b3c4d5e69"; :>> outcome = VerdictKind::pass; :>> judgedAgainst = "e028df8"; :>> judgedAt = "2026-07-18"; :>> judgedBy = "claudeOpus"; }
        // ===== Design-pattern conformance critique (2026-07-19): 3 OPEN follow-on actions. Findings from
        // 5 independent conformance critics over the 27 pattern-tagged CodeElements (verified against code). =====
        action patternConformanceHardening;
        verification patternConformanceHardeningDoD : Test { :>> id = "9a77e001-1b2c-4d3e-8f40-5a6b7c8d9e01"; :>> method = VerificationMethod::test; :>> procedureText = "DONE (reverify green @ f96b217, deliverableTestGate: server cargo test --locked + clippy -D warnings + client vitest 453): implemented all four resolved issues, each behaviour-preserving + tested — (1) validateFileMeta now validates mtime via asNum + constructs (no cast); (2) SafeName newtype (users.rs) + SafeVaultPath brand (pathsafe.ts, the raw-fs join gated via rawFsAbs) + ServerOrigin refined type (connstr.ts, cleartext verdict parsed once); (3) reconcileOne→pure finalize()→ReconcileEffect + reconcileMergeOrConflict→pure planMerge()→MergePlan + acceptedBasePaths() guard-denominator dedup + item-4 (confirmedAbsent→ProbedPresence tagged type, mapPool shared abort flag, ContentStore put-vs-remove contract doc); (4) ChunkHash newtype + conflictCopyIfRaced RaceOutcome union + parseSettings() parser + OpenLockReaper RAII guard + AuditAction/Outcome catalog newtypes. Commits 59a7613..f96b217. ORIGINAL PLAN follows. (1) DEFECT issueValidateFileMetaMtimeUnchecked — validateFileMeta (protocol.ts:52) validates path/hash/size/version/chunks but NOT mtime, yet returns `o as FileMeta` asserting mtime:number; a hostile server's mtime:'evil'/NaN passes + flows into base stat-stamping. Fix: add asNum(m.mtime) + construct-don't-cast (like validateStatus). (2) issueBoolPredicatesNoRefinedType — turn bool safety-predicates into refined/branded types so the checked property is type-carried, not re-asserted at every call site: safe_name (users.rs, re-checked ~20 sites incl. a double-check on register — a SafeName newtype whose only ctor parses; highest ROI since the name becomes an FS segment), isSafeVaultPath (5 client I/O sites → branded SafeVaultPath), isInsecureRemote (4 sites → fold the verdict into normalizeServer's refined ServerOrigin). (3) issueFunctionalCoreShellsReDecide — widen the pure core: reconcileOne → a pure finalize(action, facts)→Effect (lift config re-adjudication + guard gating out of the shell; resolve confirmedAbsent/exists to booleans first), reconcileMergeOrConflict → a pure MergePlan value (shell only executes writes), reconcilePath → a shared perPassDeleteGuard helper (dedup the runDeleteGuard drift, B1). (4) low: ContentStore::put — document/guard the put-vs-remove concurrency contract (safety currently BORROWED from the Vault RwLock + orphan-TTL across 3 files, not enforced in the store); confirmedAbsent → return LocalContent/Presence not bool; mapPool — a shared abort flag if a non-idempotent caller ever appears (today safe by idempotency). Resolves issueValidateFileMetaMtimeUnchecked + issueBoolPredicatesNoRefinedType + issueFunctionalCoreShellsReDecide + issuePatternUntaggedShouldAdopt."; }
        part patternConformanceHardeningDoDR1 : TestResult { :>> id = "9a77e001-1b2c-4d3e-8f40-5a6b7c8d9e05"; :>> outcome = VerdictKind::pass; :>> judgedAgainst = "f96b217"; :>> judgedAt = "2026-07-19"; :>> judgedBy = "claudeOpus"; }
        action stateMachineConsolidation;
        verification stateMachineConsolidationDoD : Test { :>> id = "9a77e002-1b2c-4d3e-8f40-5a6b7c8d9e02"; :>> method = VerificationMethod::test; :>> procedureText = "DONE (reverify green @ f96b217): consolidated the sync-lifecycle state machines — (a) chose DELETE for the dead syncstate::transition/SyncMachine duplicate (kept Phase/light/isWsStale; test trimmed); (b) made the implicit FSMs explicit as pure enumerated tables: D1 WS/transport → transportTransition (transportstate.ts; offline/dialing/live/degraded, exhaustive test net), D2 scan-mode → decideReconcileMode(), D3 config-path → adjudicateConfigConflict(), D4 the engine hybrid → folded connected/retrying into EngineState-derived accessors (running kept as the pump concurrency guard, documented); plus issueVaultLifecycleImplicitFsm → server VaultState::next(event) transition (vault.rs). Each with tests; full client + server suites + clippy green. Commits 59a7613..f96b217. ORIGINAL PLAN follows. (a) The 2 TAGGED FSMs (syncstate::transition + SyncMachine, syncstate.ts) are CORRECT total (State,Event)→State machines but DEAD — only client/test/syncstate.test.ts imports them; the operational machine migrated to syncengine.ts. Decide: DELETE them (+ trim the test to the still-live Phase/light/isWsStale) OR REUNIFY — refactor SyncEngine.handle's imperative transitions onto a total transition(EngineState,EngineEvent)→{state,effects} table, retiring the duplication + making engine transitions exhaustively testable. (b) Make the IMPLICIT FSMs explicit, highest-value first: D1 WS/transport lifecycle (main.ts spinUpWs/startWsLiveness/close-handler — realtimeConnected/opened/`ws!==ws`/poll-cadence/wsLivenessTimer implicitly encode no-socket/dialing/open/half-open-stale/closed-redial/closed-reconnect; a documented history of race patches → an explicit TransportState machine); D4 the engine HYBRID (EngineState enum + 3 aux booleans connected/retrying/running + imperative transitions → fold the aux booleans into the state enum + the total transition table from (a)); D2 doReconcileAll scan-mode (4 booleans → a pure decideReconcileMode()→noop|delta|delta+config|full); D3 config-path adjudication (array-membership-as-state → an explicit per-path status). Model = decide()'s pure enumerated table. Each with tests. Resolves issueStateMachineOrphanedAndImplicit + issueVaultLifecycleImplicitFsm."; }
        part stateMachineConsolidationDoDR1 : TestResult { :>> id = "9a77e002-1b2c-4d3e-8f40-5a6b7c8d9e06"; :>> outcome = VerdictKind::pass; :>> judgedAgainst = "f96b217"; :>> judgedAt = "2026-07-19"; :>> judgedBy = "claudeOpus"; }
        action patternRegistryReview;
        verification patternRegistryReviewDoD : Test { :>> id = "9a77e003-1b2c-4d3e-8f40-5a6b7c8d9e03"; :>> method = VerificationMethod::test; :>> procedureText = "Made the design-pattern tags across the CodeElement registry honest. (a) RETAGGED the 5 mislabels the critique found (D0032 adds the 2 enum members needed): ceContentStorePut singleWriter→contentAddressedImmutable; ceResolveConfigConflict command→strategy; ceSharesAuthorized + ceMergeEnabledPlugins makeIllegalStatesUnrepresentable→functionalCoreImperativeShell; ceIsolatedPass boundedPool→errorIsolationLoop. (The orphaned ceSsSyncMachine/ceSsTransition `state` tags are handled by stateMachineConsolidation, not here.) (b) REVIEWED all 142 untagged elements (7 independent reviewers, by shape) and APPLIED 56 already-conforms tags — tagged coverage 27→83 (singleWriter stores, parseDontValidate boundary parsers, functionalCore pure cores, the transport adapter, RAII guards, the serialized actor, UI templateMethod modals); should-adopt refactors spun out to issueVaultLifecycleImplicitFsm + issuePatternUntaggedShouldAdopt. (c) FIXED the .engine/docs/design-patterns.md parseDontValidate exemplar row (validateChanges/validateFileMeta historically cast; the true exemplars are safe_rel_path + validateStatus). keel validate clean; keel guard ALL PASS. Resolves issuePatternTagsMislabeled + issueUntaggedElementsPatternReview."; }
        part patternRegistryReviewDoDR1 : TestResult { :>> id = "9a77e003-1b2c-4d3e-8f40-5a6b7c8d9e04"; :>> outcome = VerdictKind::pass; :>> judgedAgainst = "21e2871"; :>> judgedAt = "2026-07-19"; :>> judgedBy = "claudeOpus"; }
        // ===== Release-discipline correction (D0047, 2026-07-19): the release-CURRENCY blind spot. OPEN —
        // the guard implementation is a process-definition CHANGE (edits release-versioning per D0070), so it
        // awaits its Change-Request Decision + human acceptance before it lands. Declared here so the Issue
        // is triaged (D0077) and computes OPEN until the guard ships. =====
        action releaseCurrencyGuard;
        verification releaseCurrencyGuardDoD : Test { :>> id = "9a77e004-1b2c-4d3e-8f40-5a6b7c8d9e07"; :>> method = VerificationMethod::test; :>> procedureText = "DONE (D0033 accepted + shipped @ 0b69885): added scripts/check-release-currency.mjs (counts unreleased shippable-path commits since the last release tag; WARN>=1, FAIL >10 commits or >14 days), wired into verify-released.yml (daily net), + process step rv6Currency + release-versioning skill doc-sync. Verified: reports 0 now (post-1.6.1) and 47 over the pre-release range (would have hard-failed as overdue). keel guard ALL PASS. ORIGINAL PLAN follows. Add a release-CURRENCY assertion. Today check-release.mjs + verify-released.yml only assert the MANIFEST's version is tagged + published — satisfied whenever the manifest points at a released version, EVEN IF main has drifted far past it. That is exactly why 48 shippable commits (of 100 total; 52 were .engine/.tracking/docs-only) piled up unreleased since 1.6.0 while both checks stayed green. Fix (mirrors D0012's repo-local, out-of-keel-scope pattern): a scripts/check-release-currency.mjs that counts main commits since the last release tag touching SHIPPABLE paths (client/**, server/**, manifest.json, versions.json — NOT engine/tracking/docs, else every stamp/CR false-positives), WARNs at >=1 unreleased shippable commit and FAILs past a threshold (~10 commits or ~14 days), wired into the daily .github/workflows/verify-released.yml net so the drift goes visible on its own. Resolves issueReleaseCurrencyBlindSpot."; }
        part releaseCurrencyGuardDoDR1 : TestResult { :>> id = "9a77e004-1b2c-4d3e-8f40-5a6b7c8d9e08"; :>> outcome = VerdictKind::pass; :>> judgedAgainst = "0b69885"; :>> judgedAt = "2026-07-19"; :>> judgedBy = "claudeOpus"; }
        // ===== Sprint statusLightFlickerFsm (2pt, 2026-07-28) — fix the status-light flitter. refine->
        // standup->implement->review->closeOut->retro->deploy(1.6.2). Owner-reported field UX defect. =====
        action statusLightFlickerFsm;
        verification statusLightFlickerFsmDoD : Test { :>> id = "9a77e005-1b2c-4d3e-8f40-5a6b7c8d9e09"; :>> method = VerificationMethod::test; :>> procedureText = "DONE (reverify green @ 18f9cc2 — full client vitest 462 + server cargo test --locked + clippy -D warnings; ships PATCH 1.6.2): eliminated the 'Fully synced' <-> 'Syncing... checking for changes' ~1x/sec flitter (issueStatusLightFlicker). Extract a PURE debounced display FSM (statuslight.ts: nextLightDisplay over {shown, armed} with LightEvent phase|settle) — DISTINCT from the engine FSM — so entering the visible 'syncing' display is DEBOUNCED and gated on syncPending>0: a 0-pending or sub-second reconcile never paints and the light holds its steady state. Remove 'checking for changes' from statusDisplay; add a render-dedupe (skip the DOM repaint when the computed light is unchanged); wire the reducer into main.ts onPhase/onProgress via a debounce timer that emits 'settle'. Behaviour otherwise unchanged. DoD: statuslight.test exhaustive transition table green + full client vitest green + tsc clean + reverify green; the flicker scenario (idle->syncing(0)->idle repeated sub-second) holds 'Fully synced'. Ships PATCH 1.6.2. Resolves issueStatusLightFlicker."; }
        part statusLightFlickerFsmDoDR1 : TestResult { :>> id = "9a77e005-1b2c-4d3e-8f40-5a6b7c8d9e0a"; :>> outcome = VerdictKind::pass; :>> judgedAgainst = "18f9cc2"; :>> judgedAt = "2026-07-28"; :>> judgedBy = "claudeOpus"; }
        // RETRO (autonomous, method=analysis): the flitter shipped because the status PROJECTION had no test
        // pinning "a no-op check must not read as a syncing state" + no display FSM. The durable control now
        // exists = statuslight.ts (pure debounced FSM) + statuslight.test (exhaustive) + the updated wiring
        // assertion — the fix IS its own guard, so no new backlog item. The one process slip (the fix was
        // started ad-hoc before being routed through a sprint) is already covered by the tracked no-sprint
        // guard (issue020 / sprint30). Velocity: 2pt delivered.
        // REVIEW — the per-sitting human gate (D0049), the single human confirmation. wweatherholtz accepted
        // this sitting explicitly; #Covers names the sprint it attests (keel sitting-coverage reads it).
        verification sittingReview20260728 : Test { :>> id = "9a77e005-1b2c-4d3e-8f40-5a6b7c8d9e0b"; :>> method = VerificationMethod::confirmation; :>> procedureText = "Per-sitting human review (D0049) for the 2026-07-28 sitting: wweatherholtz accepted the statusLightFlickerFsm sprint (the debounced status-light display FSM that eliminated the 'Fully synced' <-> 'Syncing... checking for changes' flitter) and its deployment as release 1.6.2, via explicit 'yes' on 2026-07-28. This is the single human confirmation gate; the sprint's closeOut (inspect) + retro (analysis) ran autonomously."; }
        part sittingReview20260728R1 : TestResult { :>> id = "9a77e005-1b2c-4d3e-8f40-5a6b7c8d9e0c"; :>> outcome = VerdictKind::pass; :>> judgedAgainst = "187c623"; :>> judgedAt = "2026-07-28"; :>> judgedBy = "wweatherholtz"; }
        // ===== Sprint embeddedTimestampMetadata (2026-07-29) — SelfSync-owned embedded created/updated
        // timestamps (ISO-8601+offset), normalized-content identity so timestamp-only diffs never conflict,
        // and embedded-time-driven filesystem mtime (+ creation time on Win/mac). REFINE phase: needs/
        // use-cases/SRs/acceptance authored; TDD + DOM + e2e architected (spec: docs/design/specs/
        // 2026-07-29-embedded-timestamp-metadata.md). Not yet implemented — ships MINOR. =====
        action embeddedTimestampMetadata;
        verification embeddedTimestampMetadataDoD : Test { :>> id = "d7c19001-0000-4a10-9b20-a1b2c3d40091"; :>> method = VerificationMethod::test; :>> procedureText = "DoD (NOT yet met — refine authored 2026-07-29): pure frontmatter.ts (parse/serialize, normalized hash masking the managed keys, raw fallback for non-md/unparseable YAML) + excludedFolders.ts (add/remove/normalize/isExcluded/matchFolders) unit tests green; reconcile.test.ts timestamp-only->no-conflict + copy-bump->reverted-not-pushed + excluded-folder->untouched + genuine-conflict->no-regression green; fstimes.ts driver tests (mtime from updated desktop; creation time from created Win/mac; Linux/mobile degrade; ctime never; native-addon-absent graceful) green; settings-ui.dom.test.ts add/remove/autocomplete wiring green; a *.pwspec.ts e2e (seed real folders, add an excluded folder in settings, assert excluded content never reaches the server) green; full client vitest + server cargo test --locked + clippy -D warnings + keel reverify all green. Ships a MINOR release. Resolves issueTimestampConflictNoise."; }
        part embeddedTimestampMetadataDoDR1 : TestResult { :>> id = "d7c1a001-0000-4a10-9b20-a1b2c3d4a001"; :>> outcome = VerdictKind::pass; :>> judgedAgainst = "ab40154"; :>> judgedAt = "2026-07-29"; :>> judgedBy = "claudeOpus"; }
        // CLOSEOUT (autonomous, method=inspect): DoD met — full deliverable gate green @ 6c33630 (server cargo
        // test + clippy -D warnings + client vitest 504) + tsc clean + plugin bundles; shipped as 1.7.0.
        // RETRO (autonomous, method=analysis): a pre-release 3-lens adversarial critique caught FIVE ship-
        // blockers the TDD suite missed (non-md corruption, cross-device churn, created=now, CRLF, quoted
        // dates) because its fixtures were all LF / unquoted / .md / strictly-ordered timestamps. Durable
        // lesson: adversarial-critique-before-release + adversarial fixtures (the fixes shipped WITH fail-
        // first tests, so the fix is its own guard). 4 lower findings tracked -> issueTimestampHardeningFollowups.
        // ===== Follow-up (v-next) — deferred hardening from the pre-release 3-lens critique. Not started. =====
        // REVIEW — the per-sitting human gate (D0049), the single human confirmation. wweatherholtz reviewed
        // the pre-release 3-lens critique results + fixes and authorized the release; #Covers names the sprint.
        verification sittingReview20260729 : Test { :>> id = "d7c1a002-0000-4a10-9b20-a1b2c3d4a002"; :>> method = VerificationMethod::confirmation; :>> procedureText = "Per-sitting human review (D0049) for the 2026-07-29 sitting: wweatherholtz accepted the embeddedTimestampMetadata sprint (SelfSync-owned embedded created/updated timestamps, volatile-field-aware sync, and embedded-time-driven FS times), having reviewed the 3-lens pre-release adversarial critique and its ship-blocker fixes, and authorized deployment as release 1.7.0 — via explicit 'good, publish' on 2026-07-29. This is the single human confirmation gate; the sprint's closeOut (inspect) + retro (analysis) ran autonomously."; }
        part sittingReview20260729R1 : TestResult { :>> id = "d7c1a003-0000-4a10-9b20-a1b2c3d4a003"; :>> outcome = VerdictKind::pass; :>> judgedAgainst = "ab40154"; :>> judgedAt = "2026-07-29"; :>> judgedBy = "wweatherholtz"; }
        // ===== Sprint frontmatterParserSafety (2026-07-29) — 1.7.1: fix the shipped block-scalar frontmatter
        // corruption + BOM/EOL/key-order rewrite surfaced by the embeddedTimestampMetadata critique. =====
        action frontmatterParserSafety;
        verification frontmatterParserSafetyDoD : Test { :>> id = "d7c19003-0000-4a10-9b20-a1b2c3d40093"; :>> method = VerificationMethod::test; :>> procedureText = "Ships PATCH 1.7.1. The frontmatter parser is block-scalar-safe (col-0-only fence: an indented --- inside a YAML block scalar never false-closes), and setManagedValue is surgical + preservation-safe — it preserves a leading BOM, CRLF/LF line endings, existing key order, and all non-managed frontmatter + body byte-for-byte; drops duplicate managed keys; appends a missing key before the closing fence. Guard (D0047): frontmatter.test block-scalar / BOM / CRLF / key-order / round-trip-stable cases + the existing suite. DoD: full client vitest (509) + tsc clean + keel reverify green. Resolves issueFrontmatterBlockScalarCorruption."; }
        part frontmatterParserSafetyDoDR1 : TestResult { :>> id = "d7c1a004-0000-4a10-9b20-a1b2c3d4a004"; :>> outcome = VerdictKind::pass; :>> judgedAgainst = "92ae8c6"; :>> judgedAt = "2026-07-29"; :>> judgedBy = "claudeOpus"; }
        // RAN: keel reverify --all-drift (re-ran the declared gate at HEAD)
        part frontmatterParserSafetyDoDR2 : TestResult { :>> id = "38879fe9-9f68-4e69-8562-d07d85fc5789"; :>> outcome = VerdictKind::pass; :>> judgedAgainst = "fdbbc3ce"; :>> judgedAt = "2026-09-07"; :>> judgedBy = "claudeOpus"; }
        // CLOSEOUT (autonomous, inspect): shipped 1.7.1; deliverable gate green @ 3b4a55e. RETRO (analysis):
        // the corruption came from a line-based parser blind to YAML block scalars — the durable guard is the
        // shipped parser test-table (block-scalar / BOM / CRLF / key-order / round-trip). Same-sitting human
        // review: wweatherholtz directed + authorized this 1.7.1 fix and its release via explicit "yes
        // implement" (2026-07-29); covered by sittingReview20260729 (this sitting's single confirmation gate).
        // ===== Sprint timestampBackfill (2026-07-29) — 1.8.0: instantiate embedded timestamps ON ENABLE
        // (convergence backfill) + the critique-hardening (instant-based compliance, alias mask, reversible
        // first pass, restore detection, honest counted confirm, Templates exclude). =====
        action timestampBackfill;
        verification timestampBackfillDoD : Test { :>> id = "d7c19004-0000-4a10-9b20-a1b2c3d40094"; :>> method = VerificationMethod::test; :>> procedureText = "Ships MINOR 1.8.0. Enabling (or a policy change, or a settled launch) runs a convergence pass that brings every in-scope .md note to compliance: INSTANT-BASED compliance (canonical unquoted ISO-with-offset, offset-agnostic -> global fixed point), a real normalizer (seed missing from OS ctime/mtime, never 'now'; re-emit non-canonical at the same instant; never bump) with the FIXED-POINT law as a shipped test; pushed via backfillPush so a masked-key-only conform is neither reverted nor re-stamped by reconcile (proven test). Paced + RESUMABLE via a per-(device,vault) policy-versioned marker+cursor; drift handled at the write boundary; REVERSIBLE first pass (conflict-copy of any not-cleanly-conformable note); informed COUNTED enable confirm with restore-signature detection; third-party alias keys MASKED in identity (Linter-loop fix); Templates folder excluded. DoD: frontmatter + timestampBackfill + reconcile(backfillPush) unit tests + settings-ui DOM (enable->consent->backfill) green; full client vitest + tsc + server cargo test + clippy -D warnings + keel reverify green. Resolves issueTimestampEnableInert."; }
        part timestampBackfillDoDR1 : TestResult { :>> id = "d7c1a005-0000-4a10-9b20-a1b2c3d4a005"; :>> outcome = VerdictKind::pass; :>> judgedAgainst = "fa3a563"; :>> judgedAt = "2026-07-29"; :>> judgedBy = "claudeOpus"; }
        // CLOSEOUT (autonomous, inspect): shipped 1.8.0; deliverable gate green @ 9d2fd65. RETRO (analysis):
        // the whole 1.8.0 design was reshaped by a 3-lens spec critique BEFORE any code (rejected an unsound
        // generic engine whose interface couldn't express config's decision; fixed a cross-TZ termination
        // flaw via instant-based compliance) — critique-before-implement paid off a THIRD time this sitting.
        // The correctness core (compliance / normalizer / planner / backfillPush) is unit + integration
        // proven; the impure orchestration ships with DOM coverage + an ACCEPTED e2e gap (owner chose to ship
        // eyes-open). That gap DISSOLVED with timestampIgnoreRedesign (1.9.0), which deleted the backfill
        // itself — there is no backfill left to e2e (project D0048).
        // Same-sitting human authorization: wweatherholtz directed + accepted the 1.8.0 build + ship via
        // explicit "2 please" + "continue until done" (2026-07-29); covered by sittingReview20260729.
        // ===== Sprint statusHangsOnSyncing (2026-07-29) — 1.8.1: fix the "hangs on Syncing..." regression
        // from the 1.6.2 flicker fix (statusText rendered the raw engine phase, bypassing the light's collapse). =====
        action statusHangsOnSyncing;
        verification statusHangsOnSyncingDoD : Test { :>> id = "d7c19005-0000-4a10-9b20-a1b2c3d40095"; :>> method = VerificationMethod::test; :>> procedureText = "Ships PATCH 1.8.1. The 0-pending-reconcile -> idle collapse is now a pure syncstate.effectivePhase(phase, syncPending), and BOTH effectiveLightPhase AND statusText route through it, so the settings status card and the ribbon light agree — a resting 0-pending reconcile shows 'Fully synced', never a stuck 'Syncing...'. Also cleans a raw NUL byte shipped in the 1.8.0 backfill sentinel (source now uses an escaped sentinel; main.ts is no longer treated as binary). Guard: syncstate.test effectivePhase table. DoD: full client vitest + tsc + server cargo test --locked + clippy -D warnings + keel reverify green. Resolves issueStatusHangsOnSyncing."; }
        part statusHangsOnSyncingDoDR1 : TestResult { :>> id = "d7c1a006-0000-4a10-9b20-a1b2c3d4a006"; :>> outcome = VerdictKind::pass; :>> judgedAgainst = "86b200e"; :>> judgedAt = "2026-07-29"; :>> judgedBy = "claudeOpus"; }
        // CLOSEOUT (autonomous, inspect): shipped 1.8.1; deliverable gate green @ f8a3436. RETRO (analysis):
        // the 1.6.2 flicker fix collapsed 0-pending syncing on the LIGHT but left statusText rendering the raw
        // phase — two display surfaces, two projections. Durable guard: ONE pure effectivePhase() both route
        // through, + the syncstate.test table. Also swept a raw-NUL sentinel shipped in 1.8.0 (source hygiene).
        // Same-sitting human authorization: wweatherholtz directed the fix via explicit "proceed with hangs on
        // syncing" (2026-07-29); covered by sittingReview20260729.
        // ===== Sprint timestampIgnoreRedesign (2026-07-30) — 1.9.0: RETIRE the "SelfSync owns created/updated"
        // approach (1.7-1.8) after it fabricated dates + flooded conflict copies on a real copied multi-device
        // vault. SelfSync now NEVER writes note timestamps; it only makes CONTENT IDENTITY ignore volatile
        // timestamp-only frontmatter diffs (value-shape gated) + always-on EOL/BOM normalization. Spec + 3
        // independent critiques: docs/superpowers/specs/2026-07-30-timestamp-ignore-redesign-design.md. =====
        action timestampIgnoreRedesign;
        verification timestampIgnoreRedesignDoD : Test { :>> id = "d7c19006-0000-4a10-9b20-a1b2c3d40096"; :>> method = VerificationMethod::test; :>> procedureText = "Ships MINOR 1.9.0. SelfSync writes NO note timestamps (seed/conform/backfill/stamp/drive-fs/restore-detection deleted; timestampBackfill.ts + fstimes.ts removed). Content identity ALWAYS normalizes EOL/BOM/trailing-newline for all text files (the CRLF-false-positive fix — normalizedHash no longer short-circuits to the raw hash for a no-frontmatter note); when the feature is on it additionally masks timestamp-VALUED frontmatter keys, VALUE-SHAPE gated (a non-date value under an ignored key still syncs) and PATTERN matched (updated-* per-device keys). Applied as a post-decide client-side override (server/manifest hash stays raw; base keeps {raw hash, normHash}) so pending-counts / delete-detection / CAS are unaffected. Hardened by 3 independent antagonistic critiques: merge3 neutralizes+restores timestamp lines (a real body merge isn't spoiled -> no spurious conflict copy); delete-local uses normHash equality (a peer deletion is honored, not resurrected); convergence keeps local bytes (no rewrite loop with an auto-timestamp plugin). Settings pivot embeddedTimestamps->ignoreTimestampChanges (default ON, identity-only, no counted-consent) with automatic migration. Guard (D0047): the redesign's own vitest cases (CRLF-only-not-pushed, timestamp-only-no-copy, Finding-B merge, Finding-C delete-local) + value-shape/pattern frontmatter tests. DoD: full client vitest (501) + tsc --noEmit clean + keel validate + guard green. Server untouched. Resolves issueTimestampFabricatedCreated + issueTimestampBackfillConflictFlood + issueCrlfFalsePositiveChanges (superseding the embeddedTimestampMetadata approach to issueTimestampConflictNoise)."; }
        part timestampIgnoreRedesignDoDR1 : TestResult { :>> id = "d7c1a007-0000-4a10-9b20-a1b2c3d4a007"; :>> outcome = VerdictKind::pass; :>> judgedAgainst = "03fa9d2"; :>> judgedAt = "2026-07-30"; :>> judgedBy = "claudeOpus"; }
        // CLOSEOUT (autonomous, inspect): shipped 1.9.0; client vitest 501 + tsc clean + keel green @ 03fa9d2.
        // RETRO (analysis): the 1.7-1.8 "own the field" design WAS the root cause — owning created/updated
        // fabricated dates (copied-vault ctime), flooded conflict copies (empty-fm needsCopy), and never
        // touched the CRLF false-positive (a SEPARATE root cause the design-fit critic confirmed). The 3
        // critiques caught THREE would-be data-integrity regressions in the redesign itself (deletion
        // resurrection, conflict-copy re-flood, vault-wide churn) before ship — critique-before-implement paid
        // off a FOURTH time. Durable lesson: don't OWN a volatile field a user / other plugin manages; IGNORE it.
        verification sittingReview20260730 : Test { :>> id = "d7c1a008-0000-4a10-9b20-a1b2c3d4a008"; :>> method = VerificationMethod::confirmation; :>> procedureText = "Per-sitting human review (D0049) for the 2026-07-30 sitting: wweatherholtz directed the timestamp-ignore redesign ('spec, indepdent antagonistic critique, refactor, then implement' -> 'proceed with the fix please') after reporting the 1.8.0 field damage (fabricated created, mass timestamp-only conflict copies) on the real vault; chose the shipped defaults via the presented options ('Both on for everyone' + 'Delete-only, to .trash, after code ships'); and directed 'proceed with all' — accepting the redesign, its 1.9.0 release, and the reversible cleanup of the 32 timestamp-only conflict copies. Same sitting: after reporting the connection auth-retry storm (a rejected sign-in looping into a self-lockout), wweatherholtz directed the connection-FSM redesign ('this is a perfect example for using an FSM... critique, and establish a basis for a proper spec, then implement' -> 'keep going please'), steered its shape ('multi FSMs per state, scoped to functions' + 'reference an enum instead of hardcoded strings'), thereby accepting connectionFsmTypedFailure + its 1.9.1 release. This is the single human confirmation gate; closeOut (inspect) + retro (analysis) ran autonomously."; }
        part sittingReview20260730R1 : TestResult { :>> id = "d7c1a009-0000-4a10-9b20-a1b2c3d4a009"; :>> outcome = VerdictKind::pass; :>> judgedAgainst = "03fa9d2"; :>> judgedAt = "2026-07-30"; :>> judgedBy = "wweatherholtz"; }
        // ===== Backlog (field-reported 2026-07-30, investigated; NOT started) — four follow-up defects the
        // owner surfaced. Each is a resolver stub for a future sprint; the DoD describes the fix, no R1 yet. =====
        action pluginSyncRemovalPropagation;
        verification pluginSyncRemovalPropagationDoD : Test { :>> id = "d7c19007-0000-4a10-9b20-a1b2c3d40097"; :>> method = VerificationMethod::test; :>> procedureText = "DONE. (a) 1.9.2 — the settings UI SPLITS 'Available from the sync (not adopted)' out of 'Synced community plugins', so the main list is only what THIS device installs/adopts (the parity confusion). (b) 1.10.0 — the explicit PURGE: a per-plugin 'Remove from server' action (behind a destructive confirm) delete-remotes the plugin's .obsidian/plugins/<id>/** files + drops the id from this device's allowlist + the server-plugins view. It is a DELIBERATE, per-plugin, behind-a-confirm gesture — the grow-only mergeEnabledPluginsJson is UNTOUCHED, so it can NEVER cascade into 'all my plugins vanished'; NOT a CHANGE to the merge. PROVENANCE CORRECTION (2026-07-31): this feature was AI-PROPOSED (as the recommended option, over a fleet-wide tombstone / leave-it) and a menu-selection was registered via a question — but the owner subsequently stated they did NOT explicitly choose a 'remove from server' feature. So this feature was AI-INITIATED (not owner-requested), off a leading option. RESOLUTION (2026-07-31): after the provenance correction + an explicit keep-vs-revert offer, the owner chose to KEEP it ('#2 keep in') — so it is now owner-ACCEPTED as a kept feature (a clean, informed decision), even though AI-initiated; the earlier 'the owner explicitly chose to build this' framing was the overstatement, retracted + replaced by this accurate record. Documented caveat: another device still actively syncing the plugin can re-push it. Guard: plugin-wiring 'removePluginFromServer purges ONLY that plugin's files + drops it from the allowlist/view'. DoD: full client vitest (527) + tsc + keel green. Resolves the removal half of issuePluginSyncStaleServerState."; }
        part pluginSyncRemovalPropagationDoDR1 : TestResult { :>> id = "d7c1a010-0000-4a10-9b20-a1b2c3d4a010"; :>> outcome = VerdictKind::pass; :>> judgedAgainst = "a33497b"; :>> judgedAt = "2026-07-31"; :>> judgedBy = "claudeOpus"; }
        action pluginSyncDisplayName;
        verification pluginSyncDisplayNameDoD : Test { :>> id = "d7c19008-0000-4a10-9b20-a1b2c3d40098"; :>> method = VerificationMethod::test; :>> procedureText = "Ships 1.9.3. A synced-but-not-yet-loaded plugin shows its real display name, not the folder id. Simpler than a server fetch (the original idea): an ADOPTED plugin's manifest.json is already synced to LOCAL disk, so getPluginDisplayName reads the 'name' from .obsidian/plugins/<id>/manifest.json (cached; async, re-renders on resolve) — the settings row + sort fall back manifests[id]?.name || getPluginDisplayName(id) || id. A truly not-adopted server-only id (the 'Available' group) keeps the honest folder id. DoD: full client vitest + tsc + keel green. Resolves issuePluginSyncFolderIdNotName."; }
        part pluginSyncDisplayNameDoDR1 : TestResult { :>> id = "d7c1a00f-0000-4a10-9b20-a1b2c3d4a00f"; :>> outcome = VerdictKind::pass; :>> judgedAgainst = "969f779"; :>> judgedAt = "2026-07-31"; :>> judgedBy = "claudeOpus"; }
        // ===== Sprint vaultChangeTransitionGuard (2026-07-31) — 1.9.2: close the vault-change-skips-transition
        // data-integrity gap. =====
        action vaultChangeTransitionGuard;
        verification vaultChangeTransitionGuardDoD : Test { :>> id = "d7c19009-0000-4a10-9b20-a1b2c3d40099"; :>> method = VerificationMethod::test; :>> procedureText = "Ships 1.9.2 (data-integrity). A vault change no longer reconciles against a STALE base (which could silently overwrite local files via decide()'s B===L->pull branch, no conflict-copy). SetupWizardModal.finish() routes a vault CHANGE (vaultId differs AND local data present) through switchToVault('merge') — pendingSwitch -> switchTo clears the stale base + unions (the safe default, nothing lost) — instead of a silent reconnect. Defense-in-depth GUARD (D0047): the persisted base is stamped with its owner/vaultId (settings.baseVaultKey) after each successful connect, and doConnect forces a safe merge-switch whenever the live vault doesn't match that stamp — so ANY future path that changes the vault without switchTo can't silently overwrite. Guard test: plugin-wiring.test 'a FOREIGN base forces a safe merge-switch'. DoD: full client vitest (525) + tsc --noEmit clean + keel green. Resolves issueVaultChangeSkipsTransition."; }
        part vaultChangeTransitionGuardDoDR1 : TestResult { :>> id = "d7c1a00b-0000-4a10-9b20-a1b2c3d4a00b"; :>> outcome = VerdictKind::pass; :>> judgedAgainst = "e0a4422"; :>> judgedAt = "2026-07-31"; :>> judgedBy = "claudeOpus"; }
        // ===== Sprint sessionIdleReloginEase (2026-07-31) — 1.9.2: make the idle-logout non-surprising. =====
        action sessionIdleReloginEase;
        verification sessionIdleReloginEaseDoD : Test { :>> id = "d7c1900a-0000-4a10-9b20-a1b2c3d4009a"; :>> method = VerificationMethod::test; :>> procedureText = "Ships 1.9.2 (UX; the behavior is WORKING-AS-DESIGNED — token-only default IA.3.5.10 + idle timeout AC.3.1.11). The idle-logout is no longer a silent surprise: the connection FSM (connectionFsmTypedFailure) surfaces the reason as blocked{sessionExpired} → 'Session expired — open Settings → Reconfigure' on the status card + light (not just an opened modal), and the 'Store password on this device' setting hint documents the friction knob (it enables silent reconnect past the idle window) + names SESSION_IDLE_TIMEOUT_SECS for admins. The optional longer default idle window is server-config tuning left to the operator. Resolves issueSessionIdleReloginFriction."; }
        part sessionIdleReloginEaseDoDR1 : TestResult { :>> id = "d7c1a00c-0000-4a10-9b20-a1b2c3d4a00c"; :>> outcome = VerdictKind::pass; :>> judgedAgainst = "e0a4422"; :>> judgedAt = "2026-07-31"; :>> judgedBy = "claudeOpus"; }
        // ===== Sprint connectionFsmTypedFailure (2026-07-30) — 1.9.1: give the connection lifecycle's FAILURE
        // EDGE a type. A hard auth rejection was retried forever like a network drop (self-lockout via the
        // server throttle + an "offline" mislabel). Owner-directed FSM redesign, spec + independent critique:
        // docs/superpowers/specs/2026-07-30-connection-fsm-typed-failure-design.md. =====
        action connectionFsmTypedFailure;
        verification connectionFsmTypedFailureDoD : Test { :>> id = "d7c1900b-0000-4a10-9b20-a1b2c3d4009b"; :>> method = VerificationMethod::test; :>> procedureText = "Ships PATCH 1.9.1. The connection lifecycle is TWO cooperating single-concern FSMs (owner's 'multi FSMs, one per concern' steer): the operational work-queue EngineState (unchanged; 'offline' renamed 'disconnected') + a NEW instance-scoped LinkState machine (ok/retrying/blocked) in connstate.ts, driven by a pure classifyConnectError (reads ONLY tagged error fields — status/retryAfter/wasLogin/endpoint minted by transport, never a message regex) + a pure recoveryFor. The FSM ALPHABET is enums in one spot (FailureKind/RecoveryKind/LinkKind/LinkEventKind/Endpoint/SyntheticKind — owner's 'reference an enum, not hardcoded strings' steer). Behaviour, per the critique-corrected table (avoids BOTH strand and loop): a 401-login → blocked{authRejected} (STOP hammering, await user) with a ~10min self-heal re-probe; 429 → the server's Retry-After window; a chunk/meta 404 stays transient (never mis-tagged vaultGone → no strand); a vault-scope 404 → blocked{vaultGone}; version mismatch/degraded → typed synthetic; residual-unknown → bounded slow retry; isAuthError FIXED to read the status field (the /HTTP 401/ regex never matched the server's 'unauthorized' body — the loop's root cause). Distinct status labels replace the single 'offline'. vaultGone/lastIssue re-pointed at the LinkState (no dual source). Guard (D0047): connstate.test (19: classify table + strand/loop invariants) + syncengine.test (LinkState integration). DoD: full client vitest (525) + tsc --noEmit clean + keel green. Server untouched. Resolves issueAuthRetryStormNoStop."; }
        part connectionFsmTypedFailureDoDR1 : TestResult { :>> id = "d7c1a00a-0000-4a10-9b20-a1b2c3d4a00a"; :>> outcome = VerdictKind::pass; :>> judgedAgainst = "93bfdc4"; :>> judgedAt = "2026-07-30"; :>> judgedBy = "claudeOpus"; }
        // CLOSEOUT (autonomous, inspect): shipped 1.9.1; client vitest 525 + tsc clean + keel green. RETRO
        // (analysis): the failure edge was UNTYPED — one 'offline' bucket + one retry-forever recovery — so a
        // hard auth failure looped and self-locked. An independent critique of the FIRST design caught that the
        // naive fix would be WORSE (strand the user on a mid-deploy 401 / a transient chunk-404), and that
        // isAuthError was already broken — critique-before-implement paid off a FIFTH time. Durable lesson +
        // guard: classify reads TYPED fields never a message regex; unknown ⇒ bounded slow retry; every blocked
        // class self-heals. Owner-shaped: two FSMs (not one enum), the alphabet as enums in one spot.
        // ===== Sprint hotLoadSyncedPlugins (2026-07-31) — 1.11.0: activate a newly-synced plugin WITHOUT a
        // restart, on a provably-private vault only. A SECURITY-scoped, owner-accepted exception to the
        // Round-6-SEC 'never auto-execute sync-delivered config' gate. =====
        action hotLoadSyncedPlugins;
        verification hotLoadSyncedPluginsDoD : Test { :>> id = "d7c19010-0000-4a10-9b20-a1b2c3d400a0"; :>> method = VerificationMethod::test; :>> procedureText = "Ships MINOR 1.11.0. A community plugin newly synced to a device is activated LIVE (Obsidian's internal app.plugins.loadManifests + enablePlugin) — no restart — instead of the 'restart to activate' banner. SECURITY-SCOPED: a NARROW, owner-ACCEPTED exception to the Round-6-SEC 'never auto-execute sync-delivered config' gate. It fires ONLY on a PROVABLY-PRIVATE vault: OUR OWN (not shared TO us) AND with NO readWrite grant or share-link to anyone (refreshVaultPrivacy — FAIL-SAFE: any doubt/error => NOT private => restart barrier stays; refreshed on connect + on every share change). A shared/shareable vault (a peer could push malicious main.js = RCE into Obsidian's un-CSP'd renderer), an UPDATE to an already-running plugin (Obsidian re-executes plugin code only on reload), a hot-load FAILURE, and CSS all KEEP the restart trust-barrier. Best-effort: a plugin that refuses to hot-load falls back to restart, never breaks sync. PROVENANCE: the owner was shown the RCE tradeoff explicitly (the never-auto-execute gate + the shared-vault threat) and CHOSE the 'own, unshared vault only' scope over 'all vaults (reverse the gate)' / 'keep the restart gate' — a genuine INFORMED security decision. Guard: plugin-wiring 'refreshVaultPrivacy fail-safe' + 'hot-load: newly-synced on a private vault activates live; running-update/shared keeps the restart barrier'. DoD: full client vitest + tsc + keel green. Resolves issueSyncedPluginRestart."; }
        part hotLoadSyncedPluginsDoDR1 : TestResult { :>> id = "d7c1a011-0000-4a10-9b20-a1b2c3d4a011"; :>> outcome = VerdictKind::pass; :>> judgedAgainst = "1283e03"; :>> judgedAt = "2026-07-31"; :>> judgedBy = "claudeOpus"; }
        // REVIEW — the per-sitting human gate (D0049) for the 2026-07-31 sitting.
        verification sittingReview20260731 : Test { :>> id = "d7c1a00d-0000-4a10-9b20-a1b2c3d4a00d"; :>> method = VerificationMethod::confirmation; :>> procedureText = "Per-sitting human review (D0049) for the 2026-07-31 sitting: wweatherholtz directed 'proceed with all others' (the four investigated field defects), thereby accepting the completed work + its 1.9.2 release: the vault-change-transition data-integrity guard (vaultChangeTransitionGuard), the idle-relogin UX (sessionIdleReloginEase), the plugin-list parity UI split (under pluginSyncRemovalPropagation), and — on the follow-up 'continue' directives — the plugin display-name fix (pluginSyncDisplayName, 1.9.3, read from the synced local manifest) and the plugin display-name fix. CORRECTION (2026-07-31): this confirmation covers ONLY what the owner actually directed — the parity RESOLUTION (via 'proceed with all others' / 'continue'). The specific 'remove from server' PURGE mechanism (pluginSyncRemovalPropagation, 1.10.0) was AI-PROPOSED, not owner-chosen; the owner stated they did not explicitly choose it. After the correction + an explicit keep-vs-revert offer, the owner chose to KEEP it ('#2 keep in') — so it is an AI-initiated but owner-ACCEPTED kept feature; this attestation records that accurate provenance, not the retracted 'owner chose to build it' framing. SEPARATELY the owner asked to activate newly-synced plugins WITHOUT a restart; when shown that this collides with the Round-6-SEC never-auto-execute gate (a shared-vault peer could push malicious plugin code = RCE), the owner made an INFORMED choice of the 'own, unshared vault only' scope (over reversing the gate / keeping it) and directed 'yes please' — accepting hotLoadSyncedPlugins (1.11.0) at that scope. Single human confirmation gate for the owner-directed work; closeOut/retro autonomous."; }
        part sittingReview20260731R1 : TestResult { :>> id = "d7c1a00e-0000-4a10-9b20-a1b2c3d4a00e"; :>> outcome = VerdictKind::pass; :>> judgedAgainst = "e0a4422"; :>> judgedAt = "2026-07-31"; :>> judgedBy = "wweatherholtz"; }
        // ===== Sitting 2026-08-01 — the owner asked 'any outstanding items? let's do a critique pass'. A
        // 4-critic INDEPENDENT antagonistic pass over the 1.9.0-1.11.0 shipped code (data-integrity / FSM /
        // security / vault lenses) surfaced 3 verified HIGH defects; each finding was re-verified against the
        // code by the reviewer before recording (critic proposes, code decides). Owner directed 'fix all 3
        // HIGHs now'; each fixed TDD and shipped in PATCH 1.11.1. Lower-severity findings recorded as backlog
        // Issues (issues.sysml). closeOut (inspect)/retro (analysis) autonomous; sitting review is the human gate. =====
        // Sprint hotLoadPrivacyGateFreshCheck (1.11.1) — SECURITY: close the hot-load RCE-gate bypass.
        action hotLoadPrivacyGateFreshCheck;
        verification hotLoadPrivacyGateFreshCheckDoD : Test { :>> id = "7b078947-1ce3-405e-8ce5-3615b7c3606d"; :>> method = VerificationMethod::test; :>> procedureText = "Ships PATCH 1.11.1 (security). The 1.11.0 hot-load gate rode a STALE vaultIsPrivate: never reset on a vault switch; flushConfigReload (which hot-loads) ran BEFORE the connect-time refreshVaultPrivacy (itself fire-and-forget `void`); and the delta/poll path that also hot-loads never refreshed it. Net RCE-barrier (R14 sec#1) bypass: a private->shared vault switch, or an out-of-band readWrite grant on your own vault, left the gate true -> a peer's synced main.js auto-executes with NO restart. Fix: applyPluginCodeChange re-derives privacy FRESH at the decision point (awaited refreshVaultPrivacy, only when a plugin actually ARRIVED - rare), so the gate is current on EVERY entry path (connect ordering + delta staleness + switch staleness all closed); a shared/shareable vault or any error fails safe to NOT-private. Guard: plugin-wiring 'hot-load re-checks privacy FRESH — a stale-true vaultIsPrivate does NOT auto-execute a now-shared vault's plugin (RCE gate)' + the updated 'newly-synced on a private vault activates live' (now driven by the fresh source). DoD: full client vitest (531) + tsc --noEmit clean + keel green. Resolves issueHotLoadPrivacyGateStale (critique-found, HIGH)."; }
        part hotLoadPrivacyGateFreshCheckDoDR1 : TestResult { :>> id = "7e00be74-ffe8-4486-8e13-718200954a32"; :>> outcome = VerdictKind::pass; :>> judgedAgainst = "98a44a3"; :>> judgedAt = "2026-08-01"; :>> judgedBy = "claudeOpus"; }
        // Sprint reconcilePathReloginOnce (1.11.1) — FSM: a mid-session token expiry self-heals, no false block.
        action reconcilePathReloginOnce;
        verification reconcilePathReloginOnceDoD : Test { :>> id = "81ce40db-cf15-4d2f-9a03-9b13850bc535"; :>> method = VerificationMethod::test; :>> procedureText = "Ships PATCH 1.11.1 (FSM/UX). A routine token expiry DURING a connected session used to mis-classify as a PERMANENT auth block: the reconcile effects (doReconcileAll/doReconcilePath) hit the API directly, unlike doConnect which re-logs-in once on a 401 — so a poll-path 401 went straight to classify -> blocked{authRejected} ('Sign-in rejected — check your password') for up to the 600s self-heal reprobe, and PERMANENTLY on a WS-less mobile client. The inverse of the auth-storm connectionFsmTypedFailure fixed. Fix: withSyncRelogin wraps the reconcile effects — on a 401, IF a password is stored, one silent re-login (freshLogin, rebuild the api) + a single retry; a second 401, or NO stored password (token-only), propagates to classify -> the correct blocked/re-auth state. Guard: plugin-wiring 'mid-session token expiry on the poll path silently re-logs-in ONCE (no false auth block)'. DoD: full client vitest (531) + tsc clean + keel green. Resolves issueReconcilePathTokenExpiryBlock (critique-found, HIGH)."; }
        part reconcilePathReloginOnceDoDR1 : TestResult { :>> id = "68275e7c-028c-40cd-a9b4-0c6fd7cd985d"; :>> outcome = VerdictKind::pass; :>> judgedAgainst = "98a44a3"; :>> judgedAt = "2026-08-01"; :>> judgedBy = "claudeOpus"; }
        // Sprint vaultKeyServerQualified (1.11.1) — DATA: server-qualify the vault-identity key.
        action vaultKeyServerQualified;
        verification vaultKeyServerQualifiedDoD : Test { :>> id = "7b975432-83a4-4fb3-82e0-6218735d91d2"; :>> method = VerificationMethod::test; :>> procedureText = "Ships PATCH 1.11.1 (data-integrity). The D0047 vault-change guard's identity key was SERVER-BLIND (historyFloorKey = owner/vault) and so was the setup wizard's vaultChanged check — so repointing this device at a DIFFERENT server that hosts the SAME vault name (e.g. 'notes', 'obsidian' — two servers trivially collide on owner=''/vault) never tripped the guard: a plain reconcile ran against a FOREIGN base and could silently overwrite local files (decide()'s B===L->pull, no conflict-copy). Fix: a new server-qualified vaultIdentityKey (`host|owner/vault`, host from URL.host; `|` occurs in neither a host nor a vault name) backs the guard + the baseVaultKey stamp; the wizard's vaultChanged now also compares serverUrl. An OLD server-blind stored key (no `|`) is GRANDFATHERED to the current server so an upgrade doesn't force a spurious merge for existing users; a genuine later server/vault/owner change still trips. Guards: plugin-wiring 'D0047 guard is SERVER-qualified: a different server with the same vault name is a different vault' + 'grandfathers an old server-blind base key' + the updated foreign-base test. DoD: full client vitest (531) + tsc clean + keel green. Resolves issueVaultKeyServerBlind (critique-found, HIGH)."; }
        part vaultKeyServerQualifiedDoDR1 : TestResult { :>> id = "fadb9c91-8c77-41db-a4a3-dd70ab37eea4"; :>> outcome = VerdictKind::pass; :>> judgedAgainst = "98a44a3"; :>> judgedAt = "2026-08-01"; :>> judgedBy = "claudeOpus"; }
        // ===== Backlog resolver stubs (recorded critique findings, NOT started) — one per critic area; each
        // DoD describes the fix, no R1 yet. They triage the backlog Issues (D0077) so resolution stays computed. =====
        action critiqueBacklogFsm;
        verification critiqueBacklogFsmDoD : Test { :>> id = "70cf3431-9e45-4a05-a840-6b0de039e020"; :>> method = VerificationMethod::test; :>> procedureText = "DONE (1.11.2 @4b88886). FIXED: F2 disconnect/unload reset LinkState + clear lastIssue (test 'disconnect resets LinkState'); F3 the synthetic serverDegraded reindex message is no longer clobbered by the generic catch (test 'a serverDegraded message survives the generic catch'); F5 the dead UserRetry edge removed. NOT-CHANGED (justified): F4 — classify already pins the server's REAL 'mfa required'/'password change' phrasings (connstate.test) + must-change is handled via the login flag, so no rewrite needed (the plugin's lack of a TOTP field is a separate FEATURE gap, logged as issueMfaLoginUnsupported); the F5 429 re-arm / 503 retry-after nuances are bounded (our server sends sane windows) and left as-is. Original findings: (F2, MED) disconnect/unload don't reset LinkState, so getLastIssue/isVaultGone leak a stale blocked/vault-gone prompt after the user disconnects — reset link=LINK_OK in the disconnect/unload handlers. (F3, MED) the actionable serverDegraded 'run reindex' message set in doConnect is CLOBBERED by the generic outer catch (lastIssue = 'Can't reach the server…'), and ServerDegraded->Retrying{Slow} then shows generic 'Reconnecting…' — don't overwrite a synthetic's lastIssue. (F4, MED) MFA / must-change-password classification matches on UN-PINNED server body strings (the anti-pattern the FSM otherwise forbids) — pin the server phrasing or carry a typed reason. (F5, LOW) the UserRetry LinkState edge is dead (never dispatched); a repeated 429 re-arms retryAfter each cycle vs the spec's 'one retry'; Retry-After is honored only for 429 (503 uses a fixed 60s). Resolves issueFsmCritiqueBacklog."; }
        part critiqueBacklogFsmDoDR1 : TestResult { :>> id = "a4033440-ae53-4e15-854f-9b8194e873c4"; :>> outcome = VerdictKind::pass; :>> judgedAgainst = "4b88886"; :>> judgedAt = "2026-08-02"; :>> judgedBy = "claudeOpus"; }
        action critiqueBacklogTimestamp;
        verification critiqueBacklogTimestampDoD : Test { :>> id = "cda4cdb2-a1fb-427d-ae1b-ef038b7a8719"; :>> method = VerificationMethod::test; :>> procedureText = "DONE (1.11.2 @4b88886). FIXED: T1/T2 the value-shape gate is now a PORTABLE ISO date/datetime regex (isTimestampValue), NOT Date.parse — a bare-year `created: 2020`/counter is no longer masked (it syncs, matching the UI promise), and identity is stable across desktop V8 / mobile JSCore (tests 'isTimestampValue: ISO shapes only' + 'a BARE-YEAR created edit is NOT masked'); T4 normalizedContent strips ALL trailing newlines + normalizes a lone CR to match merge3's sameIgnoringEol exactly (test 'a lone-CR and a final-newline TOGGLE are non-differences'). ACCEPTED (documented, LOW): T3 normHash-never-persisted / >1MiB gap — the base.text recompute covers the common <=1MiB case; persisting it for streamed large files isn't worth a LOW finding (already documented in baseNormHash). Original findings: (T1, MED) the value-shape gate is Date.parse-based, so a bare-year `created: 2020` (or a manually-curated date) is masked -> editing it silently doesn't propagate, contradicting the settings UI's 'a non-date value under the same key still syncs' — tighten the gate to a portable date-shape regex + reconcile the UI copy. (T2, MED) identity leans on Date.parse (engine-defined), so a non-canonical timestamp value hashes differently on desktop V8 vs mobile JSCore -> cross-platform churn — use a portable parser. (T4, LOW/MED) trailing-newline normalization is inconsistent: normalizedContent collapses 2+ -> 1 (keeps 0-vs-1 distinct) while merge3's sameIgnoringEol strips all -> a final-newline toggle churns on the push path but not the merge path; lone-CR (old-Mac) isn't normalized either. (T3, LOW) normHash is declared/serialized/read but NEVER written -> the override rides on base.text recompute; a >1MiB/text-less base has no identity (documented-accepted, churn+resurrection for large files only). Resolves issueTimestampGateCritiqueBacklog."; }
        part critiqueBacklogTimestampDoDR1 : TestResult { :>> id = "72d1ca51-6fc3-4a71-b492-097c122046a5"; :>> outcome = VerdictKind::pass; :>> judgedAgainst = "4b88886"; :>> judgedAt = "2026-08-02"; :>> judgedBy = "claudeOpus"; }
        action critiqueBacklogVault;
        verification critiqueBacklogVaultDoD : Test { :>> id = "577e534c-a351-46a3-ae0c-cc4b2b44a4a0"; :>> method = VerificationMethod::test; :>> procedureText = "DONE (1.11.2 @4b88886). FIXED: V2 — the D0047 guard's auto-merge now shows a user Notice (no longer SILENT), and redeeming a share on a device with local data routes through switchToVault('merge') (like the wizard's finish()) instead of a silent reconnect against a foreign base (setupwizard finishRedeem). ACCEPTED (LOW): V3 — the empty-base case has NO overwrite risk (no foreign base entries to trigger decide()'s pull; the local push-up is the broader resolution-modal UX question, not a data-loss bug), and the baseVaultKey fire-and-forget stamp is idempotent/self-healing. A full per-perm Download/Upload/Cancel modal on the guard path stays a possible future UX enhancement (the safe merge + notice is non-destructive meanwhile). Original findings: (V2, MED) the setup wizard's finishRedeem + the direct-adopt path route a redeem / an owner-axis change through reconnect() with NO resolution modal (only the vaultId-name axis was closed), relying on the silent guard; and the guard's own remedy is a SILENT merge (a union = cross-vault contamination), not the Download/Upload/Cancel adjudication modal SwitchVaultModal offers — route guard-detected changes through the same modal. (V3, LOW) the guard requires base.paths().length, so a vault change with an empty base but local files skips it (pushes local into the new vault); baseVaultKey is stamped via a fire-and-forget save (a crash re-fires a redundant merge). Resolves issueVaultTransitionModalBacklog."; }
        part critiqueBacklogVaultDoDR1 : TestResult { :>> id = "ba43bafd-b7c0-4049-b9d8-11d330224e05"; :>> outcome = VerdictKind::pass; :>> judgedAgainst = "4b88886"; :>> judgedAt = "2026-08-02"; :>> judgedBy = "claudeOpus"; }
        action critiqueBacklogSecurity;
        verification critiqueBacklogSecurityDoD : Test { :>> id = "e188c851-5285-4dec-ae5c-acacda3c7536"; :>> method = VerificationMethod::test; :>> procedureText = "DONE (1.11.2 @4b88886). FIXED: S3 — removePluginFromServer now validates the plugin id against /^[A-Za-z0-9][A-Za-z0-9._-]*$/ (rejects `..`/slash/empty) BEFORE it builds the delete prefix, so a server/peer-influenced id can't widen the deletion beyond one plugin folder (test 'removePluginFromServer REJECTS a traversal / malformed plugin id'). S2 — OWNER DECISION (recorded, not code): shown the malicious-server threat (the gate trusts server-reported share metadata, and that same server ships the plugin bytes), the owner chose ACCEPT-RISK via the question 'How should we treat that?' -> 'Accept the risk (trust your server)'. Rationale (owner-endorsed): a compromised server already controls the plugin bytes it delivers, so trusting its share-metadata adds NO new exposure; the self-hosted single-user server is in the trust boundary. The private-vault hot-load exception stands as-is. The S3 re-push-re-hot-loads note is documented-accepted (on a private vault, re-activating your OWN re-pushed code needs no re-approval by design). Original findings: (S2, MED — threat-model decision) the hot-load privacy gate derives vaultIsPrivate from share metadata the SERVER reports; a COMPROMISED server (which also ships the plugin bytes) could lie 'not shared' -> hot-load. In scope only if the self-hosted server is treated as untrusted — needs an owner decision (accept-risk vs client-side attestation vs revert the hot-load exception). (S3, LOW) removePluginFromServer(id) builds a delete prefix from a server/peer-influenced id without validating it (reject `..`/`/`/empty); and a removed plugin re-pushed by another active device re-arrives and, on a private vault, hot-loads again without re-approval (allowlist desync). Resolves issueSecurityHardeningBacklog."; }
        part critiqueBacklogSecurityDoDR1 : TestResult { :>> id = "ffb9caa4-d246-4ae3-9775-1d8ab546367d"; :>> outcome = VerdictKind::pass; :>> judgedAgainst = "4b88886"; :>> judgedAt = "2026-08-02"; :>> judgedBy = "claudeOpus"; }
        // ===== Sprint statusDisplayPureProjection (2026-08-02) — 1.11.3: FIELD BUG. The mobile status card
        // latched "Switching vault… applying your choice" on a persisted pendingSwitch even while synced. =====
        action statusDisplayPureProjection;
        verification statusDisplayPureProjectionDoD : Test { :>> id = "e113e917-9cc3-4390-ab54-60fe37171b63"; :>> method = VerificationMethod::test; :>> procedureText = "Ships PATCH 1.11.3. Owner-reported on mobile: the status card showed 'Switching vault… applying your choice' PERSISTENTLY while connected + synced, with no switch initiated. Root cause: statusDisplay() reached AROUND the pure Phase projection to read settings.pendingSwitch (a persisted CONFIG value) + this.resuming (a loose flag) — neither is an FSM state — so a pendingSwitch that lingered set (its switchTo reconcile killed mid-flight on mobile before it cleared) latched the label. The D0047 guard was NOT the trigger (no 'base belonged to' line in the owner's shared debug log). Spec: docs/superpowers/specs/2026-08-02-status-display-pure-projection-design.md; independent antagonistic critique before ship. FIX: statusDisplay is now a PURE projection of Phase (+ syncPending/realtimeConnected/vaultReadOnly), reading no setting/flag — a switch/resume is a TRANSIENT shown as the normal connecting/syncing/idle projection, so a stale setting can never latch a label; the `resuming` field + isResuming() are deleted (display-only, now dead). CRITIQUE-HARDENED: (HIGH) an ALREADY-APPLIED guard clears a lingering AUTHORITATIVE switch (download/upload) whose base already belongs to the target vault — preventing a per-connect RE-CLOBBER of local edits (a not-yet-applied switch still replays, preserving R12-CA1; merge is idempotent); (MEDIUM) the settings-card dot now passes realtimeConnected into light() like the ribbon (no green-dot-over-polling divergence). Copy: '.obsidian file(s) in scope' -> 'syncing N Obsidian settings file(s)'. Guards: plugin-wiring 'statusDisplay … a PURE projection (no setting/flag can latch a label)' + 'a lingering already-applied authoritative switch is cleared, NOT re-run'. DoD: full client vitest (536) + tsc --noEmit clean + keel green. Resolves issueStatusSwitchingLatched."; }
        part statusDisplayPureProjectionDoDR1 : TestResult { :>> id = "6f4992b2-ebe2-40e8-a07c-1eb1c63f0f60"; :>> outcome = VerdictKind::pass; :>> judgedAgainst = "6183b5c"; :>> judgedAt = "2026-08-02"; :>> judgedBy = "claudeOpus"; }
        // ===== Sprint switchAbortOnOutage (2026-08-02) — 1.11.4: FIELD BUG surfaced by the owner's 1.11.3 log.
        // A vault switch swallowed a whole-server outage as per-file skips → a FALSE "Synced (polling)". =====
        action switchAbortOnOutage;
        verification switchAbortOnOutageDoD : Test { :>> id = "23ceec46-8334-4b63-b3d7-4055677e0f47"; :>> method = VerificationMethod::test; :>> procedureText = "Ships PATCH 1.11.4. Owner's 1.11.3 debug log (mobile): a persisted 'upload' switch ran during a DNS outage and logged a FLOOD of per-file 'UnknownHostException: Unable to resolve host notes2… — skipped it, other files continue', then the card settled to a FALSE 'Synced (polling)' (yellow) while the server was actually unreachable. Root cause: the normal reconcile loops abort a pass on a connection-level error (isConnectionError -> throw -> engine offline+backoff ONCE), but switchTo's helpers (switchDownload/switchUpload) did NOT — every server-op catch went straight to onFileError (skip+continue). So a whole-server outage (DNS unresolvable, hits EVERY file identically) was swallowed file-by-file, the switch 'completed' with everything skipped, and the engine settled to idle -> the STATUS LIED 'synced' when it couldn't reach the server at all. FIX: switchDownload (applyPull) + switchUpload (pushFile, deleteFile) check isConnectionError first and re-throw, mirroring reconcileAll -> a DNS/host-unreachable outage aborts the switch -> engine disconnected -> 'Reconnecting…' (honest), no per-file skip flood; the local io.remove (not a server op) stays isolated; merge already routed through reconcileAll (covered). Side effect: the stuck 'upload' now aborts cleanly and completes+clears once the network returns instead of looping on skips. Guards: reconcile.test 'upload ABORTS on a whole-server outage (DNS)' + 'download ABORTS on a whole-server outage (DNS)'. DoD: full client vitest (538) + tsc clean + keel green. Resolves issueSwitchOutageFalseSynced. NOTE: the underlying host-unresolvable condition (notes2.willweatherholtz.com) is the owner's network/server to diagnose — the client's job is the honest status, which this restores."; }
        part switchAbortOnOutageDoDR1 : TestResult { :>> id = "a24e3e51-bb65-44a9-a602-62f36f821786"; :>> outcome = VerdictKind::pass; :>> judgedAgainst = "1608366"; :>> judgedAt = "2026-08-02"; :>> judgedBy = "claudeOpus"; }
        // ===== Sprint connectPhaseNoOptimisticFlip (2026-08-02) — 1.11.5: FIELD BUG (deeper layer). After the
        // 1.11.4 abort, the card STILL read 'Synced (polling)' during the failing connect attempts. =====
        action connectPhaseNoOptimisticFlip;
        verification connectPhaseNoOptimisticFlipDoD : Test { :>> id = "8884b3ca-21ad-47e7-bcc0-5e77f54fa6e8"; :>> method = VerificationMethod::test; :>> procedureText = "Ships PATCH 1.11.5. Follow-up to switchAbortOnOutage on the owner's log: the switch now correctly ABORTED on the DNS outage (connect FAILED -> retrying in 3s), but the card STILL read 'Synced (polling)' during the failing ~30s connect attempts. Root cause, one FSM layer deeper: markReconciling() optimistically flipped connecting/disconnected -> reconciling (-> phase 'syncing') the moment the health check passed, BEFORE the initial reconcile; when that reconcile transferred NOTHING (failing on DNS), syncPending stayed 0 and effectivePhase collapsed syncing-0-pending -> idle -> a FALSE 'Synced (polling)' for the whole attempt. A normal POLL never had this — it doesn't pre-flip (beginReconcile escalates idle->reconciling only on real work). FIX: make connect behave like a poll — REMOVED markReconciling; broadened beginReconcile to escalate from idle OR an in-flight connect (connecting/disconnected); onProgress(pending>0) now calls it too. So the initial reconcile shows 'Connecting…' and becomes 'Syncing… N' ONLY while actually transferring — a failing/empty connect stays 'Connecting…'/'Reconnecting…' and can NEVER collapse to a false 'Synced'; beginReconcile is now the single door into 'reconciling'. No events lost (path/remote during connect still queue + process after connect). Spec (updated): docs/superpowers/specs/2026-08-02-status-display-pure-projection-design.md. Guards: syncengine.test 'the initial reconcile shows Connecting until it has real work, then Syncing' + 'a connect whose initial reconcile transfers NOTHING never shows a false syncing/idle' + 'a retry that reaches the server upgrades to syncing when it finds work'. DoD: full client vitest (538) + tsc clean + keel green. Resolves issueConnectFalseSyncedDuringInitialReconcile."; }
        part connectPhaseNoOptimisticFlipDoDR1 : TestResult { :>> id = "8c8c39ab-03d2-4ffd-ace5-7b14fa87454e"; :>> outcome = VerdictKind::pass; :>> judgedAgainst = "08438fa"; :>> judgedAt = "2026-08-02"; :>> judgedBy = "claudeOpus"; }
        // ===== Sprint switchReportsProgress (2026-08-02) — 1.11.6: FIELD BUG. A vault switch reported no
        // progress, so on 1.11.5 it sat on a static 'Connecting…' and read as HUNG. =====
        action switchReportsProgress;
        verification switchReportsProgressDoD : Test { :>> id = "7fd0d646-4414-4917-9c1c-46c3b5a8c93f"; :>> method = VerificationMethod::test; :>> procedureText = "Ships PATCH 1.11.6. Follow-up to connectPhaseNoOptimisticFlip on the owner's log ('hung on connecting?'): on 1.11.5 the card honestly showed 'Connecting…' during the initial reconcile, but a vault SWITCH (upload/download) reports NO onProgress — so syncPending stayed 0, there was no 'Syncing… N' and no state escalation, and it sat on a STATIC 'Connecting…' the whole time (looked hung during a long upload). The normal reconcile (reconcileAll) reports onProgress; switchTo did not. FIX: switchDownload + switchUpload now report onProgress like reconcileAll — the full count up front, decrementing to 0 as each file transfers — which drives the 'N pending' detail AND (via main's onProgress -> beginReconcile) escalates the status to 'Syncing…'. So an active switch shows 'Syncing… N pending' that DECREASES (clearly working), a stalled one shows a stuck count, and a whole-server outage still aborts to 'Reconnecting…' (switchAbortOnOutage). merge already routed through reconcileAll (had progress). Guards: reconcile.test 'upload reports progress (full count -> 0)' + 'download reports progress (full count -> 0)'. DoD: full client vitest (540) + tsc clean + keel green. Resolves issueSwitchNoProgressLooksHung."; }
        part switchReportsProgressDoDR1 : TestResult { :>> id = "30634ebc-b184-4804-9774-0ad7b096404a"; :>> outcome = VerdictKind::pass; :>> judgedAgainst = "7981610"; :>> judgedAt = "2026-08-02"; :>> judgedBy = "claudeOpus"; }
        // ===== Sprint resumeReattemptsConnection (2026-08-02) — 1.11.7: FIELD BUG. On mobile, a failed
        // connection didn't re-attempt on resume (suspended backoff timer + a dropped remote event). =====
        action resumeReattemptsConnection;
        verification resumeReattemptsConnectionDoD : Test { :>> id = "784b9237-6d07-476e-8919-b15e2683a103"; :>> method = VerificationMethod::test; :>> procedureText = "Ships PATCH 1.11.7. Owner (mobile): 'url works fine… is it rechecking though? I don't see it reattempt.' It wasn't. Root cause (mobile context-switching): (1) the backoff reconnect timer is window.setTimeout, which mobile SUSPENDS while backgrounded, so a pending retry sits paused; (2) onResume enqueued a `remote` event, which the engine DROPS while disconnected (it ignores work until connected). So foregrounding after a failed connect did nothing to re-attempt — it looked stuck with nothing in the log. FIX: onResume checks engine.getState(); if DISCONNECTED, it cancels the stale (paused) backoff timer and enqueues a fresh `connect` immediately (re-probing the now-available network/DNS), and LOGS 'app resumed — re-checking the connection' so the recheck is VISIBLE; if connected it re-assesses (reconcile) as before; 'off' (user-disconnected) is left alone. So every foreground promptly rechecks instead of waiting on a suspended timer. Guard: plugin-wiring 'mobile resume RE-ATTEMPTS a failed connection (not a dropped remote)'. DoD: full client vitest (541) + tsc clean + keel green. Resolves issueMobileResumeNoReattempt. NOTE: the owner confirmed the server URL works — this closes the mobile resume-recheck gap; a genuinely-unreachable server still shows honest 'Reconnecting…'."; }
        part resumeReattemptsConnectionDoDR1 : TestResult { :>> id = "d4b8725a-14a9-4521-9bfa-6fdde360c4db"; :>> outcome = VerdictKind::pass; :>> judgedAgainst = "777f586"; :>> judgedAt = "2026-08-02"; :>> judgedBy = "claudeOpus"; }
        // ===== Sprint switchUploadProbeGuard (2026-08-02) — 1.11.8: an L-1 data-loss bug FOUND by an STPA-UCA
        // hunt (not the field) — the upload switch tombstoned a remote file on a false-absent io.list(). =====
        action switchUploadProbeGuard;
        verification switchUploadProbeGuardDoD : Test { :>> id = "27eba8dd-fdd9-473f-b21c-336019865532"; :>> method = VerificationMethod::test; :>> procedureText = "Ships PATCH 1.11.8 (DATA-INTEGRITY, L-1). Found by an STPA-UCA hunt on the delete/overwrite control actions (NOT a field report): switchUpload's remote-drop loop issued delete-remote (→ a server tombstone → delete-local on EVERY peer) for any path missing from the switch's SINGLE io.list() snapshot, with NO probePresence re-probe and NO bulk guard. io.list() is fallible (an un-hydrated cloud placeholder, a dir that fails to enumerate, an OS/AV lock transiently omits a STILL-PRESENT file); on an 'upload' switch that file is then never pushed AND tombstoned server-side → peers delete their real copy (L-1). This was the ONE delete path that trusted the raw listing — reconcileOne + reconcileDelta re-probe (probePresence) and switchDownload's local-mirror is bulk-ratio-guarded; switchUpload had neither, an asymmetry the codebase's own issueFalseAbsenceDelete guard exists to prevent. FIX: gate the remote-drop with probePresence — present OR indeterminate ⇒ KEEP on the server (only a definitive local absence tombstones), mirroring reconcileOne's delete-remote. Guard (fail-first proven — RED without the probe: keep.md tombstoned; GREEN with it): reconcile.test 'upload switch does NOT tombstone a remote file that io.list() FALSELY omits'. DoD: full client vitest (553) + tsc clean + keel green. Resolves issueSwitchUploadFalseAbsenceDelete. Realizes the SR for UCA-6 on the switch path (STPA S-17)."; }
        part switchUploadProbeGuardDoDR1 : TestResult { :>> id = "590dd37c-9fe5-439c-aceb-35bf4db7b30e"; :>> outcome = VerdictKind::pass; :>> judgedAgainst = "e1a9d21"; :>> judgedAt = "2026-08-02"; :>> judgedBy = "claudeOpus"; }
        // Backlog stub (STPA-hunt finding 2, owner-decision) — untrusted CSS from a shared vault is applied
        // with only a restart notice, no trust warning + no private-vault gate (unlike plugin code). NOT started.
        action cssTrustGate;
        verification cssTrustGateDoD : Test { :>> id = "0a214c17-b7f8-44d7-8f05-53223201d333"; :>> method = VerificationMethod::test; :>> procedureText = "DONE (1.11.9 @059830d). The second STPA-hunt finding (L-3, Medium): flushConfigReload classified synced themes/snippets/appearance CSS as 'will apply after restart' (a bare Notice) on the premise 'CSS never auto-applied' — but the plugin WRITES the CSS to disk during reconcile and Obsidian hot-reloads an ENABLED snippet/theme with no restart; CSS in the un-CSP'd renderer enables exfil (background:url) + phishing. UCA-7 named CSS but its mitigation SR-5 gated only plugin CODE. OWNER DECISION: the owner directed 'close css gap' (gate, not accept-by-parity). FIX: flushConfigReload handles CSS on its own branch with a FRESH privacy re-check (like the hot-load gate) — a SHARED/shareable vault gets a TRUST WARNING ('CSS arrived via sync from a shared vault … REVIEW it and remove anything from a source you don't trust'), a provably-PRIVATE vault a plain notice; the stale 'never auto-applied' comment corrected; the test-harness Notice records messages so the warning is asserted. Guard: plugin-wiring 'synced CSS from a SHARED vault warns … PRIVATE plain'. DoD: full client vitest (554) + tsc clean + keel green. Resolves issueUntrustedCssApplied."; }
        part cssTrustGateDoDR1 : TestResult { :>> id = "7857965c-e4f9-4f7e-9d49-a077e74f2572"; :>> outcome = VerdictKind::pass; :>> judgedAgainst = "059830d"; :>> judgedAt = "2026-08-02"; :>> judgedBy = "claudeOpus"; }
        // RAN: keel reverify --all-drift (re-ran the declared gate at HEAD)
        part cssTrustGateDoDR2 : TestResult { :>> id = "084b6e41-5c7a-471d-b17c-f034cea7b092"; :>> outcome = VerdictKind::pass; :>> judgedAgainst = "fdbbc3ce"; :>> judgedAt = "2026-09-07"; :>> judgedBy = "claudeOpus"; }
        // ===== Sprint deleteRemoteCasGuard (2026-08-02) — an L-1 LOST-UPDATE (server) FOUND by an STPA-UCA
        // hunt on the delete/overwrite control actions; the owner chose CAS-guard over accept-authoritative. =====
        action deleteRemoteCasGuard;
        verification deleteRemoteCasGuardDoD : Test { :>> id = "4c8a1f20-3b6d-4e91-a7c2-9d05e8f13b46"; :>> method = VerificationMethod::test; :>> procedureText = "Ships PATCH 1.11.10 (DATA-INTEGRITY, L-1) — client + SERVER (the self-hosted server image MUST be redeployed for the guard to take effect; both sides are backward-compatible so either can update first). STPA-UCA hunt on the server delete control action: Vault::commit CAS-guards optimistic concurrency (expected_version) but Vault::delete did NOT — a device on a STALE base could delete a file another device just edited (A edits v5->v6; B, still at v5, deletes -> tombstone v7), and the editor pulls the tombstone + silently loses its edit FLEET-WIDE (a lost update, no conflict marker) — the exact class commit's CAS stops; a readWrite grantee could weaponize it. OWNER DECISION (AskUserQuestion 2026-08-02): CAS-guard delete, symmetric with commit, over accept-authoritative (recorded in deleteRemoteCasGuardChoice). FIX: server Vault::delete_checked(path, expected_version) mirrors commit's CAS (stale -> AlreadyExists -> 409); delete_file parses expected_version + maps the conflict to 409; the authoritative Vault::delete(path) wrapper (None) still always wins for deliberate deletes + tests. Client transport.deleteFile(path, expectedVersion?) wires the query param + maps 409 -> CommitConflictError; the reconcile deleteRemote effect carries the based-on remote version + the shell sends it; user-gesture / adjudication / switch deletes OMIT it. On a 409 the client re-reconciles and — because decide() keys on hashes — remote-advanced-since-base reads as edit-wins-pull, RESURRECTING the edit (never lost). Backward-compatible both ways (old client omits the field; old server ignores the unknown query param). Guards (fail-first — without the guard the stale delete clobbers): server cargo vault::tests::delete_cas_rejects_a_stale_delete_that_would_clobber_a_newer_commit + authoritative_delete_always_wins_and_absent_delete_is_a_noop; client reconcile.test 'delete-remote CAS ... passes the based-on remote version' + '... a stale delete 409s and the peer's concurrent edit is resurrected (edit-wins-pull), never lost'; finalize.test asserts the deleteRemote effect carries the version. DoD: full server cargo test (all suites 0 failed) + full client vitest (186) + tsc clean + keel validate + guard green. Resolves issueDeleteNoCasLostUpdate. Realizes the SR for the delete control action (STPA S-18)."; }
        part deleteRemoteCasGuardDoDR1 : TestResult { :>> id = "5e9b2a31-4c7e-4f02-b8d3-ae16f9024c57"; :>> outcome = VerdictKind::pass; :>> judgedAgainst = "f141a3a"; :>> judgedAt = "2026-08-02"; :>> judgedBy = "claudeOpus"; }
        // The owner's DESIGN CHOICE (confirmation) — CAS-guard over accept-authoritative; the evidence is their explicit pick.
        verification deleteRemoteCasGuardChoice : Test { :>> id = "6f0c3b42-5d8f-4013-c9e4-bf27a0135d68"; :>> method = VerificationMethod::confirmation; :>> procedureText = "The owner was shown the VERIFIED fork — DELETE has no CAS, so a stale delete silently discards a concurrent edit, while COMMIT already guards exactly this — and chose 'CAS-guard delete (like commit)' over 'Accept delete-authoritative' and 'Let me see both diffs first', via an explicit AskUserQuestion on 2026-08-02. This records ONLY that design-approach choice (their word is the evidence, D0016); it is NOT acceptance of the shipped RESULT — the per-sitting review (sittingReview20260802b) stays open for the owner's review of 1.11.10."; }
        part deleteRemoteCasGuardChoiceR1 : TestResult { :>> id = "7a1d4c53-6e90-4124-daf5-c038b1246e79"; :>> outcome = VerdictKind::pass; :>> judgedAgainst = "f141a3a"; :>> judgedAt = "2026-08-02"; :>> judgedBy = "wweatherholtz"; }
        // Backlog stub (STPA server-hunt LOW finding, issueMirrorWriteNotSelfHealed) — a failed bind-mount mirror
        // write isn't self-healed by a later idempotent commit retry. NOT data loss (chunk store authoritative);
        // niche (direct host-fs editing). NOT started — honestly-incomplete backlog (non-blocking, D0098).
        action mirrorWriteSelfHealBacklog;
        verification mirrorWriteSelfHealBacklogDoD : Test { :>> id = "a1b2c3d4-1700-4a10-9b20-d1700c0de017"; :>> method = VerificationMethod::test; :>> procedureText = "Ships with 1.17.0 (server; redeploy). A failed best-effort bind-mount mirror write is now REPAIRED by a later idempotent re-commit: Vault::commit's same-content short-circuit re-attempts write_mirror when the on-disk mirror is absent or its size differs (gated on cheap fs::metadata — write_mirror is atomic temp+fsync+rename, so a size match is a reliable already-healed signal; avoids a full-file read per re-commit, critique #2). NOT data loss (the chunk store is authoritative + serves get_chunk); niche (a user editing on the host FS via the bind mount). Guard: vault::tests::idempotent_recommit_self_heals_a_missing_mirror + clippy -D warnings. Resolves issueMirrorWriteNotSelfHealed."; }
        part mirrorWriteSelfHealBacklogDoDR1 : TestResult { :>> id = "a1b2c3d4-1700-4a10-9b20-d1700c0de018"; :>> outcome = VerdictKind::pass; :>> judgedAgainst = "b997a63"; :>> judgedAt = "2026-08-05"; :>> judgedBy = "claudeOpus"; }
        // ===== Sprint removeDiagnoseButton (2026-08-02) — 1.11.11: remove the misleading 'Diagnose' button
        // (L-5 false all-clear); the honest FSM-projected status card is the single source of truth. =====
        action removeDiagnoseButton;
        verification removeDiagnoseButtonDoD : Test { :>> id = "9d3f0a51-6c8e-4b72-a1d4-0e5f28b39c60"; :>> method = VerificationMethod::test; :>> procedureText = "Ships PATCH 1.11.11 (UX / L-5). Owner-reported: 'does diagnose actually do much? always says everything is fine even if it's not working.' HttpTransport.diagnose probed only the CONNECTION chain (reachable/version/auth/vault/degraded) via out-of-band HTTP and returned 'All good' whenever those five links were healthy — NEVER consulting the live sync engine, so it was blind to sync non-convergence (stalled/off engine, pending not draining, a file looping, a wedged FSM) and gave a false all-clear in exactly the stuck-but-pipe-fine case the user clicks it for. Analysis: the honest status card (a pure FSM projection, built this sitting) ALREADY surfaces every actionable cause diagnose gave, via connstate.blockedTip (version mismatch / sign-in / session / MFA / vault-gone / access-removed / degraded), derived from REAL failures — so diagnose was a redundant SECOND source of truth whose only distinctive behavior was the misleading all-clear (the dual-source anti-pattern). OWNER DECISION ('consider just removing'): REMOVE the Diagnose button + its whole chain — settings.ts button+runDiagnosis, main.ts diagnoseConnection, transport.ts HttpTransport.diagnose + the Diagnosis/DiagnosisLayer types, the transport.test diagnose ladder suites, the ui-dom-harness mock — leaving the honest status line as the single source (it cannot give a false all-clear, being a pure projection). The separate 'Diagnostics' group (Show sync log / Copy debug info) is untouched; tryJson stays (shared). Guard: transport.test green with the diagnose suites removed (no dead reference); tsc clean proves no orphaned import (CLIENT_API_VERSION import dropped). DoD: full client vitest + tsc clean + esbuild build clean + keel validate + guard green. Resolves issueDiagnoseFalseAllClear. Relates to H-9 (reported!=actual -> L-5); no new STPA element — removing the redundant feedback channel collapses it into the FSM-projected card already covered by S-13..S-15."; }
        part removeDiagnoseButtonDoDR1 : TestResult { :>> id = "ae2c4f60-7d19-4083-b5e6-1f307a248d71"; :>> outcome = VerdictKind::pass; :>> judgedAgainst = "64708b4"; :>> judgedAt = "2026-08-02"; :>> judgedBy = "claudeOpus"; }
        // The owner's DESIGN CHOICE (confirmation) — remove over upgrade; their word is the evidence.
        verification removeDiagnoseButtonChoice : Test { :>> id = "bf3d5071-8e2a-4194-c6f7-20418b359e82"; :>> method = VerificationMethod::confirmation; :>> procedureText = "The owner reported the diagnostic's false all-clear ('always says everything is fine even if it's not working') and, when offered a heavier live-state+active-probe upgrade, redirected: 'might be totally unnecessary. consider just removing.' Shown the evidence that the honest status card already gives every actionable cause diagnose provided, the owner's direction was to REMOVE. This records ONLY that design-approach choice (their word is the evidence, D0016); it is NOT acceptance of the shipped RESULT — sittingReview20260802b covers the owner's review of 1.11.11."; }
        part removeDiagnoseButtonChoiceR1 : TestResult { :>> id = "c04e6182-9f3b-42a5-d708-31529c460f93"; :>> outcome = VerdictKind::pass; :>> judgedAgainst = "64708b4"; :>> judgedAt = "2026-08-02"; :>> judgedBy = "wweatherholtz"; }
        // REVIEW — the per-sitting human gate (D0049) for the 2026-08-01 sitting. PENDING owner confirmation:
        // the owner directed the critique + 'fix all 3 HIGHs', but that is direction to DO the work, NOT
        // acceptance of the COMPLETED fixes — so R1 is stamped only on the owner's explicit review of the
        // shipped 1.11.1 (confirmation-authenticity). Until then this gate is honestly open.
        verification sittingReview20260801 : Test { :>> id = "625e9b3a-efbc-499c-9449-108fb07cab13"; :>> method = VerificationMethod::confirmation; :>> procedureText = "Per-sitting human review (D0049) for the 2026-08-01 sitting. The owner asked for a critique pass; shown 3 verified HIGH findings + the Medium/Low backlog, the owner directed 'fix all 3 HIGHs now'. This gate covers the three fixes shipped in PATCH 1.11.1 — hotLoadPrivacyGateFreshCheck (hot-load RCE-gate bypass), reconcilePathReloginOnce (mid-session token-expiry false block), vaultKeyServerQualified (server-blind vault key) — plus the decision to backlog the lower-severity findings. The owner asked for an independent RE-VERIFICATION ('you check again please') and gave a PROVISIONAL acceptance ('I'll ok it for now'), explicitly to be revisited after their own hands-on device check. The re-verification was clean: fresh client vitest 531 pass; release 1.11.1 built from the fix commit 98a44a3 (workflow success, main.js published); all three fixes present + correct in committed source; keel validate + guard ALL PASS. R1 records that PROVISIONAL owner acceptance — NOT a hands-on device sign-off (which the owner has not yet done)."; }
        part sittingReview20260801R1 : TestResult { :>> id = "a4cd447a-d0a2-49c6-8a1c-6decd8813455"; :>> outcome = VerdictKind::pass; :>> judgedAgainst = "98a44a3"; :>> judgedAt = "2026-08-01"; :>> judgedBy = "wweatherholtz"; }
        // REVIEW — the per-sitting human gate (D0049) for the 2026-08-02 sitting. PENDING owner confirmation:
        // the owner directed 'proceed with the backlog' + chose ACCEPT-RISK on the S2 malicious-server
        // question, but directing the work + a scoped risk decision is not acceptance of the COMPLETED fixes —
        // R1 is stamped only on the owner's explicit review of the shipped 1.11.2 (confirmation-authenticity).
        verification sittingReview20260802 : Test { :>> id = "ca873ca6-8455-4d14-a920-76dd70c97eb6"; :>> method = VerificationMethod::confirmation; :>> procedureText = "Per-sitting human review (D0049) for the 2026-08-02 sitting. The owner directed 'let's proceed with the backlog' and, on the one item that was genuinely their call, chose ACCEPT-RISK for the S2 malicious-server threat ('Accept the risk (trust your server)'). This gate covers the four backlog fixes shipped in PATCH 1.11.2 — critiqueBacklogFsm (F2/F3/F5), critiqueBacklogTimestamp (T1/T2/T4; T3 accepted), critiqueBacklogVault (V2; V3 accepted), critiqueBacklogSecurity (S3 + the S2 accept-risk) — closing all four backlog Issues, plus the newly-logged issueMfaLoginUnsupported (feature gap, not built). ALSO covers the mid-sitting field bugs the owner reported + the exercises they directed: the status-display family shipped 1.11.3-1.11.7 (statusDisplayPureProjection, switchAbortOnOutage, connectPhaseNoOptimisticFlip, switchReportsProgress, resumeReattemptsConnection — spec + independent critique + STPA deepening); the functional-decoupling of the connection subsystem (behavior-preserving, no releases) + the STPA L-5 deepening (D0036); the STPA-UCA HUNT that FOUND + fixed an unshipped L-1 data-loss bug (switchUploadProbeGuard, 1.11.8); and cssTrustGate (1.11.9, the CSS trust gate the owner directed 'close css gap'). The owner SIGNED OFF ('close css gap, and signed off. continue') — an explicit acceptance of the sitting's completed + released content (through 1.11.9), given after seeing the honest reports. Single human confirmation gate for the sitting; closeOut/retro autonomous."; }
        part sittingReview20260802R1 : TestResult { :>> id = "ae0a2df4-69e4-4591-a0f0-9179cfb388d4"; :>> outcome = VerdictKind::pass; :>> judgedAgainst = "059830d"; :>> judgedAt = "2026-08-02"; :>> judgedBy = "wweatherholtz"; }
        // REVIEW — the per-sitting human gate (D0049) for the post-1.11.9 continuation. HONESTLY PENDING: the
        // owner CHOSE the delete-CAS design (AskUserQuestion) but has NOT yet reviewed the shipped 1.11.10 —
        // so this gate carries NO passing R1 (confirmation-authenticity: a design-approach pick is not
        // acceptance of the shipped result). The design choice itself is recorded in deleteRemoteCasGuardChoice.
        verification sittingReview20260802b : Test { :>> id = "8b2e5d64-7fa1-4235-eb06-d149c2357f8a"; :>> method = VerificationMethod::confirmation; :>> procedureText = "Per-sitting human review (D0049) for the post-1.11.9 continuation. After signing off through 1.11.9 the owner directed 'continue'; an STPA-UCA hunt on the SERVER found an L-1 lost-update — DELETE lacked commit's optimistic-concurrency (CAS) guard, so a stale delete could silently discard a concurrent edit fleet-wide — and the owner CHOSE the CAS-guard fix via an explicit AskUserQuestion. This gate covers deleteRemoteCasGuard (1.11.10 — server + client) and the backlog-logged issueMirrorWriteNotSelfHealed (LOW, not built); it ALSO covers removeDiagnoseButton (1.11.11) — the owner reported the 'Diagnose' button's false all-clear and directed 'consider just removing' it, and it was removed so the honest FSM-projected status card is the single source of truth (removeDiagnoseButtonChoice records that owner direction). The owner SIGNED OFF ('signed off. proceed') on 2026-08-02 after redeploying the server image (delete-CAS live) and having the chance to check both on-device — an explicit acceptance of the sitting's shipped content (1.11.10 + 1.11.11). Single human confirmation gate for the sitting; closeOut/retro autonomous."; }
        part sittingReview20260802bR1 : TestResult { :>> id = "d9e1f072-3a4b-4c85-9e60-1b2c3d4e5f60"; :>> outcome = VerdictKind::pass; :>> judgedAgainst = "c2523ec"; :>> judgedAt = "2026-08-02"; :>> judgedBy = "wweatherholtz"; }
        // ===== Sprint connectPhaseVisibility (2026-08-02) — 1.12.0: surface the connect sub-phases + timed
        // log so 'Connecting…' stops reading as hung (owner-reported L-5). =====
        action connectPhaseVisibility;
        verification connectPhaseVisibilityDoD : Test { :>> id = "1a6b3c80-5d4e-4f92-b7a1-0c8e29f45d63"; :>> method = VerificationMethod::test; :>> procedureText = "Ships MINOR 1.12.0 (new user-facing capability; client-only, NO server redeploy). Owner-reported (field): the status hung on 'connecting' with no insight — the log showed a 36s gap between 'connecting to ...' and 'config sync on — syncing 38 files'. doConnect runs THREE phases all labeled 'Connecting…' with no logging between them: establishSession (token -> status() 30s-timeout round-trip -> version -> refreshShareGrant), reconcileAll (fetch the full remote manifest via changes(0) THEN list+hash every local file — so the 36s of silence was establishSession + the manifest fetch, before the local scan started), finishConnect (WS + poll). FIX: a reconcile onStage hook (ReconcileDeps.onStage) fires the coarse sub-phases (fetching changes from the server -> scanning local files -> reconciling N local files); doConnect + establishSession add the earlier stages (signing in / checking the server / checking your access) and a 'finishing up'; a connect-gated setConnectStage names the current sub-phase as the 'Connecting…' DETAIL (paintLight's tip + the settings card, label stays the pure FSM projection) AND logs each with cumulative elapsed. Gated on a `connecting` flag so a poll/remote reconcile (which also fires onStage) never logs or paints a stage. So the next connect shows WHERE it is + times each phase, locating a stall instead of an opaque 'Connecting…'. Guards (fail-first): reconcile.test 'fires onStage in order: fetching changes -> scanning local files -> reconciling N' + 'no-op when onStage is not wired'; plugin-wiring 'surfaces the live connect sub-phase as the Connecting… detail, cleared after connect'. DoD: full client vitest (555) + tsc clean + esbuild build clean + keel validate/guard green. Resolves issueConnectStatusOpaque. Realizes SR-25 for the connect feedback loop (STPA S-19)."; }
        part connectPhaseVisibilityDoDR1 : TestResult { :>> id = "2b7c4d91-6e5f-40a3-c8b2-1d9e30056e74"; :>> outcome = VerdictKind::pass; :>> judgedAgainst = "34db694"; :>> judgedAt = "2026-08-02"; :>> judgedBy = "claudeOpus"; }
        // REVIEW — the per-sitting human gate (D0049) for the connect-visibility work. HONESTLY PENDING: the
        // owner directed the fix but has NOT yet seen 1.12.0 on-device (they'll watch the sub-phases + timing
        // on the next connect) — no passing R1 until that explicit review.
        verification sittingReview20260802c : Test { :>> id = "3c8d5e02-7f60-4194-d9c3-2e0f41167f85"; :>> method = VerificationMethod::confirmation; :>> procedureText = "Per-sitting human review (D0049) for the connect-visibility continuation. The owner reported the plugin hanging on 'connecting' with no insight ('surely connecting has multiple phases?') and, shown the phase map + that the 36s was establishSession + the remote-manifest fetch (before the local scan), directed 'Status sub-phases + timed log'. This gate covers connectPhaseVisibility (1.12.0). HONESTLY PENDING: the owner has NOT yet reviewed the shipped 1.12.0 on their device (the payoff is visible on the NEXT connect — the named sub-phases + per-phase timing that locate the 36s); R1 is stamped only on that explicit review."; }
        // ===== Sprint streamedPullRacingEditGuard (2026-08-02) — 1.12.1: close SR-2's accepted streamed-pull
        // residual (a mid-stream local edit lost on a >=8 MiB pull, L-1). Found by the chunking STPA-hunt. =====
        action streamedPullRacingEditGuard;
        verification streamedPullRacingEditGuardDoD : Test { :>> id = "4d9e2b70-6c81-4f35-a2c6-1e0f39a57b48"; :>> method = VerificationMethod::test; :>> procedureText = "Ships PATCH 1.12.1 (DATA-INTEGRITY, L-1; client-only, NO server redeploy). The client chunking/reassembly STPA-UCA hunt (independent critic) found the one real unrecoverable-loss window in the subsystem: applyPull's streamed branch (rmeta.size >= 8 MiB) checked for a racing local edit BEFORE streaming, then streamFileToDisk reassembled to a temp + atomic-renamed over `path` in close() with NO seam re-check — so an edit saved DURING the multi-second download was clobbered and base set to remote (next reconcile: local==base==in-sync -> edit gone). The buffered path (< 8 MiB notes) already re-checks after the fetch; this was the asymmetry, and EXACTLY SR-2's documented 'Residual (accepted): sub-window TOCTOU on very large streamed pulls'. The owner chose to fix (streamedPullRacingEditGuardChoice). FIX: streamFileToDisk gains a beforeRename hook (after the incremental hash-verify, before close()'s rename); applyPull passes a seam guard reusing conflictCopyIfRaced on the ORIGINAL on-disk file (still holds the racing edit — NOT the post-rename result, so base is only ever rmeta.hash; this is why the retired 'post-write re-read' regressed and this doesn't). A >8 MiB config race throws StreamRaceAbort -> adjudicate, never overwrite. An independent critic (SOUND-WITH-CHANGES) caught a follow-on hole -> the fix does NOT delete the seam copy on a post-beforeRename failure (a post-rename close() throw would leave the copy the SOLE surviving edit), plus a close()-must-never-throw-after-rename contract. Guards (fail-first): reconcile.test 'preserves a mid-stream local edit as a conflict copy', 'makes NO spurious copy when there is no racing edit', 'a >8 MiB CONFIG file edited mid-stream ABORTS (adjudicate)', 'a close() failure AFTER the rename does NOT delete the sole surviving racing edit'. DoD: full client vitest (559) + tsc clean + esbuild build clean + keel validate/guard green. Resolves issueStreamedPullMidEditLoss; closes SR-2's streamed-pull residual (STPA S-3 / UCA-4)."; }
        part streamedPullRacingEditGuardDoDR1 : TestResult { :>> id = "5e0f3c81-7d92-4046-b3d7-2f1a40b68c59"; :>> outcome = VerdictKind::pass; :>> judgedAgainst = "a347bf8"; :>> judgedAt = "2026-08-02"; :>> judgedBy = "claudeOpus"; }
        // The owner's DESIGN CHOICE (confirmation) — fix over accept-the-residual; their word is the evidence.
        verification streamedPullRacingEditGuardChoice : Test { :>> id = "6f1a4d92-8e03-4157-c4e8-30256bc79d6a"; :>> method = VerificationMethod::confirmation; :>> procedureText = "The owner was shown the VERIFIED finding — a mid-stream local edit unrecoverably lost on a >=8 MiB streamed pull, the buffered path already safe, the window narrow + currently an accepted residual, closable but in a seam that regressed once — and chose 'Fix it (careful spec + critique + TDD)' over 'Keep the accepted residual' and 'Write the diff for review first', via an explicit AskUserQuestion on 2026-08-02. This records ONLY that design-approach choice (their word is the evidence, D0016); it is NOT acceptance of the shipped RESULT — sittingReview20260802d covers the owner's review of 1.12.1."; }
        part streamedPullRacingEditGuardChoiceR1 : TestResult { :>> id = "7a2b5e03-9f14-4268-d5f9-41367cd8ae7b"; :>> outcome = VerdictKind::pass; :>> judgedAgainst = "a347bf8"; :>> judgedAt = "2026-08-02"; :>> judgedBy = "wweatherholtz"; }
        // REVIEW — the per-sitting human gate (D0049) for the stream-race fix. HONESTLY PENDING: the owner
        // chose the fix but has NOT reviewed the shipped 1.12.1 (a data-integrity fix they can't easily see) —
        // no passing R1 until that explicit review.
        verification sittingReview20260802d : Test { :>> id = "8b3c6f14-a025-4379-e6a0-52478de9bf8c"; :>> method = VerificationMethod::confirmation; :>> procedureText = "Per-sitting human review (D0049) for the stream-race fix. The client chunking/reassembly STPA-hunt found a mid-stream local-edit loss on >=8 MiB streamed pulls (SR-2's accepted residual); shown it, the owner chose 'Fix it (careful spec + critique + TDD)'. Done as spec -> independent critique (SOUND-WITH-CHANGES, caught the orphan-cleanup hole) -> fail-first TDD. This gate covers streamedPullRacingEditGuard (1.12.1). HONESTLY PENDING: the owner has NOT reviewed the shipped 1.12.1 result (design-approach choice recorded in streamedPullRacingEditGuardChoice); R1 stamped only on that explicit review."; }
        // ===== Sprint persistScanSkipHint (2026-08-02) — 1.12.2: persist the (size,mtime) scan-skip hint so a
        // plugin reload doesn't re-hash the whole vault (owner field report; reverses R15 sync#3). =====
        action persistScanSkipHint;
        verification persistScanSkipHintDoD : Test { :>> id = "5e0a3c81-7d92-4f46-b3d8-2f1a40c67b59"; :>> method = VerificationMethod::test; :>> procedureText = "Ships PATCH 1.12.2 (perf/UX; client-only, NO server redeploy). Owner-reported via the 1.12.0 connect timing: every fresh 'plugin loaded' re-reads+re-hashes the whole vault (~1137 files) on the first connect though nothing changed. Cause: BaseStore.toJSON persisted only hash/text/normHash, DROPPING the (size,mtime) scan-skip hint (R15 sync#3, 'never let a perf hint outlive its verifying session'), so a reload had no stamps and reconcileOne re-hashed every file. OWNER DECISION (AskUserQuestion 'Persist the scan-skip hints', recorded in persistScanSkipHintChoice): persist size+mtime. FIX (minimal): toJSON emits size+mtime (the constructor already loads them; main.ts already round-trips base.toJSON through saveData/loadData) -> baseStatUnchanged matches on reload -> the read+SHA-256 is skipped for unchanged files. Independent critic verdict SOUND (no data-loss path): under a scan-hit decide() can only return in-sync or pull (every destructive action needs L!=B, but the scan-hit pins L=B); the one mutating path (pull) re-reads live in applyPull->conflictCopyIfRaced, so even a LYING stamp colliding with a remote change writes a conflict copy, never a silent overwrite; remote changes are detected via the manifest regardless. Accepted (widened) residual: a mtime-preserving out-of-band edit isn't re-hashed until the next edit event / size|mtime change / remote divergence (the reload full-rehash backstop is removed) — a DELAY, never loss. Guards (fail-first): base.test 'PERSISTS the (size,mtime) scan-skip hint through toJSON/reload'; reconcile T2/T5 'an unchanged file skips the read AND does nothing', T3 'a STALE stamp does NOT mask a changed file', T4 (safety) 'a LYING stamp colliding with a remote change makes a CONFLICT COPY, never a silent overwrite', T6 'a persisted stamp for an ABSENT local file does NOT mask the deletion'; + a main.ts mtime-source-parity invariant comment (T7). DoD: full client vitest (563) + tsc clean + esbuild build clean + keel validate/guard green. Resolves issueScanSkipHintNotPersisted. (The ~18s .obsidian config-tree walk + the every-connect token re-login surfaced by the same log are SEPARATE, not in this sprint.)"; }
        part persistScanSkipHintDoDR1 : TestResult { :>> id = "6f1b4d92-8e03-4057-c4e9-30251bd78c6a"; :>> outcome = VerdictKind::pass; :>> judgedAgainst = "ab7e47e"; :>> judgedAt = "2026-08-02"; :>> judgedBy = "claudeOpus"; }
        // The owner's DESIGN CHOICE (confirmation) — persist over keep-dropping; their word is the evidence.
        verification persistScanSkipHintChoice : Test { :>> id = "7a2c5e03-9f14-4168-d5fa-41362ce89d7b"; :>> method = VerificationMethod::confirmation; :>> procedureText = "Shown that the whole-vault re-hash on every reload is because the (size,mtime) scan-skip hint is deliberately not persisted, and the tradeoff of persisting it (the accepted rsync/Syncthing residual, now spanning restarts), the owner chose 'Persist the scan-skip hints' over 'Chase the 18s config-tree walk instead' and 'Just fix the label + look at the token', via an explicit AskUserQuestion on 2026-08-02. This records ONLY that design-approach choice (their word is the evidence, D0016) — reversing R15 sync#3; it is NOT acceptance of the shipped RESULT (sittingReview20260802e)."; }
        part persistScanSkipHintChoiceR1 : TestResult { :>> id = "8b3d6f14-a025-4279-e6ab-52473def9c8d"; :>> outcome = VerdictKind::pass; :>> judgedAgainst = "ab7e47e"; :>> judgedAt = "2026-08-02"; :>> judgedBy = "wweatherholtz"; }
        // REVIEW — the per-sitting human gate (D0049) for the persist-scan-skip fix. HONESTLY PENDING: the owner
        // chose the fix but has NOT seen 1.12.2 on-device (the payoff shows on the NEXT reload — a cheap connect
        // instead of re-hashing ~1137 files) — no passing R1 until that explicit review.
        verification sittingReview20260802e : Test { :>> id = "9c4d7015-b136-4380-f7bc-63584efa0d9e"; :>> method = VerificationMethod::confirmation; :>> procedureText = "Per-sitting human review (D0049) for the persist-scan-skip fix. From the 1.12.0 connect log the owner saw the plugin re-reconciling ~1137 files on every reload with nothing changed; shown the cause (the scan-skip hint isn't persisted) + the tradeoff, the owner directed 'Persist the scan-skip hints'. Done as spec -> independent critique (SOUND — confirmed the conflict-copy re-read rules out data loss, required the T4-T7 safety tests) -> fail-first TDD. This gate covers persistScanSkipHint (1.12.2). HONESTLY PENDING: the owner has NOT reviewed the shipped 1.12.2 on-device (the payoff is the NEXT reload being cheap); R1 stamped only on that explicit review."; }
        // ===== Sprint tokenIdleDefaultOff (2026-08-02) — 1.12.3: make the server session idle-timeout default-OFF
        // so the plugin stops re-logging in on every reopen after a break (owner field report). SERVER change. =====
        action tokenIdleDefaultOff;
        verification tokenIdleDefaultOffDoD : Test { :>> id = "6e1b4d92-8f03-4157-c4e9-30251be89d7c"; :>> method = VerificationMethod::test; :>> procedureText = "Ships PATCH 1.12.3 (SERVER — the self-hosted server image MUST be redeployed to take effect; the plugin re-release is a no-op, client unchanged). Owner-reported via the 1.12.0 connect log: 'token rejected — re-logging in' on connect. Cause: the server's persisted bearer tokens (survive restart) carry a 30-day absolute cap AND an IDLE timeout (AC.3.1.11) that DEFAULTED to 30 min — a device closed/not-syncing for >30 min idle-expires, so the next open 401s + the client auto-relogins. OWNER DECISION (AskUserQuestion 'Default to the 30-day absolute cap (no idle expiry)', recorded in tokenIdleDefaultOffChoice): default idle expiry OFF. FIX: tokens.rs DEFAULT_IDLE_TTL_SECS 30*60 -> 0 (idle off; token lives its full 30-day absolute cap + revoke/password-change). The control REMAINS available — a compliance-seeking operator opts in via SESSION_IDLE_TIMEOUT_SECS=<positive>. COMPLIANCE reconciled honestly (D0098 — not silently): NIST 800-171 3.1.11 disposition partial->operator (opt-in) + 3.13.9's inactivity clause; docs/cmmc-posture.md + docs/deployment.md doc-synced (default-off + how to opt in). Guards (fail-first): server tokens.rs default_has_no_idle_expiry_only_the_absolute_cap (locks the new default: a long-idle token still resolves, the absolute cap still expires it) + idle_expires_a_stale_token_but_keeps_an_active_one (the control WHEN opted-in). DoD: full server cargo test (all suites 0 failed) + clippy clean + keel validate/guard green. Resolves issueTokenIdleReloginFriction. (The ~18s .obsidian config-tree walk from the same log is the NEXT sprint, owner 'then the other'.)"; }
        part tokenIdleDefaultOffDoDR1 : TestResult { :>> id = "7a2c5e03-9f14-4268-d5fa-41362cf89d8b"; :>> outcome = VerdictKind::pass; :>> judgedAgainst = "f7f7d05"; :>> judgedAt = "2026-08-02"; :>> judgedBy = "claudeOpus"; }
        // The owner's DESIGN CHOICE (confirmation) — default idle off over keep-30-min; their word is the evidence.
        verification tokenIdleDefaultOffChoice : Test { :>> id = "8b3d6f14-a025-4379-e6ab-52473def9c8e"; :>> method = VerificationMethod::confirmation; :>> procedureText = "Shown that the connect re-login is a 30-min session idle-timeout (AC.3.1.11) and the security-vs-convenience tradeoff, the owner chose 'Default to the 30-day absolute cap (no idle expiry)' over 'A longer idle default (7 days)' and 'Leave the default, just document the env var', via an explicit AskUserQuestion on 2026-08-02. This records ONLY that design-approach choice (their word is the evidence, D0016) — relaxing the out-of-box idle control (kept opt-in via SESSION_IDLE_TIMEOUT_SECS); it is NOT acceptance of the shipped RESULT (sittingReview20260802f)."; }
        part tokenIdleDefaultOffChoiceR1 : TestResult { :>> id = "9c4e7015-b136-4480-f7bd-63584efb0da0"; :>> outcome = VerdictKind::pass; :>> judgedAgainst = "f7f7d05"; :>> judgedAt = "2026-08-02"; :>> judgedBy = "wweatherholtz"; }
        // REVIEW — the per-sitting human gate (D0049) for the token + (upcoming) config-walk batch the owner
        // directed together ('fix the token one first, then the other'). HONESTLY PENDING: the owner chose the
        // fix but has NOT seen 1.12.3 on-device (+ hasn't redeployed the server) — no passing R1 until that review.
        verification sittingReview20260802f : Test { :>> id = "ad5e8016-c247-4491-08cd-74695afc1eb0"; :>> method = VerificationMethod::confirmation; :>> procedureText = "Per-sitting human review (D0049) for the token-idle + config-walk batch (owner: 'fix the token one first, then the other'). Covers tokenIdleDefaultOff (1.12.3 — server session idle-timeout default-off; the owner chose 'Default to the 30-day absolute cap', recorded in tokenIdleDefaultOffChoice) AND configWalkParallel (1.12.4 — the ~18s .obsidian config-tree walk parallelized under a bounded cap). HONESTLY PENDING: the owner has NOT reviewed the shipped 1.12.3/1.12.4 (nor redeployed the server, which the token fix requires); R1 stamped only on that explicit review."; }
        // ===== Sprint configWalkParallel (2026-08-02) — 1.12.4: parallelize the .obsidian config-tree walk
        // (the ~18s 'scanning local files' phase) under a bounded cap. Owner directed ('then the other'). =====
        action configWalkParallel;
        verification configWalkParallelDoD : Test { :>> id = "7f2c5e14-9a03-4268-b5da-41362cf89e8c"; :>> method = VerificationMethod::test; :>> procedureText = "Ships PATCH 1.12.4 (perf; client-only, NO server redeploy). Owner-reported via the 1.12.0 connect timing: the 'scanning local files' phase took ~18s. Cause: ObsidianVaultIo.enumerateConfig walked the .obsidian tree FULLY SEQUENTIALLY (one awaited adapter.list/stat at a time, depth-first), so the wall-clock was (call COUNT x per-call latency) — brutal on a mobile latency-bound adapter, every reconcile. Owner directed the fix ('then the other'). FIX: extract the walk into a pure, unit-tested configwalk.ts (walkConfigTree) that runs adapter.list/stat CONCURRENTLY under a GLOBAL concurrency cap (CONFIG_ENUM_CONCURRENCY=12, a counting semaphore — a per-call mapPool can't bound a recursive walk), collapsing wall-clock toward (tree DEPTH x latency). Behavior-preserving + read-only: the SAME passing-file set (order-independent), an unlistable dir SKIPPED not treated-as-empty (+ logged; reconcile's per-file probe still guards a false delete), and a slow walk logs its shape ('config scan: N folders + M files in Xs') so the win is measurable on the next connect. Guards (configwalk.test): finds every passing file across a nested tree; respects the passes filter; a list error skips only that subtree + continues; NEVER exceeds the cap (peak<=limit) yet DID parallelize (peak>1); empty tree. DoD: full client vitest (566) + tsc clean + esbuild build clean + keel validate/guard green. Resolves issueConfigWalkSlow."; }
        part configWalkParallelDoDR1 : TestResult { :>> id = "8a3d6f25-ab14-4379-c6eb-52473df9af9d"; :>> outcome = VerdictKind::pass; :>> judgedAgainst = "d4cdd32"; :>> judgedAt = "2026-08-02"; :>> judgedBy = "claudeOpus"; }
        // ===== Sprint reconcileExamProgress (2026-08-02) — 1.12.5: honest 'checking N' label + live progress
        // for the connect examination (owner: 'says reconciling but not doing anything' / 'stuck on label'). =====
        action reconcileExamProgress;
        verification reconcileExamProgressDoD : Test { :>> id = "9b4d7136-ac15-4380-c6ec-52473e0abfad"; :>> method = VerificationMethod::test; :>> procedureText = "Ships PATCH 1.12.5 (UX + DIAGNOSTIC; client-only, NO server redeploy). Owner-reported (field): the connect showed 'reconciling 1137 local file(s)' and appeared idle ('says reconciling but not doing anything'), then 'stuck on label'. Two issues: (1) the 1.12.0 sub-phase label 'reconciling N' read as 'syncing N' when the pass EXAMINES all files + transfers only what changed; (2) it was STATIC, so a slow full pass (a first-run re-hash before the 1.12.2 scan-skip stamps persist, or a large mobile vault) looked frozen and a hang was indistinguishable from slow. FIX: (a) honest label 'checking N files for changes' (real transfer work still shows as 'Syncing… N pending' via onProgress); (b) LIVE 'checked X/N files' progress (every 250 examined) so a slow pass shows MOVEMENT and a genuine hang is PINPOINTED (the count freezes at the stuck file). This is a UX + diagnostic fix — if the stall is a HARD hang (not a one-time slow re-hash that completes + persists stamps -> fast thereafter), the frozen count locates it for a targeted follow-up. Guards: reconcile.test onStage sequence updated (fetching -> scanning -> 'checking N files for changes'). DoD: full client vitest (566) + tsc clean + esbuild build clean + keel validate/guard green. Resolves issueReconcileExamOpaque."; }
        part reconcileExamProgressDoDR1 : TestResult { :>> id = "ac5e8247-bd16-4491-08cd-63584f0bcfbe"; :>> outcome = VerdictKind::pass; :>> judgedAgainst = "918974e"; :>> judgedAt = "2026-08-02"; :>> judgedBy = "claudeOpus"; }
        // ===== Sprint removePluginServerButton (2026-08-02) — 1.12.5: remove the per-plugin 'Remove from
        // server' button (owner: 'taking up far too much space for a rare need'). =====
        action removePluginServerButton;
        verification removePluginServerButtonDoD : Test { :>> id = "ad6f9358-ce27-45a2-19de-74695f1cd0cf"; :>> method = VerificationMethod::inspect; :>> procedureText = "Ships PATCH 1.12.5 (UI declutter; client-only). Owner-directed: 'get rid of the Remove from server button ... if the owner wants to remove packages, they can do so in the admin interface ... taking up far too much space for a rare need.' The settings plugin list rendered a 'Remove from server' button on EVERY server-present plugin row (settings.ts renderPluginRows) — a button per row for a rare, admin-appropriate need. FIX: remove the per-row button + its confirm/purge onClick. The plugin's removePluginFromServer method STAYS (still tested — plugin-wiring 'purges ONLY that plugin's server files' + 'REJECTS a traversal/malformed id'), just not surfaced as per-row UI. Verified by INSPECTION (a UI-space removal): tsc clean (no orphaned refs — onServer/manifests/confirmModal all used elsewhere), no test asserted the button, full client vitest (566) + DOM suites green. Resolves issuePluginRemoveButtonClutter."; }
        part removePluginServerButtonDoDR1 : TestResult { :>> id = "be7a0469-df38-4033-2aef-857a601de0d0"; :>> outcome = VerdictKind::pass; :>> judgedAgainst = "918974e"; :>> judgedAt = "2026-08-02"; :>> judgedBy = "claudeOpus"; }
        // REVIEW — the per-sitting human gate (D0049) for the 1.12.5 batch (label/progress + button declutter).
        // HONESTLY PENDING the owner's on-device review of 1.12.5.
        verification sittingReview20260802g : Test { :>> id = "bf8b157a-e049-4144-3bf0-968b712ef1e1"; :>> method = VerificationMethod::confirmation; :>> procedureText = "Per-sitting human review (D0049) for the 1.12.5 batch. Covers reconcileExamProgress (the owner reported 'says reconciling but not doing anything' / 'stuck on label' -> honest 'checking N' label + live progress; a UX + diagnostic fix) and removePluginServerButton (the owner directed removing the per-plugin 'Remove from server' button as clutter). HONESTLY PENDING: the owner has NOT reviewed the shipped 1.12.5 on-device; R1 stamped only on that explicit review — AND the reconcile-stall root cause (slow re-hash vs hard hang) is only DIAGNOSED by this change, not yet confirmed fixed (awaits the owner's next connect log)."; }
        // Owner sign-off 2026-08-03 ('reviewed and looks good') — explicit acceptance of the shipped content
        // of reviews c–g (1.12.0–1.12.6), after living with it on-device (incl. the connect logs that
        // CONFIRMED the reconcile stall was a one-time re-hash that completes, resolving g's open caveat).
        part sittingReview20260802cR1 : TestResult { :>> id = "e2b91741-9357-4a05-b6ca-0d4f3c2b7052"; :>> outcome = VerdictKind::pass; :>> judgedAgainst = "62b8a03"; :>> judgedAt = "2026-08-03"; :>> judgedBy = "wweatherholtz"; }
        part sittingReview20260802dR1 : TestResult { :>> id = "f3ca2852-a468-4b16-c7db-1e503d3c8163"; :>> outcome = VerdictKind::pass; :>> judgedAgainst = "62b8a03"; :>> judgedAt = "2026-08-03"; :>> judgedBy = "wweatherholtz"; }
        part sittingReview20260802eR1 : TestResult { :>> id = "04db3963-b579-4c27-d8ec-2f614e4d9274"; :>> outcome = VerdictKind::pass; :>> judgedAgainst = "62b8a03"; :>> judgedAt = "2026-08-03"; :>> judgedBy = "wweatherholtz"; }
        part sittingReview20260802fR1 : TestResult { :>> id = "15ec4a74-c68a-4d38-e9fd-30725f5ea385"; :>> outcome = VerdictKind::pass; :>> judgedAgainst = "62b8a03"; :>> judgedAt = "2026-08-03"; :>> judgedBy = "wweatherholtz"; }
        part sittingReview20260802gR1 : TestResult { :>> id = "260d5b85-d79b-4e49-fa0e-41836a6fb496"; :>> outcome = VerdictKind::pass; :>> judgedAgainst = "62b8a03"; :>> judgedAt = "2026-08-03"; :>> judgedBy = "wweatherholtz"; }
        // ===== Sprint wsSupersededGuard (2026-08-02) — 1.12.6: the WS-push STPA-UCA hunt's one real bug — the
        // open/error handlers lacked the superseded-socket identity guard that close has. =====
        action wsSupersededGuard;
        verification wsSupersededGuardDoD : Test { :>> id = "cf9c268b-f047-4144-3bf1-069c823f02f2"; :>> method = VerificationMethod::test; :>> procedureText = "Ships PATCH 1.12.6 (client-only, NO server redeploy). An independent STPA-UCA hunt on the WS push path (server + client) found this ONE real defect (Medium): spinUpWs's `open`/`error` handlers lacked the `this.ws !== ws` superseded-socket guard that `close` + the liveness tick already apply — the FSM's own design (transportstate.ts:7) requires ALL socket events to honor it. So a late `error` from a SUPERSEDED old socket degraded the CURRENT live socket (realtimeConnected->false, yellow 'Synced (polling)' instead of green, poll pinned to 4s -> battery, no self-heal until the next socket cycle). Safe direction (no missed changes / no false-synced -> Medium), a clear asymmetric-guard bug. FIX: add the identity guard to both open + error, matching close. Guard (fail-first): plugin-wiring 'a SUPERSEDED WS socket's late open/error does NOT disturb the current live socket' (the harness fake WS made fireable). DoD: full client vitest (567) + tsc clean + esbuild build clean + keel validate/guard green. Resolves issueWsSupersededOpenError. HUNT RESULT: the WS path is otherwise well-defended — server side NULL on auth/isolation(per-vault channel, no cross-tenant leak)/notify/revoke(re-authed before every delivery)/bounds/close; client side NULL on token-handling/close-recovery/message-flood/false-live. The only other items are a LOW server defense-in-depth (issueWsSessionAliveMustChange, backlogged) + accepted tradeoffs (per-delivery re-auth amplification; a bounded transient false-green; a negligible shared lastWsActivity) — not defects."; }
        part wsSupersededGuardDoDR1 : TestResult { :>> id = "d0ad379c-0158-4255-4c02-17ad934013a3"; :>> outcome = VerdictKind::pass; :>> judgedAgainst = "0d02f1e"; :>> judgedAt = "2026-08-02"; :>> judgedBy = "claudeOpus"; }
        // Backlog stub (server WS-hunt LOW / defense-in-depth, issueWsSessionAliveMustChange) — add must_change
        // to session_alive so the per-delivery liveness check is self-contained. NOT started (needs a server
        // redeploy; not exploitable — every must_change path already revokes tokens, which session_alive catches).
        action wsSessionAliveMustCheckBacklog;
        verification wsSessionAliveMustCheckBacklogDoD : Test { :>> id = "a1b2c3d4-1700-4a10-9b20-d1700c0de019"; :>> method = VerificationMethod::test; :>> procedureText = "Ships with 1.17.0 (server; redeploy). The WS per-delivery liveness re-check (ws.rs session_alive) now also asserts !users.must_change(user) (fail-closed on a poisoned lock), so a must-change account's live socket tears down through the must_change dimension ITSELF — self-contained defense-in-depth, no longer merely transitive through the paired token revocation. Critique: no new deadlock (session_alive holds no lock across the new users lock; no caller holds st.users), no wrongful teardown (normal accounts must_change=false). Guard: ws::tests::ws_session_dies_when_the_account_is_flagged_must_change + clippy. Resolves issueWsSessionAliveMustChange."; }
        part wsSessionAliveMustCheckBacklogDoDR1 : TestResult { :>> id = "a1b2c3d4-1700-4a10-9b20-d1700c0de020"; :>> outcome = VerdictKind::pass; :>> judgedAgainst = "b997a63"; :>> judgedAt = "2026-08-05"; :>> judgedBy = "claudeOpus"; }
        // ===== Sprint timestampSettingsUx (2026-08-03) — 1.12.7: declutter the timestamp settings + turn the
        // ignored-date-fields textarea into a validated add/remove list (owner: prevent errors). =====
        action timestampSettingsUx;
        verification timestampSettingsUxDoD : Test { :>> id = "28fb6ca7-5024-4e91-c7b3-16ad04f13ba4"; :>> method = VerificationMethod::test; :>> procedureText = "Ships PATCH 1.12.7 (UX; client-only, NO server redeploy). Owner-directed: 'revisit the timestamp area UX — descriptions way too verbose, and the date field identification should be an array input, not a huge text field; we try and prevent errors.' FIX (renderIgnoreTimestamps): (1) all three descriptions tightened to one short line; (2) the 'Ignored date fields' 5-row TEXTAREA replaced with a validated ADD-a-row LIST (each key a row + Remove; an 'Add a date field' input + 'Add field' button gated by a new pure validateTimestampKey in frontmatter.ts that rejects empty / ':' / unmatchable / case-insensitive-duplicate keys with a short Notice — errors PREVENTED, not silently accepted); (3) a 'Restore default date fields' safety shown only when the list drifts (the old textarea's implicit empty->defaults, now explicit). No reconcile-semantics change (same s.ignoredTimestampKeys + saveSettings). Guards (fail-first for the validator): frontmatter.test 'validateTimestampKey' (accepts default shapes/wildcards/spaced keys, trims, rejects empty/colon/junk/case-dup); settings-ui.dom 'date fields are a validated add/remove LIST' + 'an INVALID or DUPLICATE date field is REJECTED'. DoD: full client vitest (573) + tsc clean + esbuild build clean + keel validate/guard green. Resolves issueTimestampSettingsVerboseUx."; }
        part timestampSettingsUxDoDR1 : TestResult { :>> id = "39ac7db8-6135-4a02-d8c4-27be15024cb5"; :>> outcome = VerdictKind::pass; :>> judgedAgainst = "8b0de36"; :>> judgedAt = "2026-08-03"; :>> judgedBy = "claudeOpus"; }
        // REVIEW — the per-sitting human gate (D0049) for 2026-08-03. HONESTLY PENDING the owner's on-device review of 1.12.7.
        // ===== Sprint settingsUxPolish (2026-08-03) — 1.12.8: little-X removes, a canonical collapsible
        // (setHeading + native chevron), Reconfigure/Disconnect moved up, brief store-password. =====
        action settingsUxPolish;
        verification settingsUxPolishDoD : Test { :>> id = "39ac7db8-6135-4b02-d8c4-27be15024cc6"; :>> method = VerificationMethod::test; :>> procedureText = "Ships PATCH 1.12.8 (UX; client-only, NO server redeploy). Owner-directed follow-up (+ mobile screenshot): (1) replace the huge per-row 'Remove' buttons on the date-field / excluded-folder lists with a little X (Obsidian's canonical addExtraButton().setIcon('x')); the lists are easily restorable so no warning; (2) make the Timestamp-changes section COLLAPSIBLE + default-collapsed; (3) fix the synced-plugin list's ORPHANED raw <details>-triangle collapse — the owner directed 'research canonical ways ... don't reinvent'; RESEARCH (Obsidian dev docs + API via context7): NO native collapsible-group API (SettingGroup v1.11.0 has addClass/addExtraButton/addSearch/addSetting/setHeading — no collapse), and setHeading() is the documented canonical section header; so the collapsible() helper is built from Obsidian's OWN components — Setting().setHeading() made clickable + a native lucide chevron via setIcon() + a body toggle (no custom disclosure widget) — used for BOTH the plugin list and the Timestamp section; (4) move Reconfigure/Disconnect from Advanced into fillStatus (top Connection group); (5) cut the store-password description to one line. Guards: settings-ui.dom 'the Timestamp changes section is a collapsible (default collapsed) that toggles on header click' + the existing add/remove-list tests (the little-X extra-button clicks through); obsidian-stub gained ExtraButtonComponent + addExtraButton. DoD: full client vitest (576) + tsc clean + esbuild build clean + keel validate/guard green. Resolves issueSettingsUxPolish."; }
        part settingsUxPolishDoDR1 : TestResult { :>> id = "4abd8ec9-7246-4c13-e9d6-38cf26135de7"; :>> outcome = VerdictKind::pass; :>> judgedAgainst = "79c403c"; :>> judgedAt = "2026-08-03"; :>> judgedBy = "claudeOpus"; }
        // ===== Sprint collapseHeaderFix (2026-08-03) — 1.12.9: the 1.12.8 collapse header didn't render as a
        // heading (setHeading without setName); fix to the canonical setName().setHeading(). =====
        action collapseHeaderFix;
        verification collapseHeaderFixDoD : Test { :>> id = "5bce9fda-8357-4c24-e9e8-49df26146ea9"; :>> method = VerificationMethod::test; :>> procedureText = "Ships PATCH 1.12.9 (UX; client-only, NO server redeploy). Owner-reported on 1.12.8 (screenshot): 'dropdown looks the same, not like a heading'. Cause: collapsible() called new Setting(c).setHeading() but built the label from a manual createSpan instead of setName(title), so Obsidian's heading styling (which targets .setting-item-name) never applied. FIX: use the canonical new Setting(c).setName(title).setHeading() (the documented section-heading), insert the native lucide chevron BEFORE the title (section-collapse convention), + a styles.css safety (.selfsync-collapse-header .setting-item-name { font-weight: 600 }) so it reads as a heading even on themes that render .setting-item-heading subtly. Guard: settings-ui.dom 'the Timestamp changes section is a collapsible (default collapsed) that toggles on header click' (header found by its heading TEXT + toggles). DoD: full client vitest (576) + tsc clean + esbuild build clean + keel validate/guard green. Resolves issueCollapseHeaderNotHeading."; }
        part collapseHeaderFixDoDR1 : TestResult { :>> id = "6cdf0aeb-9468-4d35-fae9-50ea37257fba"; :>> outcome = VerdictKind::pass; :>> judgedAgainst = "171160c"; :>> judgedAt = "2026-08-03"; :>> judgedBy = "claudeOpus"; }
        // ===== Sprint collapseHeaderGroupFix (2026-08-03) — 1.12.10: the 1.12.9 setName().setHeading() fix
        // was STILL too subtle on mobile themes (owner hard-restarted, confirmed 1.12.9 running, "looks the
        // same"); the real fix is to render the collapse header as a real SettingGroup heading. =====
        action collapseHeaderGroupFix;
        verification collapseHeaderGroupFixDoD : Test { :>> id = "8ef1024d-b68a-4f57-1b01-72fc59479b1c"; :>> method = VerificationMethod::test; :>> procedureText = "Ships PATCH 1.12.10 (UX; client-only, NO server redeploy). Owner-reported on 1.12.9 AFTER a hard restart (so 1.12.9 was running): the '7 synced' collapse still rendered as a small dim row, not a section heading. Cause: 1.12.8/1.12.9 used Setting().setHeading() — an inline heading ROW (.setting-item-heading) — whereas the prominent section headings the owner compares against ('Synced community plugins', 'Advanced') are SettingGroup headings, which mobile themes style far more prominently; no setName()/font-weight tweak could close the gap. FIX: render the collapsible() header as a real new SettingGroup(c).setHeading(title) — the SAME component as the other section headings, so it renders identically on every theme — and toggle the group's PUBLIC listEl (since Obsidian 1.11.0) as the body, rendering rows into it; the native lucide chevron is prepended to the heading, reached via listEl.previousElementSibling (public API, not an internal class name). styles.css: dropped the now-moot .selfsync-collapse-header font-weight override, kept only the chevron affordance. Guard: settings-ui.dom 'the Timestamp changes section is a collapsible ...' updated to find the SettingGroup heading + toggle its listEl (still green). DoD: full client vitest (576) + tsc clean + esbuild build clean + keel validate/guard green. Resolves issueCollapseStillNotHeadingMobile."; }
        part collapseHeaderGroupFixDoDR1 : TestResult { :>> id = "9f02135e-c79b-4068-2c12-83fd6a58a02d"; :>> outcome = VerdictKind::pass; :>> judgedAgainst = "0d2971d"; :>> judgedAt = "2026-08-03"; :>> judgedBy = "claudeOpus"; }
        // ===== D0037 (1.13.0) — share-links canonical + link onboarding; admin console rework.
        // SERVER REDEPLOY required. Two phases, both delivered @bc11f9c. =====
        action shareLinksCanonical;
        verification shareLinksCanonicalDoD : Test { :>> id = "a1b2c3d4-0037-4a10-9b20-d0037c0de001"; :>> method = VerificationMethod::test; :>> procedureText = "Ships part of MINOR 1.13.0 (D0037; SERVER IMAGE REDEPLOY required — server behavior changes). Phase 1 (admin console + server): retire the grantee-username grant path — remove POST /api/admin/shares (share_create) + GET /api/admin/usernames (its only consumer); KEEP DELETE /api/admin/shares (grant revoke — a redeemed link mints the same D0008 grant). Admin console (admin_ui.html): a SINGLE Sharing section (not per-vault) — vault dropdown + permission -> a copyable selfsync-share:// link whose server address is an EDITABLE field defaulting to location.origin (correct for split/proxied deploys, per critique); active (unredeemed) links + redeemed grants each revocable; registration open/closed is a real toggle switch (was a checkbox); each vault shows last_used (newest .sync-index.db server-side mtime, computed in spawn_blocking, no schema migration). Guards: server cargo test (admin 33 incl. owner_grants_and_revokes now via a redeemed link + owner_share_endpoints_reachable_on_public_surface) + clippy -D warnings + client vitest 577 + tsc clean. Realizes D0037."; }
        part shareLinksCanonicalDoDR1 : TestResult { :>> id = "a1b2c3d4-0037-4a10-9b20-d0037c0de002"; :>> outcome = VerdictKind::pass; :>> judgedAgainst = "bc11f9c"; :>> judgedAt = "2026-08-03"; :>> judgedBy = "claudeOpus"; }
        action shareLinkOnboarding;
        verification shareLinkOnboardingDoD : Test { :>> id = "a1b2c3d4-0037-4a10-9b20-d0037c0de003"; :>> method = VerificationMethod::test; :>> procedureText = "Ships part of MINOR 1.13.0 (D0037). Phase 2 (link onboarding — server + plugin): new PUBLIC POST /api/share-redeem-register { token, username, password } creates a brand-new account authorized BY a valid vault share link (link-as-invite — works even under CLOSED registration), CLAIM-FIRST so a username collision is one-shot (anti-enumeration parity with a closed-reg invite) and a crash leaves no orphan account, rolling back BOTH the link claim and the just-created account on cap/grant failure (rollback failures logged, not swallowed), returning a session token. The plugin setup wizard's redeem-mode 'Create account' routes through transport.redeemRegister so a new user onboards straight from a share link; the plugin's grantee-username share UI (ShareManageModal add-a-grant, plugin.shareVault, transport.shareCreate) is removed (grant revoke kept). An INDEPENDENT security/correctness critique was run on the auth path; its three Medium findings (link-holder username-enumeration oracle, fire-and-forget rollback orphan, location.origin link) were all fixed and covered by tests. Guards: 3 sharing E2E through the REAL server incl. 'a new account redeems a share LINK to onboard (link-as-invite) under closed registration' + share_redeem_register_onboards_* / _rejects_bad_token_and_collisions (one-shot) server tests + clippy -D warnings + client vitest 577 + tsc clean. Realizes D0037."; }
        part shareLinkOnboardingDoDR1 : TestResult { :>> id = "a1b2c3d4-0037-4a10-9b20-d0037c0de004"; :>> outcome = VerdictKind::pass; :>> judgedAgainst = "bc11f9c"; :>> judgedAt = "2026-08-03"; :>> judgedBy = "claudeOpus"; }
        // ===== D0037 completion + a test-reliability fix (1.14.0). =====
        action accountCreationLink;
        verification accountCreationLinkDoD : Test { :>> id = "a1b2c3d4-0037-4a10-9b20-d0037c0de005"; :>> method = VerificationMethod::test; :>> procedureText = "Completes D0037's account-creation link (MINOR 1.14.0; SERVER REDEPLOY for the admin-console part). The owner's model distinguished the vault share link (account+share) from a standalone account-creation link that 'just makes the first step' (an account, no vault) — this delivers the latter. New client codec invitelink.ts (selfsync-invite://register?server=&token=, mobile-safe like the share-link codec); the setup wizard recognizes a pasted invite link (prefills server + invite token + register mode) and THREADS the token through HttpTransport.register so account creation works on a CLOSED server (WizardState gains `invite`); the admin console (admin_ui.html renderInvites) surfaces each issued invite as a copyable account-creation LINK with an EDITABLE server address (parity with share links, correct for split/proxied deploys) plus the raw token for manual entry. Guards: client vitest — invitelink.test.ts (codec encode/parse/reject/mobile-percent-encoding) + modals-ui.dom 'pasting an account-creation (invite) link prefills the server + registers WITH the invite token' (asserts register called with the token); server register-with-invite already covered (admin_sets_registration_and_issues_working_invite). Full client vitest + tsc + build clean. Realizes D0037."; }
        part accountCreationLinkDoDR1 : TestResult { :>> id = "a1b2c3d4-0037-4a10-9b20-d0037c0de006"; :>> outcome = VerdictKind::pass; :>> judgedAgainst = "3585b23"; :>> judgedAt = "2026-08-03"; :>> judgedBy = "claudeOpus"; }
        action pluginWiringTimerLeakFix;
        verification pluginWiringTimerLeakFixDoD : Test { :>> id = "a1b2c3d4-0047-4a10-9b20-d0047c0de007"; :>> method = VerificationMethod::test; :>> procedureText = "Fixes the intermittent plugin-wiring flake (issuePluginWiringTimerLeak; ships with 1.14.0, client-test-only). A leaked reconnect-backoff setTimeout / poll setInterval from one test fired during a LATER test (real Node timers persist across tests) and re-stamped baseVaultKey mid-assertion, so 'D0047 guard is SERVER-qualified' failed ~1 in 3 full runs. FIX (D0047 — a correction becomes a permanent guard): plugin-wiring.test.ts now TRACKS every window timer a test schedules and force-clears all live ones in afterEach, guaranteeing timer isolation regardless of whether each onunload path cleared its own timers. Verified by THREE consecutive full client vitest runs green (the flake could no longer reproduce). Resolves issuePluginWiringTimerLeak."; }
        part pluginWiringTimerLeakFixDoDR1 : TestResult { :>> id = "a1b2c3d4-0047-4a10-9b20-d0047c0de008"; :>> outcome = VerdictKind::pass; :>> judgedAgainst = "3585b23"; :>> judgedAt = "2026-08-03"; :>> judgedBy = "claudeOpus"; }
        // ===== 1.14.1 — collapse chevron placement fix (owner mobile report). =====
        action collapseChevronFix;
        verification collapseChevronFixDoD : Test { :>> id = "a1b2c3d4-1210-4a10-9b20-d1210c0de009"; :>> method = VerificationMethod::test; :>> procedureText = "Ships PATCH 1.14.1 (UX; client-only, NO server redeploy). Owner-reported on 1.14.0 (mobile screenshot): the '7 synced' SettingGroup heading looked right but its chevron was DETACHED — inside the list card, divorced from the label, and the label didn't toggle. Cause: 1.12.10 placed the chevron/click by GUESSING the heading via group.listEl.previousElementSibling, which is wrong on mobile Obsidian's SettingGroup DOM. FIX: add the chevron with addExtraButton (the documented way to add a control to a SettingGroup heading) so it lands IN the heading next to the label with no DOM guessing; the whole heading row toggles, derived from the button via the stable .setting-item class; graceful degradation (chevron button toggles even if the row-click derivation fails). obsidian-stub models SettingGroup.addExtraButton in the heading. Guard: settings-ui.dom 'the Timestamp changes section is a collapsible ...' still green. DoD: full client vitest (583) + tsc + esbuild build clean + keel validate/guard green. Resolves issueCollapseChevronDetached."; }
        part collapseChevronFixDoDR1 : TestResult { :>> id = "a1b2c3d4-1210-4a10-9b20-d1210c0de010"; :>> outcome = VerdictKind::pass; :>> judgedAgainst = "ff98d78"; :>> judgedAt = "2026-08-03"; :>> judgedBy = "claudeOpus"; }
        // ===== 1.15.0 — settings tab revamp (owner-directed, mockup-approved). =====
        action settingsRevamp;
        verification settingsRevampDoD : Test { :>> id = "a1b2c3d4-1500-4a10-9b20-d1500c0de011"; :>> method = VerificationMethod::test; :>> procedureText = "Ships MINOR 1.15.0 (UX; client-only, NO server redeploy). Owner-directed settings-tab redesign, previewed as an HTML mockup and approved before implementation. Same features, reorganized: (1) a live STATUS hero leads (dot + state + last-synced; Reconnect only when down; still a pure FSM projection, fillStatus refreshes just that row); (2) CONNECTION facts (server/account/vault) + a 'Sync a device' row — the old section-and-row 'Connection' name collision gone; (3) 'Obsidian configuration' -> 'What syncs'; (4) Advanced + Timestamp-changes collapsed by default. LABELS (owner): 'Reconfigure' -> 'Setup' on the Server row next to 'Disconnect'; 'Add a device' -> 'Sync a device'; per-plugin 'Use synced' -> 'Use server's' (name which side WINS), standardized across the config-direction + config-conflict modals ('the server's version'). GLYPHS: every Connection/status action button gains a leading native lucide icon (iconBtn helper; settings/unplug/key/log-out/share-2/arrow-left-right/link/refresh-cw), Sign out red-tinted. Guards: full client vitest (585) incl. settings-ui.dom + configdir.dom + modals-ui.dom (controls found by label; icon spans carry no text) + tsc + esbuild build clean + keel validate/guard green. Nothing removed — same code paths."; }
        part settingsRevampDoDR1 : TestResult { :>> id = "a1b2c3d4-1500-4a10-9b20-d1500c0de012"; :>> outcome = VerdictKind::pass; :>> judgedAgainst = "58020c4"; :>> judgedAt = "2026-08-03"; :>> judgedBy = "claudeOpus"; }
        // ===== 1.15.1 — Connection-row button overflow fix (owner mobile report). =====
        action connectionRowOverflowFix;
        verification connectionRowOverflowFixDoD : Test { :>> id = "a1b2c3d4-1501-4a10-9b20-d1501c0de013"; :>> method = VerificationMethod::test; :>> procedureText = "Ships PATCH 1.15.1 (UX; client-only, NO server redeploy). Owner-reported on 1.15.0 (mobile screenshot): the Connection Server row rendered its long https:// URL inline in the control strip with the Setup/Disconnect buttons, pushing Disconnect off the card's right edge on a narrow screen. FIX: factRow renders each fact value as the row DESCRIPTION (full-width, wraps) rather than an inline control-area span, so the control row holds only the action buttons — robust for any long value (long username/vault name too). Retired the unused .selfsync-value CSS. Guard: settings-ui.dom green. DoD: full client vitest (585) + tsc + esbuild build clean + keel validate/guard green. Resolves issueConnectionRowButtonOverflow."; }
        part connectionRowOverflowFixDoDR1 : TestResult { :>> id = "a1b2c3d4-1501-4a10-9b20-d1501c0de014"; :>> outcome = VerdictKind::pass; :>> judgedAgainst = "40fab98"; :>> judgedAt = "2026-08-04"; :>> judgedBy = "claudeOpus"; }
        // ===== 1.16.0 — per-plugin Push/Pull (replaces the inert direction dropdown; owner-directed). =====
        action pluginPushPull;
        verification pluginPushPullDoD : Test { :>> id = "a1b2c3d4-1600-4a10-9b20-d1600c0de015"; :>> method = VerificationMethod::test; :>> procedureText = "Ships MINOR 1.16.0 (new capability; client-only, NO server redeploy). Owner-identified quandary: the per-plugin config-sync direction dropdown was INERT for an already-synced plugin (it only governed a no-base first contact) — flipping it did nothing, silently (an nHonestStatus / L-5 gap; issuePluginDirectionInert). Owner chose option #1: replace the dropdown (installed+synced plugin on a read-write vault) with explicit PUSH (make the server + other devices match this device's copy) / PULL (replace this device's copy with the server's) — confirmed authoritative overwrites scoped to .obsidian/plugins/<id>/, over the UNION of local+server files (pluginFilePaths), reusing the tested resolveConfigConflict per path. INDEPENDENT CRITIQUE run on the data-safety: fixed the self-folder guard to the shared case-insensitive+legacy isSelfPluginId (forcePlugin bypasses shouldSync — must not touch SelfSync's credential folder) and made partial-failure reported not swallowed; findings 3-5 (reconcile concurrency = same profile as removePluginFromServer; resolveConfigConflict inner read-only guard; filtered-io.list strand) accepted with rationale. community-plugins.json (enabled list) is never in the union, so Push/Pull can't disable a plugin fleet-wide. Guards: pluginFilePaths (union/scope/no-prefix-bleed) + isSelfPluginId (case-insensitive+legacy) pure tests + settings-ui.dom 'a synced+installed plugin offers Push/Pull ...' wiring test; full client vitest (589) + tsc + esbuild build clean + keel validate/guard green. Resolves issuePluginDirectionInert; realizes nHonestStatus."; }
        part pluginPushPullDoDR1 : TestResult { :>> id = "a1b2c3d4-1600-4a10-9b20-d1600c0de016"; :>> outcome = VerdictKind::pass; :>> judgedAgainst = "3079cd7"; :>> judgedAt = "2026-08-04"; :>> judgedBy = "claudeOpus"; }
        // ===== 1.17.0 — MFA deprecation (D0038): the code disabling MFA behind the mfa_enabled flag. =====
        action mfaDeprecation;
        verification mfaDeprecationDoD : Test { :>> id = "a1b2c3d4-1700-4a10-9b20-d1700c0de021"; :>> method = VerificationMethod::test; :>> procedureText = "Ships MINOR 1.17.0 (SERVER REDEPLOY). Realizes D0038: MFA (TOTP) disabled behind a runtime mfa_enabled flag (env MFA_ENABLED, default OFF), the mfa.rs/totp.rs code retained. auth::login enforces the TOTP second factor ONLY when mfa_enabled (an already-enrolled account signs in with password alone — no lockout; the password gate is unchanged, so a wrong password still fails); require_admin's REQUIRE_ADMIN_MFA gate applies only when mfa_enabled, with a boot warning if REQUIRE_ADMIN_MFA=1 && !MFA_ENABLED (critique #1 silent-downgrade guard); /api/mfa/* mounted only when enabled; /api/admin/me reports mfa_enabled + the admin console hides the Two-factor panel. Independent critique verdict: safe to ship (no High/Med; no auth bypass; no lockout; no deadlock). Guards: mfa_is_off_by_default (routes 404 + me.mfa_enabled false), the retained mfa_totp_full_lifecycle + require_admin_mfa via for_test_mfa (proving MFA_ENABLED=1 reversal still works), clippy -D warnings, client vitest 589. Realizes D0038; issueMfaLoginUnsupported mooted by D0038."; }
        part mfaDeprecationDoDR1 : TestResult { :>> id = "a1b2c3d4-1700-4a10-9b20-d1700c0de022"; :>> outcome = VerdictKind::pass; :>> judgedAgainst = "b997a63"; :>> judgedAt = "2026-08-05"; :>> judgedBy = "claudeOpus"; }
        // ===== 1.18.0 — change provenance + source-driven config-change notifications (owner-directed; SERVER REDEPLOY). =====
        action changeProvenanceNotify;
        verification changeProvenanceNotifyDoD : Test { :>> id = "a1b2c3d4-1800-4a10-9b20-d1800c0de023"; :>> method = VerificationMethod::test; :>> procedureText = "Ships MINOR 1.18.0 (new capability; SERVER REDEPLOY — SQLite index schema v2). Owner-directed: attribute every synced .obsidian/ config/plugin change to WHO made it and notify by SOURCE, retiring the shared-vs-private 'trust the source' warning that fired even on the owner's OWN plugin updates (the noise the owner flagged). SERVER: files-index columns author_user (SERVER-authenticated committer, never a client field), author_device_id, author_device_name; commit(req,&user) records them + changes() returns them; additive serde(default, skip_serializing_if) protocol fields (NO API_VERSION bump); v1->v2 migrate via idempotent ALTER-ADD (pre-provenance rows read None). CLIENT: a STABLE per-device UUID (crypto.randomUUID + WebView-safe non-throwing fallback, minted + DURABLY persisted at load via ensureDeviceId, independent of the mutable device name) stamped on every commit; per-device toggle configChangeNotify = 'user' (default: notify ONLY on ANOTHER PERSON's change) | 'userDevice' (also another of your OWN devices); own edits stay silent; identity = authenticated account then the UUID, so a rename can neither forge nor dodge a notice; the plugin-CODE hot-load-vs-restart RCE barrier is UNCHANGED + orthogonal (still gates on a freshly re-derived vaultIsPrivate). The decision rule is the pure, exhaustively-tested shouldNotifyConfigChange (unknown author -> conservative notify). INDEPENDENT SECURITY CRITIQUE run pre-ship (distinct lenses on spec+diff): FIXED finding-1 HIGH (community-plugins.json union-merge bypassed applyPull so recorded NO provenance -> every plugin enable/disable notified as 'unknown source', re-creating the spam; now records onRemoteConfig), finding-2 (per-surface path scoping so a mixed flush never misattributes one surface's change to another's author), finding-3 (randomUUID WebView fallback, never throws on the connect path), finding-4 (device id durably minted at load, not fire-and-forget), finding-5 (stale provenance cleared each pass); confirmed CLEAN: author is unforgeable (server-set; client CommitRequest carries no author field), the RCE hot-load barrier is intact, migration back-compat is safe, and the notify logic is total. SCOPED OUT (honest limitation, tracked): a peer's config/plugin DELETION is applied WITHOUT a notice because the Deletion wire type carries no provenance -> issueDeletionProvenanceUnnotified, a follow-up. Guards: full server cargo test + clippy -D warnings green; client vitest 603 (new shouldNotifyConfigChange/changeSourceLabel spoof-resistance tests, protocol author-mapping tests, parseSettings coercion, transport device-stamp test, rewritten source-driven CSS wiring test; server v1->v2 migration + commit-provenance tests) + tsc + esbuild build clean; keel validate/guard green. Realizes nChangeAttribution + ucNotifyForeignConfigChange."; }
        part changeProvenanceNotifyDoDR1 : TestResult { :>> id = "a1b2c3d4-1800-4a10-9b20-d1800c0de024"; :>> outcome = VerdictKind::pass; :>> judgedAgainst = "7fb0fc9"; :>> judgedAt = "2026-08-05"; :>> judgedBy = "claudeOpus"; }
        verification sittingReview20260803a : Test { :>> id = "4abd8ec9-7246-4b13-e9d5-38cf26135dc6"; :>> method = VerificationMethod::confirmation; :>> procedureText = "Per-sitting human review (D0049) for the 2026-08-03→05 sitting — a long owner-directed arc of settings-UX cleanup, sharing/onboarding rework, and two capability changes, each shipped as a release the owner iterated on: the timestamp-settings + collapsible-header UX refined against the owner's on-device mobile screenshots (timestampSettingsUx 1.12.7, settingsUxPolish 1.12.8, collapseHeaderFix 1.12.9, collapseHeaderGroupFix 1.12.10, collapseChevronFix 1.14.1); share-links-as-canonical + link onboarding + the admin-console rework (shareLinksCanonical/shareLinkOnboarding 1.13.0, accountCreationLink 1.14.0, D0037) + a test-reliability guard (pluginWiringTimerLeakFix); the mockup-approved settings-tab revamp (settingsRevamp 1.15.0) + its overflow fix (connectionRowOverflowFix 1.15.1); per-plugin Push/Pull replacing the inert direction dropdown (pluginPushPull 1.16.0); MFA deprecation behind a runtime flag (mfaDeprecation 1.17.0, D0038); and the change-provenance + source-driven config-change notifications the owner designed interactively — user+device identity, a stable per-device UUID as the spoof-proof identity, a user-default notify toggle, non-blocking notices, phase-2-first (changeProvenanceNotify 1.18.0). Every behavior/data/security-touching release went through an independent antagonistic critique before ship, which caught + fixed real bugs (e.g. the share-link enumeration oracle, the Push/Pull self-folder guard, and the 1.18.0 community-plugins.json notification-spam gap). The owner SIGNED OFF on 2026-08-05 ('reviewed') — an explicit acceptance of the sitting's completed + released content through 1.18.0. Single human confirmation gate for the sitting; each sprint's closeOut (inspect) + retro (analysis) ran autonomously."; }
        part sittingReview20260803aR1 : TestResult { :>> id = "4abd8ec9-7246-4b13-e9d5-38cf26135dc7"; :>> outcome = VerdictKind::pass; :>> judgedAgainst = "2fa1a63"; :>> judgedAt = "2026-08-05"; :>> judgedBy = "wweatherholtz"; }
        // ===== 1.19.0 — Push/Pull preview (owner-directed: "more intelligence on push & pull"). NEW sitting. =====
        action pushPullPreview;
        verification pushPullPreviewDoD : Test { :>> id = "a1b2c3d4-1900-4a10-9b20-d1900c0de025"; :>> method = VerificationMethod::test; :>> procedureText = "Ships MINOR 1.19.0 (new capability; client-only, NO server redeploy). Owner intent: 'more intelligence on push & pull — what are we pushing to and from?' — the shipped Push/Pull (1.16.0) only showed a generic 'Overwrite the server's copy' confirm, never WHAT it overwrites. FIX: a PREVIEW modal fronting each per-plugin Push/Pull — the direction/ENDPOINTS (this device <-> the server + your other devices), a per-file classification (overwrite / add / remove) + counts, and an on-demand line diff for the changed text settings; an already-in-sync folder shows 'nothing to change' + disables Confirm. New pure pushpreview.ts — classifyPushPull MIRRORS resolveConfigConflict exactly (push: local-absent=>delete server, else overwrite/create; pull: server-absent=>delete here, else overwrite/create), with a presence-vs-hash SideState so an unreadable file classifies per what the real action sees; lineDiff reuses merge.ts's tested LCS anchors (capped 2000 lines). New pushpreviewmodal.ts (lazy per-file diffs). Uses the SAME file union (pluginFilePaths) + hash basis (local sha256 vs server FileMeta.hash — un-normalized config, so comparable) + data source (io.list + changes(0)) as forcePlugin, so the preview cannot disagree with what Push/Pull actually does. INDEPENDENT SECURITY CRITIQUE run pre-ship (distinct lenses on spec+diff): CONFIRMED clean — hash basis, diff direction, self-plugin credential-folder guard (isSelfPluginId returns null before any read; never opens SelfSync's own data.json), modal resolution (only an explicit Confirm resolves true; dismiss=false; no double-resolve), read-only-vault guard (no Push button on a read-only vault + forcePlugin defense-in-depth). FIXED finding-1 MEDIUM (unbounded memory — the preview slurped whole files to hash/diff; now SIZE-GATED: a large file is neither read-to-hash nor fetched-to-diff, matching the real pull's streaming, so no mobile OOM) + finding-3 LOW (an unreadable-but-present local file now classifies per direction — a pull is an overwrite, not a false 'add'). ACCEPTED finding-2 with rationale: the real push re-commits every present file, but the server's IDEMPOTENT commit short-circuit (vault.rs: identical path+hash+chunks => returns the existing meta unchanged — no version bump, no provenance restamp, no broadcast) makes an unchanged re-push a genuine no-op, so the 'unchanged' label is honest about the OUTCOME. Guards: full client vitest 619 (new classifyPushPull + lineDiff pure tests incl. presence/size/unread edge cases + a PushPreviewModal DOM test proving endpoints/summary/lazy-diff/confirm-resolution) + tsc + esbuild build clean; keel validate/guard green. Realizes nPushPullPreview + ucPreviewPushPull."; }
        part pushPullPreviewDoDR1 : TestResult { :>> id = "a1b2c3d4-1900-4a10-9b20-d1900c0de026"; :>> outcome = VerdictKind::pass; :>> judgedAgainst = "8daa0bd"; :>> judgedAt = "2026-08-05"; :>> judgedBy = "claudeOpus"; }
        // ===== 1.20.0 — instant Push/Pull grey-out (hint) + faster on-click check (owner: "lots of inactionable push/pulls"). =====
        action pushPullGreyout;
        verification pushPullGreyoutDoD : Test { :>> id = "a1b2c3d4-2000-4a10-9b20-d2000c0de027"; :>> method = VerificationMethod::test; :>> procedureText = "Ships MINOR 1.20.0 (client-only, NO server redeploy). Owner feedback on 1.19.0: 'lots of push/pulls that are inactionable — grey them out if the server already holds our changes / the device already has the server's config; but checking is slow (~2s on mobile), I don't want them prechecked all the time. options?' Of three presented options the owner chose INSTANT, network-free grey-out from sync state. FIX: pluginSyncClean(id) decides if a plugin folder is already CONVERGED (local == last-synced base) INSTANTLY + network-free — the pure stampsConverged() compares the base's persisted (size,mtime) stamps to a SCOPED walkConfigTree of just .obsidian/plugins/<id> (NO whole-vault io.list, NO changes(0) server fetch, NO hashing); conservative on ANY doubt (recorded config conflict, missing stamp, set mismatch, unlistable folder) → NOT converged. Settings DIMS Push/Pull as a hint when converged (cached for instant no-flicker re-render + refreshed async each render; entry dropped after a push/pull, cache cleared on hide). PERF: the on-click preview now also scopes its local list to the plugin folder (was the whole-vault io.list — the owner-reported ~2s). INDEPENDENT SECURITY CRITIQUE run pre-ship: confirmed conservative-toward-live everywhere that matters, scoped-walk equivalence for the rendered case, guard robustness, no uncaught exception paths. FIXED its one MEDIUM finding (§1): the grey-out shares auto-sync's (size,mtime) skip heuristic, so an out-of-band change preserving BOTH size AND mtime is invisible to auto-sync — and a HARD-disabled override would then trap the user (couldn't Pull to restore a locally-corrupted file). Fix per the critique's recommendation: the grey-out is a HINT, never a lock — buttons stay CLICKABLE (dimmed via opacity, NOT setDisabled), and a click ALWAYS runs the accurate preview, so the manual override can always recover the truth. Guards: full client vitest 625 (new stampsConverged pure tests incl. stamp-drift / set-mismatch / no-stamp edge cases + a settings DOM test proving the buttons DIM yet stay clickable + run the accurate preview) + tsc + esbuild build clean; keel validate/guard green. Realizes nPushPullPreview (viability visibility + performance)."; }
        part pushPullGreyoutDoDR1 : TestResult { :>> id = "a1b2c3d4-2000-4a10-9b20-d2000c0de028"; :>> outcome = VerdictKind::pass; :>> judgedAgainst = "0fc2f78"; :>> judgedAt = "2026-08-05"; :>> judgedBy = "claudeOpus"; }
        // ===== 1.21.0 — author + timestamp in the Push/Pull preview (owner: "know the author + a timestamp"). =====
        action pushPullProvenance;
        verification pushPullProvenanceDoD : Test { :>> id = "a1b2c3d4-2100-4a10-9b20-d2100c0de029"; :>> method = VerificationMethod::test; :>> procedureText = "Ships MINOR 1.21.0 (client-only, NO server redeploy). Owner: 'I want to know the author when I'm pushing and overwriting settings, and when pulling settings. I want a timestamp and a user' — the original 'made from Wills Desktop at X timestamp' format they'd described. The 1.18.0 change-provenance (author + device_id/name + mtime) already rides on every server FileMeta and pluginPushPullPreview already fetches it via changes(0); this SURFACES it in the preview. Each preview row that touches a SERVER copy now shows 'on server: <user> · <device> · <when>' — a Push tells you WHOSE settings you're overwriting/removing, a Pull tells you whose you're adopting. A local-only file (no server copy) shows no line; a pre-1.18.0 file (no author recorded) shows just the timestamp. author is SERVER-AUTHENTICATED (unspoofable); deviceName is a display-only label. Pure FileChangeView + serverProvenanceWho() helper; the modal formats mtime (toLocaleString). Display-only — no sync behavior/data change, no server change — so a SELF-REVIEW stands in for a full independent critique (setText escapes any label; the provenance is already-validated FileMeta data; author can't be spoofed). Guards: full client vitest 629 (serverProvenanceWho pure test + a modal DOM test asserting the who/device line renders on the overwrite + delete rows, and is absent on a local-only create) + tsc + esbuild build clean; keel validate/guard green. Realizes nChangeAttribution + nPushPullPreview (completing the owner's original 'who + when' intent in the push/pull path)."; }
        part pushPullProvenanceDoDR1 : TestResult { :>> id = "a1b2c3d4-2100-4a10-9b20-d2100c0de030"; :>> outcome = VerdictKind::pass; :>> judgedAgainst = "6da17b6"; :>> judgedAt = "2026-08-05"; :>> judgedBy = "claudeOpus"; }
        // ===== 1.21.1 — settings scroll no longer jumps to top on a toggle (owner-reported bug). =====
        action settingsScrollPreserve;
        verification settingsScrollPreserveDoD : Test { :>> id = "a1b2c3d4-2101-4a10-9b20-d2101c0de031"; :>> method = VerificationMethod::test; :>> procedureText = "Ships PATCH 1.21.1 (bugfix; client-only, NO server redeploy). Owner-reported: 'most of the time when I click an option, a slide toggle on community plugins for example, it resets the settings page to the top.' Root cause: the config-sync surface toggles + the community-plugin checklist call this.display(), which does containerEl.empty() + a full tab rebuild — discarding the scroll position. FIX: display() now captures the scrolling ancestor's scrollTop BEFORE empty() (scrollEl() walks up to the overflow:auto/scroll ancestor) and restores it after the rebuild; sections rebuild at the same heights so the user stays put. Centralised in display() — the single re-render choke point — so EVERY handler that re-renders is fixed structurally, not by per-handler vigilance (D0047: the centralisation IS the durable control; happy-dom has no layout so real scroll isn't unit-testable). Guards: full client vitest 629 (settings-ui.dom still green through the display() restructure — body moved under `if (configured)`) + tsc + esbuild build clean; keel validate/guard green. Resolves issueSettingsScrollResetsOnToggle."; }
        part settingsScrollPreserveDoDR1 : TestResult { :>> id = "a1b2c3d4-2101-4a10-9b20-d2101c0de032"; :>> outcome = VerdictKind::pass; :>> judgedAgainst = "23e009b"; :>> judgedAt = "2026-08-05"; :>> judgedBy = "claudeOpus"; }
        // ===== 1.21.2 — HARD-disable Push/Pull when inactionable (owner reversed the §1 hint). =====
        action pushPullDisableInactionable;
        verification pushPullDisableInactionableDoD : Test { :>> id = "a1b2c3d4-2102-4a10-9b20-d2102c0de033"; :>> method = VerificationMethod::test; :>> procedureText = "Ships PATCH 1.21.2 (owner-directed behavior change; client-only, NO server redeploy). Owner directed: 'disable push and pull buttons if there is no real action. They're updated quickly enough that if I really want to push, and someone is legitimately updating concurrently, I can wait a second. In the meantime, we'll accurately prevent misleading the user 99%+ of the time.' This REVERSES the pushPullGreyout §1 'hint, not lock' softening (which had kept the buttons dimmed-but-clickable so an out-of-band divergence stayed recoverable). OWNER'S INFORMED ACCEPTANCE of the tradeoff (recorded after I re-surfaced the residual): when the plugin folder is converged (pluginSyncClean), the Push/Pull buttons are now setDisabled AND the act() click is guarded (a no-op) — so a LIVE button ALWAYS means a real overwrite (never misleading). The concurrent-remote-edit case self-heals within ~a second (next poll) — the owner's 'wait a second' reasoning; the ONLY non-self-healing residual — an out-of-band change preserving BOTH size AND mtime — is an accepted, PRE-EXISTING auto-sync blindspot (auto-sync misses it too via the same (size,mtime) skip, so the button was never a reliable recovery for it), acknowledged by the owner. Guards: full client vitest 629 (settings-ui.dom updated: a converged button is DISABLED + its click is a guarded no-op — no preview, no overwrite) + tsc + esbuild build clean; keel validate/guard green. Refines pushPullGreyout (nPushPullPreview); the owner decision + accepted residual are recorded HERE (capture-the-decision, D-invariant §2.4)."; }
        part pushPullDisableInactionableDoDR1 : TestResult { :>> id = "a1b2c3d4-2102-4a10-9b20-d2102c0de034"; :>> outcome = VerdictKind::pass; :>> judgedAgainst = "3dffae6"; :>> judgedAt = "2026-08-05"; :>> judgedBy = "claudeOpus"; }
        // ===== 1.21.3 — make the disabled Push/Pull buttons genuinely unclickable (owner-reported on 1.21.2). =====
        action pushPullDisableInert;
        verification pushPullDisableInertDoD : Test { :>> id = "a1b2c3d4-2103-4a10-9b20-d2103c0de035"; :>> method = VerificationMethod::test; :>> procedureText = "Ships PATCH 1.21.3 (bugfix; client-only, NO server redeploy). Owner-reported on 1.21.2: 'the push and pull buttons are grayed, but clickable. they should be disabled/unclickable.' Root cause: ExtraButtonComponent.setDisabled only adds an is-disabled CLASS to the button's div/anchor (not a native <button disabled>), so it GREYS the control but does NOT block the onClick — the act() guard no-op'd the action, but the button still felt interactive. FIX: when converged, also set pointer-events:none on the button element, making it genuinely INERT (no click/hover) — a real disabled control; the act() guard stays as defense-in-depth. GUARD (D0047 — a correction gets a permanent automated guard): the settings-ui.dom test now asserts the converged button's style.pointerEvents === 'none' (not just that a click no-ops), catching any regression to greyed-but-clickable. Guards: full client vitest 629 + tsc + esbuild build clean; keel validate/guard green. Resolves issuePushPullDisabledStillClickable; completes pushPullDisableInactionable."; }
        part pushPullDisableInertDoDR1 : TestResult { :>> id = "a1b2c3d4-2103-4a10-9b20-d2103c0de036"; :>> outcome = VerdictKind::pass; :>> judgedAgainst = "466aa82"; :>> judgedAt = "2026-08-05"; :>> judgedBy = "claudeOpus"; }
        verification sittingReview20260805a : Test { :>> id = "5b0d8f05-0805-4a10-9b20-a1b2c3d40805"; :>> method = VerificationMethod::confirmation; :>> procedureText = "Per-sitting human review (D0049) for the 2026-08-05 sitting — the NEW work AFTER the 2026-08-03 sitting was signed off ('reviewed'). The owner reported that pushing plugin settings gave no indication of what it overwrites ('am I forgetting something'), directed 'more intelligence on push & pull — what are we pushing to and from?' + 'record as need please', then followed up that many push/pulls are inactionable and should grey out (but the check is slow on mobile). This gate covers pushPullPreview (1.19.0 — the per-file PREVIEW modal: direction/endpoints + overwrite/add/remove counts + on-demand text diffs), pushPullGreyout (1.20.0 — the instant network-free grey-out HINT + the scoped-list perf fix), and pushPullProvenance (1.21.0 — the SERVER copy's author + device + timestamp per preview row, the owner's original 'who + when' format), the first two built through independent security critiques (preview-matches-action + memory bounds; and the grey-out-is-a-hint-not-a-lock fix), the last a display-only self-reviewed increment. The owner SIGNED OFF on 2026-08-07, directing 'stamp and proceed' — an explicit acceptance of the sitting's released content (1.19.0 through 1.21.3: the Push/Pull preview, the instant grey-out + scoped-list perf fix, the per-row server provenance, the settings-scroll-preserve fix, and the Push/Pull hard-disable + inert-button corrections). Single human confirmation gate for the sitting; each sprint's closeOut (inspect) + retro (analysis) ran autonomously."; }
        part sittingReview20260805aR1 : TestResult { :>> id = "5b0d8f05-0805-4a10-9b20-a1b2c3d40806"; :>> outcome = VerdictKind::pass; :>> judgedAgainst = "e0f378e"; :>> judgedAt = "2026-08-07"; :>> judgedBy = "wweatherholtz"; }
        // ===== 1.22.0 — plugin-sync autopilot + peer-approval gate (owner-directed set-and-forget). NEW sitting. =====
        action pluginSyncAutopilot;
        verification pluginSyncAutopilotDoD : Test { :>> id = "a1b2c3d4-2200-4a10-9b20-d2200c0de037"; :>> method = VerificationMethod::test; :>> procedureText = "Ships MINOR 1.22.0 (new capability + settings-UX; client-only, NO server redeploy). Owner-directed SET-AND-FORGET after a design discussion working through config-sync AUDIENCES (device-local / personal / shared): a 'Auto-sync new plugins' setting (default OFF — auto-propagating plugin CODE is security-sensitive, so opt-in). When on, runPluginAutopilot (on each full reconcile via onRemotePlugins + on settings render): (a) a plugin installed HERE and (b) a server plugin from YOUR OWN account (main.js committer == you, or unknown-author on your PROVABLY-PRIVATE vault) → auto-added to the synced allowlist (upload / adopt); (c) a plugin added by ANOTHER PERSON → NEVER auto-adopted — it lands in a persistent 'Awaiting your approval' list (the reframed Available section, labeled WHO added it) + a one-time toast. Ownership keys on the AUTHENTICATED committer of main.js (the EXECUTABLE), so a device rename can't fake it. A persisted 'seen' set means an un-ticked plugin is never re-added (the policy never fights a manual choice). Bundled settings-UX: copy fixes (plugin rows say what+when — 'here only — uploads to the server on next sync'), removed the redundant 'Sync none' button, and the 'Greyed Push/Pull = already in sync' note. INDEPENDENT SECURITY CRITIQUE run pre-ship: CONFIRMED author is server-authenticated (a peer can't forge author==you) + the autopilot only whitelists/downloads — the separate hot-load gate still re-derives vault privacy + keeps the restart/trust barrier, so it CANNOT run a peer's code. FIXED findings: F2 (ownership keys on main.js not manifest.json — a peer overwriting main.js can't be auto-adopted as yours), F1 (author sourced from the reconcile's own manifest — no per-plugin/per-render fileMeta network storm), F4 (peer plugins not marked seen → a later ownership flip can still auto-adopt), F7 (.catch on the fire-and-forget); CONFIRMED clean: F3 (no peer-code execution), F5 (username exact-match, fail-safe). ACCEPTED F6 (documented, = the nPerUserConfigScope SPIKE): on a shared vault, auto-synced plugins land in the shared store visible to peers — personal-vs-shared scope is the pinned spike. Guards: full client vitest 633 (autopilot own-adopt vs peer-gate, un-tick-sticks, off-is-no-op; parseSettings opt-in; reconcile onRemotePlugins carries main.js authors) + tsc + esbuild build clean; keel validate/guard green. Realizes nPluginSyncAutopilot + ucSetAndForgetPluginSync."; }
        part pluginSyncAutopilotDoDR1 : TestResult { :>> id = "a1b2c3d4-2200-4a10-9b20-d2200c0de038"; :>> outcome = VerdictKind::pass; :>> judgedAgainst = "e61df7e"; :>> judgedAt = "2026-08-07"; :>> judgedBy = "claudeOpus"; }
        // ===== composed-vaults Phase 1 — mount data model + two-sided path math + boundary rules (D0039). NO release. =====
        action mountsFoundation;
        verification mountsFoundationDoD : Test { :>> id = "a1b2c3d4-3900-4a10-9b20-d3900c0de039"; :>> method = VerificationMethod::test; :>> procedureText = "Phase 1 of the D0039 composed-vaults epic — FOUNDATION only. NO version bump / NO release (internal scaffolding — no engine wiring, no user-facing behavior yet), so CI validates on push but the release/publish workflow does not fire. New PURE module client/src/mounts.ts (no Obsidian API, no engine dependency, so exhaustively unit-testable + can never drift from the reconcile that consumes it in Phase 2+): the Mount type ({source:{owner,vaultId,sourcePath}, mountPoint, direction:'pull'|'sync'}); normFolder (the single source of truth for path comparison/building); the LOAD-BEARING BOUNDARY rules claimsLocal / primaryExcludes (segment-safe — a sibling that merely shares a name prefix is NOT claimed — so the primary reconcile scope excludes exactly the mount points and a mounted file never double-syncs to the primary server vault, the one invariant a bug here would corrupt/duplicate data); the two-sided path translation local <-> mount-relative <-> source-S-relative (mountRelFromLocal / mountRelFromSource / localFromMountRel / sourceFromMountRel, whole-source vs subfolder, round-trip); validateMounts (rejects empty/root + duplicate + nested mount points, allows name-prefix siblings); and parseMounts (parse-don't-validate at the persistence boundary — drops malformed entries, normalizes both paths, defaults an unknown direction to the SAFE 'pull'). Plus the settings.mounts PER-DEVICE data model (composition is a local choice, never synced — like the primary target; normalized + malformed-dropped on parse). Guards: full client vitest 648 (new client/test/mounts.test.ts — normFolder, boundary + segment-safety, two-sided round-trip, whole-source vs subfolder, validateMounts overlap/nest, parseMounts coercion/drop) + tsc --noEmit clean; keel validate/guard green. Realizes nComposedVaults (Phase 1 of N — foundation). Next: Phase 2 (pull mount engine + MountedIo adapter + per-mount FSM + aggregate status fold)."; }
        part mountsFoundationDoDR1 : TestResult { :>> id = "a1b2c3d4-3900-4a10-9b20-d3900c0de040"; :>> outcome = VerdictKind::pass; :>> judgedAgainst = "2933ee7"; :>> judgedAt = "2026-08-07"; :>> judgedBy = "claudeOpus"; }
        verification sittingReview20260807a : Test { :>> id = "7a0d8f07-0807-4a10-9b20-a1b2c3d40807"; :>> method = VerificationMethod::confirmation; :>> procedureText = "Per-sitting human review (D0049) for the 2026-08-07 sitting. After a design discussion (the owner worked through config-sync AUDIENCES — device-local / personal / shared — confirmed they DO share vaults with others, and pinned two SPIKES: nPerUserConfigScope + nComposedVaults for a later brainstorm), the owner directed 'do the shared vault feature now': the plugin-sync AUTOPILOT (pluginSyncAutopilot, 1.22.0) — set-and-forget auto-sync of your own new plugins with a peer-approval gate keyed on the authenticated main.js committer — plus the bundled settings-UX (copy fixes, 'Sync none' removed, the 'Greyed = already in sync' note). Built through an independent security critique (main.js-not-manifest ownership + no fetch-storm fixes). The owner SIGNED OFF on 2026-08-07, directing 'stamp and proceed' — an explicit acceptance of the sitting's content: the plugin-sync autopilot + bundled settings-UX (1.22.0) and the composed-vaults Phase 1 foundation (mountsFoundation — internal scaffolding, method=test self-evidencing). Single human confirmation gate for the sitting; each sprint's closeOut (inspect) + retro (analysis) ran autonomously."; }
        part sittingReview20260807aR1 : TestResult { :>> id = "7a0d8f07-0807-4a10-9b20-a1b2c3d40808"; :>> outcome = VerdictKind::pass; :>> judgedAgainst = "e0f378e"; :>> judgedAt = "2026-08-07"; :>> judgedBy = "wweatherholtz"; }
        // ===== composed-vaults Phase 2 (1/n) — MountedIo + MountedApi prefix-translating adapters (D0039). NEW sitting. NO release. =====
        action mountIoAdapters;
        verification mountIoAdaptersDoD : Test { :>> id = "a1b2c3d4-3901-4a10-9b20-d3901c0de041"; :>> method = VerificationMethod::test; :>> procedureText = "Phase 2 (increment 1) of the D0039 composed-vaults epic — the two-sided PREFIX-TRANSLATING adapters that let a Mount reuse the existing reconcile engine unchanged. ENGINE-INTERNAL (not yet wired to a live reconcile), NO version bump / NO release. New PURE module client/src/mountio.ts (no Obsidian API, no transport — wraps an injected VaultIo/SyncApi, so exhaustively unit-testable): MountedIo (local-side mount-relative <-> <mountPoint>/<rel>; list() exposes ONLY the mount subtree, re-keyed + data-only-filtered; exists/appendWrite mirror the base's capability); MountedApi (source-side mount-relative <-> <sourcePath>/<rel> over a source-vault-bound API; changes() drops outside-subtree + config paths but preserves the source-global version so the cursor stays consistent; HARD-REFUSES commit/deleteFile on a pull/read-only mount — the load-bearing safety net); isDataPath (the data-only boundary, reject .obsidian/**, case-folded). INDEPENDENT SECURITY CRITIQUE run pre-commit (3 lenses: path-translation, invariant-bypass, reconcile-integration). FIXED: B1 HIGH (deleteFile guarded read-only but NOT data-only — a sync mount could delete source config; now symmetric with commit), A1 MED (normFolder trimmed each segment, corrupting round-trip for a filename with legitimate leading/trailing whitespace — now round-trip-faithful; user-input trim deferred to the Phase-4 UI), B2 MED (fileMeta returns null for a config path — config invisible even via a direct lookup), B3 (isDataPath case-folded so .Obsidian can't bypass on a case-insensitive FS). CONFIRMED CLEAN: read-only structurally sound (B4); the delete-guard ratio uses the mount's FILTERED manifest, not the global version (C2); the filtered stream manufactures no phantom deletions + the cursor stays in source-global space (C3). RECORDED as a tracked hazard (issueMountBaseIsolation, C1 HIGH — NOT adapter-enforceable): the Phase-3 wiring MUST give each mount its OWN base+state (a shared base -> phantom mass-delete), marked by a load-bearing invariant comment + resolved by the mountEngine action. ACCEPTED C4 LOW (a legitimately-emptied small mount subtree trips the conservative bulk-delete guard — a Phase-3 delete-propagation concern, no corruption). Guards: full client vitest 661 (mountio.test — local/source translation, whole-source, capability mirror, read-only refusal, symmetric config write/delete refusal, fileMeta config-null, case-fold; mounts.test — whitespace round-trip) + tsc --noEmit clean; keel validate/guard green. Realizes nComposedVaults (Phase 2 adapters)."; }
        part mountIoAdaptersDoDR1 : TestResult { :>> id = "a1b2c3d4-3901-4a10-9b20-d3901c0de042"; :>> outcome = VerdictKind::pass; :>> judgedAgainst = "58c2fdd"; :>> judgedAt = "2026-08-07"; :>> judgedBy = "claudeOpus"; }
        // ===== composed-vaults Phase 2 (2/n) — the pure mount-engine CORE (per-mount runtime + FSM + status fold). NO release. =====
        action mountEngineCore;
        verification mountEngineCoreDoD : Test { :>> id = "a1b2c3d4-3902-4a10-9b20-d3902c0de043"; :>> method = VerificationMethod::test; :>> procedureText = "Phase 2 (increment 2) of the D0039 composed-vaults epic — the pure mount-engine core that lets a mount run as a SECOND concurrent reconcile scope reusing the pure engine unchanged. ENGINE-INTERNAL (not yet driven by a live loop), NO version bump / NO release. Two pure modules (no Obsidian API, no transport — unit-testable): (1) mountengine.ts — MountRuntime bundles one mount's scope and STRUCTURALLY owns its isolation: it ALWAYS constructs its OWN BaseStore + SyncState + DeleteRateGuard + retry budget, so a caller CANNOT inject the primary's — making issueMountBaseIsolation (critique C1 HIGH: a shared base -> phantom mass-delete) impossible to violate by construction; deps() assembles a ReconcileDeps over the mount's own base/state + the MountedIo/MountedApi wrappers + the isDataPath data-only accepts, with readOnly=true for a PULL mount (reconcile's pull-only path, defense-in-depth with MountedApi's write hard-refuse); mountKey() is a stable order-independent per-mount identity for persisting its own base+cursor (MountPersist). (2) mountfsm.ts — the per-mount lifecycle FSM (detached/mounting/live/syncing/diverged/offline/unmounting/failed) as a pure transition (unmount+fail from any live state; unknown transition = conservative no-op), plus the aggregate status FOLD (mountHealth/foldHealth/aggregateStatus) that folds the primary scope's health with every mount's and surfaces the WORST as the single status light's state + reason, so a struggling mount is never masked (nor masks the primary). Same pure-projection discipline as connstate/transportstate/statuslight. Guards: full client vitest 673 (mountengine.test — structural isolation [distinct base/state/guard per runtime + mutation isolation], restore/persist round-trip, deps wiring, pull=readOnly; FSM happy-path + offline/diverged/failed recovery + unmount/fail-from-any + no-op; fold worst-wins + reason) + tsc --noEmit clean; keel validate/guard green. Resolves the ISOLATION invariant of issueMountBaseIsolation STRUCTURALLY (the live mountEngine wiring will still assert it end-to-end before the issue closes). Realizes nComposedVaults (Phase 2 engine core)."; }
        part mountEngineCoreDoDR1 : TestResult { :>> id = "a1b2c3d4-3902-4a10-9b20-d3902c0de044"; :>> outcome = VerdictKind::pass; :>> judgedAgainst = "cb36a8e"; :>> judgedAt = "2026-08-07"; :>> judgedBy = "claudeOpus"; }
        // ===== composed-vaults Phase 3 (1/n + 2/n) — the LIVE mount engine (sync loop + main.ts wiring). Resolver for issueMountBaseIsolation. NO release (dormant). =====
        action mountEngine;
        verification mountEngineDoD : Test { :>> id = "a1b2c3d4-3903-4a10-9b20-d3903c0de045"; :>> method = VerificationMethod::test; :>> procedureText = "Phase 3 of the D0039 composed-vaults epic — the LIVE mount engine, wired into the plugin as a SECOND concurrent sync scope per settings.mounts entry, DORMANT until a mount is configured (no UI sets one yet → zero behaviour change; NO version bump / NO release). Two increments: (1) mountsync.ts — the sync LOOP (pollMount → decideReconcileMode → reconcileAll|reconcileDelta; reconcileMountScope(s) advancing the pure mountfsm, fail-isolated: a poll throw → offline (transient) or failed after MAX_MOUNT_FAILS), exercised END-TO-END in unit tests over the REAL reconcile engine (faithful chunked source + in-memory io); (2) main.ts glue — mountScopes/mountStateStore/sessionToken/mountIo fields, buildMountApi (a HttpTransport bound to the SOURCE vault, same server+session token), rebuildMountScopes (build/preserve/dedupe/restore-own-base+cursor), reconcileMounts (DETACHED + re-entrancy-guarded + fail-isolated, run after the primary pass), the primary-scope BOUNDARY exclusion (activeMounts() feeds both passes/accepts AND scope-building), mountState persistence, teardown cleanup. v1 is POLL-DRIVEN on the primary cycle (per-mount real-time ws deferred, D0040). INDEPENDENT SECURITY CRITIQUE (3 lenses) + a re-verify pass, both pre-commit. FIXED: A1 HIGH (the mount had reused the primary's filtered io → mount writes silently dropped + a reconnect delete-remote'd the SOURCE vault; now a mount wraps a separate DATA-ONLY io — forMount: passes=!isConfigPath, no mount-exclusion, no .obsidian walk — the traversal-safety guard stays); A2/C3 MED (a hand-edited overlapping/duplicate mount set is rejected wholesale via validateMounts + deduped by mountKey); B1 MED (reconcileMounts DETACHED + re-entrancy-guarded so a hung mount can't stall the primary engine queue); B2/N2 MED/LOW (mountState loaded via a validated parseMountState — finite ≥0 version, base entries need a string hash, non-string merge-ancestor text dropped — so hostile persisted input can't reach the engine); N1 MED (the primary exclusion + scope-building now share ONE activeMounts() validated set, so a bad set can't leave a folder excluded-from-primary yet handled-by-no-mount). CONFIRMED CLEAN + re-confirmed after fixes: pull=read-only (deps.readOnly + MountedApi hard-refuse + reconcile readOnly throw), throw fail-isolation, per-mount base/state/guard isolation (each MountRuntime constructs its OWN — a caller cannot inject the primary's), persist single-flight coalescing of base+mountState, content-addressed cache sharing. ACCEPTED N3 LOW (a never-settling source poll leaves the subsystem dormant — not reachable via HttpTransport's request timeout; strictly better than hanging the primary). HONEST RESIDUAL: no end-to-end integration test through the REAL Obsidian ObsidianVaultIo (not unit-testable without Obsidian) — validated by the critique's static trace + the owner's on-device pass (Phase 4). Guards: full client vitest 683 (mountsync end-to-end pull/push/fail-isolation/recovery; parseMountState hostile-input validation) + tsc --noEmit clean + esbuild build clean; keel validate/guard green. RESOLVES issueMountBaseIsolation (isolation structurally enforced + critique-re-confirmed). Realizes nComposedVaults (Phase 3 live engine, dormant)."; }
        part mountEngineDoDR1 : TestResult { :>> id = "a1b2c3d4-3903-4a10-9b20-d3903c0de046"; :>> outcome = VerdictKind::pass; :>> judgedAgainst = "13fbd86"; :>> judgedAt = "2026-08-07"; :>> judgedBy = "claudeOpus"; }
        // ===== composed-vaults Phase 4 — the mount-management UX (settings section + guided add modal). NO release (staged for an on-device pass). =====
        action mountUx;
        verification mountUxDoD : Test { :>> id = "a1b2c3d4-3904-4a10-9b20-d3904c0de047"; :>> method = VerificationMethod::test; :>> procedureText = "Phase 4 of the D0039 composed-vaults epic — the user-facing UX, the FIRST consumer that lets a mount be configured (activating the otherwise-dormant engine). Built from a use-case + human-factors analysis (the driver is the safety of a data-moving feature). NO version bump / NO release — the whole composed-vaults feature (Phases 1-4) stays STAGED on main until the owner's on-device pass, then the v1 release. New client/src/mountsettings.ts (pure helpers + the modal): sourceOptions (candidate sources = vaults I own + vaults shared TO me, EXCLUDING the primary so you can't mount a vault into itself, marking write permission), mountRowLabel/mountStateLabel, validateMountDraft (why Save is disabled), and MountEditModal — the guided add form: default PULL (safe, source untouched); SYNC offered ONLY for a writable source and behind a ⚠ warning naming the target + audience; live validation disables Save on overlap/blank/root. settings.ts renderComposedVaults: a collapsed 'Composed vaults' section listing each mount (source→local, direction, live per-mount state) with a NON-DESTRUCTIVE remove flow (files kept as normal notes; the destructive delete option deferred as the safest v1 choice). main.ts: mountStates/addMount/removeMount wiring. INDEPENDENT UX + code CRITIQUE (2 lenses) run pre-commit — headline CONFIRMED: no normal-UI path causes an accidental write/delete to an unintended source (sync is opt-in + write-perm-gated + warned + names the target). FIXED: C1 MED (removeMount raced an in-flight reconcile → the removed mount's state got re-persisted; onEvent now skips a scope no longer in mountScopes), U1 MED (perm not re-checked at save → a save-time downgrade to pull on a non-writable source, defense-in-depth over the trusted-server 403 — D0007), U2/U3 MED (clearer copy: adding DETACHES the folder from primary sync + conflict-copy semantics; removing UPLOADS the kept files to the primary vault + other devices), C4 LOW (saved set only after addMount resolves). ACCEPTED C2 LOW (owner-alias exact-match — not reachable with current transport). Guards: full client vitest 692 (mountsettings pure-helper tests: sourceOptions primary-exclusion + read/readWrite perm, validateMountDraft overlap/root/blank, labels; settings-ui.dom: the section lists a mount with direction+state + Add button, + the empty state) + tsc --noEmit clean + esbuild build clean; keel validate/guard green. Realizes nComposedVaults (Phase 4 UX). REMAINING before v1: the owner's on-device pass, then the release."; }
        part mountUxDoDR1 : TestResult { :>> id = "a1b2c3d4-3904-4a10-9b20-d3904c0de048"; :>> outcome = VerdictKind::pass; :>> judgedAgainst = "69857e3"; :>> judgedAt = "2026-08-08"; :>> judgedBy = "claudeOpus"; }
        // ===== composed-vaults hardening sweep (owner-directed: "5 more rounds of critique, diligently implement one after the other"). NO release. =====
        action mountHardeningR1;
        verification mountHardeningR1DoD : Test { :>> id = "a1b2c3d4-3905-4a10-9b20-d3905c0de049"; :>> method = VerificationMethod::test; :>> procedureText = "Hardening Round 1 (independent critique, lens: CONCURRENCY & LIFECYCLE races). ENGINE-INTERNAL, NO release. FIXED: F1/F5 MED — an add/reconnect during an in-flight detached mount pass was DROPPED by the re-entrancy guard and never rebuilt (rebuild only fired on initial||empty), so a new mount silently never started AND its folder — already excluded from the primary scope — synced to NOBODY; fix: rebuild EVERY pass (preserve-by-key + add/drop to match the configured set) + defer a mid-pass request (mountReconcilePending) and re-run on release. F2 MED — mount source transports capture the session token by value; a reactive-401 relogin rotated it but the old scope was preserved → 401 forever; fix: track mountScopesToken, drop+rebuild all scopes on rotation (base+cursor survive in mountStateStore → resume). F3 MED (data-touching) — an in-flight pass could mutate the DISK for a just-removed mount before the onEvent guard; fix: removeMount marks the scope 'unmounting' first + reconcileMountScopes re-checks an isLive predicate before driving each scope. F4 LOW-MED — a detached pass could write to the vault after teardown/unload; fix: isLive returns false when unloading + the deferred re-run is suppressed while unloading. CONFIRMED SAFE: the guard can't stick, no two-pass overlap, persist single-flight coalescing, cache sharing, MountRuntime isolation. Guards: full client vitest 693 (new mountsync isLive-skip test) + tsc + build clean; keel validate/guard green."; }
        part mountHardeningR1DoDR1 : TestResult { :>> id = "a1b2c3d4-3905-4a10-9b20-d3905c0de050"; :>> outcome = VerdictKind::pass; :>> judgedAgainst = "dcd13d0"; :>> judgedAt = "2026-08-08"; :>> judgedBy = "claudeOpus"; }
        action mountHardeningR2;
        verification mountHardeningR2DoD : Test { :>> id = "a1b2c3d4-3906-4a10-9b20-d3906c0de051"; :>> method = VerificationMethod::test; :>> procedureText = "Hardening Round 2 (independent critique, lens: DATA INTEGRITY & CORRUPTION). ENGINE-INTERNAL, NO release. FIXED: F1 HIGH (silent data loss) — a PULL mount's first-contact over a pre-existing DIFFERENT local file called adoptRemote with NO conflict copy (readOnly took the fresh-share adopt-over-local path), destroying the user's version — and composing a pull mount over a populated folder is the primary use case; fix: opt-in ReconcileDeps.preserveLocalFirstContact (default OFF → a fresh read-only SHARE + the primary unchanged), mounts set it → a no-base first-contact divergence takes readOnlyKeepCopy (keep the local as a conflict copy + adopt the source, push nothing). F2 MED — the emptyManifest bulk-delete guard is a whole-vault index-loss heuristic that on a legitimately-emptied source SUBTREE refuses forever and was SILENT (onGuard unwired); fix: wire onGuard (toast+log) so the stall is visible, keep the fail-safe (also protects the mount from a source index-loss wipe). F3 MED — the mount hardcoded reset:false + left onKeptAbsent unwired so a SYNC mount could SILENTLY resurrect a peer's deletion into the shared source; fix: wire onKeptAbsent (toast+log) so a keep/restore is visible (a PULL mount can't resurrect — read-only); full D0019 reset-detection for mounts is the tracked follow-up issueMountResetDetection. CONFIRMED CORRECT: base/cursor persist atomically, cursor never skips an in-subtree change, per-mount isolation, removeMount/addMount handoff non-destructive, merge ancestor sound under re-keyed paths. Guards: full client vitest 695 (planMerge firstContactKeepCopy case + a new end-to-end pull-mount-over-existing-file conflict-copy test; full reconcile suite 169 green — the shared flag is opt-in/default-off) + tsc + build clean; keel validate/guard green. Realizes nComposedVaults (hardening)."; }
        part mountHardeningR2DoDR1 : TestResult { :>> id = "a1b2c3d4-3906-4a10-9b20-d3906c0de052"; :>> outcome = VerdictKind::pass; :>> judgedAgainst = "8ac8975"; :>> judgedAt = "2026-08-08"; :>> judgedBy = "claudeOpus"; }
        action mountHardeningR3;
        verification mountHardeningR3DoD : Test { :>> id = "a1b2c3d4-3907-4a10-9b20-d3907c0de053"; :>> method = VerificationMethod::test; :>> procedureText = "Hardening Round 3 (independent critique, lens: BOUNDARY & PATH-TRANSLATION adversarial). ENGINE-INTERNAL, NO release. A coherent hardening pass on the pure path/validation layer. FIXED: H1 HIGH — the boundary compare (claimsLocal/mountRelFromLocal/mountRelFromSource/validateMounts) was case-sensitive, so on a case-insensitive FS a case-drifted folder LEAKED to the primary vault while the mount synced nothing (split-brain); fix: segment-based NFC + case-FOLDED matching (matching the codebase's isDataPath/shouldSync convention), rel keeps REAL case for round-trip — also fixes M4 (Unicode NFC/NFD) + M5 (two mounts over one folder by case). H2 HIGH — a mount anchored under .obsidian could pull another vault's config as data or EXFILTRATE SelfSync's credential data.json to the source (read→push); fix: validateMounts REJECTS any mount point or source subfolder inside .obsidian (→ activeMounts empty → dormant + Save disabled) AND ObsidianVaultIo.read/exists refuse a config path on a mount io (defense-in-depth closing the read→push vector). M1 MED — mountKey delimiter-joined form could collide two distinct mounts whose fields contain #/=/> (a folder named 'C#') onto one key → shared base/cursor; fix: JSON-encode the components (collision-free). M3/L2 — a mount point with stray whitespace / trailing dot / backslashes persisted verbatim → inert mount + leak; fix: new normMountFolder sanitizes user config at the parse boundary + the modal draft. L1 — normFolder now drops '..' (defense-in-depth over asSafeVaultPath). CONFIRMED SAFE: segment-boundary safety (ASIx≠ASI), trailing-slash mount point, whole-source .obsidian exclusion both directions, activeMounts() at every primary sink incl. switchTo + config reconcile, activeMounts fail-safe, pull read-only, .obsidianX false-positive. ACCEPTED L3 (duplicate-source-to-multiple-locals — a valid pattern, not blocked). Guards: full client vitest 702 (new adversarial mounts tests: case-insensitive boundary, NFC/NFD, case-dupe reject, .obsidian mount/source reject, normMountFolder sanitize, normFolder .. drop; mountKey non-collision) + tsc + build clean; keel validate/guard green. Realizes nComposedVaults (hardening)."; }
        part mountHardeningR3DoDR1 : TestResult { :>> id = "a1b2c3d4-3907-4a10-9b20-d3907c0de054"; :>> outcome = VerdictKind::pass; :>> judgedAgainst = "bb5c0c6"; :>> judgedAt = "2026-08-08"; :>> judgedBy = "claudeOpus"; }
        action mountHardeningR4;
        verification mountHardeningR4DoD : Test { :>> id = "a1b2c3d4-3908-4a10-9b20-d3908c0de055"; :>> method = VerificationMethod::test; :>> procedureText = "Hardening Round 4 (independent critique, lens: FAILURE, RECOVERY & RESOURCE). ENGINE-INTERNAL, NO release. FIXED: F1 HIGH — the mount status FOLD (mountfsm/mountStatusSummary) had ZERO callers, so a silently offline/failed PULL mount showed green 'Fully synced' while the composed notes went stale; fix: effectiveLightPhase ESCALATES a resting primary to attention when a mount problem exists + paintLight surfaces which mount in the tooltip (finishes the #101 status-light fold). F2 MED — a failed mount never auto-recovered (the FSM retry was never dispatched); fix: a failed scope resets to detached after a backoff (MOUNT_FAILED_RETRY_MS=5min via failedAt) + a detached scope is started on ANY pass, so recovery + newly-added mounts take effect. F3 MED — onPullExhausted + onSkip were unwired, so a permanently-corrupt or over-size source file was silently missing; fix: wire both (notice + log). F4 MED — mounts never checked the SOURCE vault readiness (unlike the primary), so a source mid-reindex serving a partial manifest could drive a spurious delete-local; fix: a sourceReady() probe (source status()==='ready') gates the first-contact/reconnect pass — a not-ready source holds the mount OFFLINE, never reconciles a degraded manifest. CONFIRMED SAFE: fail-isolation (both layers), no unbounded hang (30s transport timeout), 503/degraded can't mass-delete (throw + emptyManifest/ratio/own DeleteRateGuard + onGuard), shared chunk cache bounded, per-mount isolation, no-session spins harmlessly, detached re-run bounded, pull read-only, removed/unmounting skipped mid-pass. NOTE (D0040 by-design): a pull mount lags ~60s (poll cadence). Guards: full client vitest 703 (new R4-F4 not-ready-source-held-offline test) + tsc + build clean; keel validate/guard green. Realizes nComposedVaults (hardening)."; }
        part mountHardeningR4DoDR1 : TestResult { :>> id = "a1b2c3d4-3908-4a10-9b20-d3908c0de056"; :>> outcome = VerdictKind::pass; :>> judgedAgainst = "5666fd6"; :>> judgedAt = "2026-08-08"; :>> judgedBy = "claudeOpus"; }
        action mountHardeningR5;
        verification mountHardeningR5DoD : Test { :>> id = "a1b2c3d4-3909-4a10-9b20-d3909c0de057"; :>> method = VerificationMethod::test; :>> procedureText = "Hardening Round 5 / FINAL (independent critique, lens: SECURITY + holistic 'what did R1-R4 miss'). ENGINE-INTERNAL, NO release. Critique verdict: SAFE TO SHIP for an on-device beta — NO exploitable breach (credential/.obsidian isolation, path-traversal containment, cross-vault non-leakage on push, token routing, per-scope isolation all verified solid + layered). FIXED: MED-1 — the `diverged` FSM state was UNREACHABLE (a mounted-folder conflict only logged → green light, violating honest-status); fix: MountRuntime.tookConflict drives the scope to `diverged` ('Needs review', surfaced on the light + card), cleared to live on a clean pass. MED-3 — one invalid hand-edited mount deactivated ALL mounts (activeMounts all-or-nothing) → primary re-absorbed their folders + uploaded source-derived content; fix: validMounts() returns the maximal valid non-overlapping SUBSET (a bad entry drops only itself). LOW-3 — switching the primary onto a mount's source → self-referential double-sync; fix: activeMounts excludes a mount of the current primary (auto-dormant after a switch). LOW-1 — MountedApi.putChunk wasn't pull-gated (the no-write-on-pull guarantee rested on reconcile, not the adapter); fix: putChunk hard-refuses on a pull mount. LOW-2 — ignorePatterns weren't applied inside mounts; fix: passed through. CONFIRMED SAFE (verified): credential/.obsidian exclusion airtight across every sink; no cross-vault content leak on push (commit chunks only the file's own bytes, never the shared cache); malicious-source traversal/huge/delete-flood/bad-chunk caught; token routing correct (encodeURIComponent'd /api/u/{owner}/{vault}); scope isolation; persistence round-trips; push/pull preview respects the boundary. MED-2 (moving a file out of a SYNC mount deletes it from the source — correct-but-surprising) recorded as issueMountCrossBoundaryMove (documented + rename/move-safety follow-up). Guards: full client vitest 703 (R2-F1 conflict test now asserts diverged→live) + tsc + build clean; keel validate/guard green. Realizes nComposedVaults (hardening — 5-round adversarial sweep complete)."; }
        part mountHardeningR5DoDR1 : TestResult { :>> id = "a1b2c3d4-3909-4a10-9b20-d3909c0de058"; :>> outcome = VerdictKind::pass; :>> judgedAgainst = "42b1449"; :>> judgedAt = "2026-08-08"; :>> judgedBy = "claudeOpus"; }
        action mountHardeningR6;
        verification mountHardeningR6DoD : Test { :>> id = "a1b2c3d4-3910-4a10-9b20-d3910c0de059"; :>> method = VerificationMethod::test; :>> procedureText = "Hardening Round 6 (independent critique, lens: MOBILE / PLATFORM-SPECIFIC). ENGINE-INTERNAL, NO release. FIXED: Med-1 — mounts were skipped on every IDLE (noop) primary poll (reconcileAllOnce returned at mode==='noop' before the reconcileMounts() call), so a source change didn't pull until the primary changed / the 15-min full scan / a reconnect (composed notes lag ~15min behind a green light; a non-dropping background→foreground resume didn't refresh mounts); fix: run reconcileMounts() on the noop branch too → mounts poll at the ~60s cadence (D0040). Med-2 — mobile OOM: the single-maxSyncMB refactor dropped the old 50-MiB mobile cap, so a mount (no streamed writer on mobile → buffers whole files ×FILE_CONCURRENCY) could buffer up to the 200-MiB desktop default and crash the WebView; fix: clamp the MOUNT's maxSyncBytes to 50 MiB on Platform.isMobile — a larger file is skipped + noticed (onSkip), never buffered (scoped to the mount; the primary user setting untouched). VERIFIED (specific points): MountedIo mirrors the base appendWrite capability (mobile→buffered fallback, not a broken stream); the mount io never enumerates .obsidian on mobile; mount base isolation holds; mounts get scan-skip + run reconcileDelta steady-state (no periodic whole-subtree re-hash). NOT fixed (un-verified / pre-existing, surfaced for on-device judgement, NOT silently changed): a possible iOS NFD-vs-NFC rel-key mismatch (may be masked by Obsidian's own normalization; a blind change risks a Linux regression) + mount deletes hard-unlinking on mobile where the adapter lacks trashLocal (pre-existing general behaviour). Both fixes are main.ts glue — verified by tsc + esbuild build + full client vitest 703 (no regression); the LIVE poll-cadence + mobile size-gate behaviour is NOT verified without an on-device run. Realizes nComposedVaults (hardening)."; }
        part mountHardeningR6DoDR1 : TestResult { :>> id = "a1b2c3d4-3910-4a10-9b20-d3910c0de060"; :>> outcome = VerdictKind::pass; :>> judgedAgainst = "ec6e661"; :>> judgedAt = "2026-08-10"; :>> judgedBy = "claudeOpus"; }
        action mountHardeningR7;
        verification mountHardeningR7DoD : Test { :>> id = "a1b2c3d4-3911-4a10-9b20-d3911c0de061"; :>> method = VerificationMethod::test; :>> procedureText = "Hardening Round 7 (independent critique, lens: PROTOCOL/WIRE + server-contract). ENGINE-INTERNAL, NO release. VERIFIED clean (traced): source responses get the SAME transport validation as the primary (malformed FileMeta throws pre-reconcile → offline, no disk mutation); retryBudget/onPullExhausted wired (hash-mismatch/404/reordered chunks → per-file skip + budget); commit CAS uses the source-global version + server-set author. FIXED: F1 MED — the mount checked source readiness but NOT apiVersion, and sessionToken persists after a version-mismatched primary connect, so a mount could poll a protocol-incompatible source (shape guards catch structural, not semantic, wire changes); fix: sourceReady() also runs versionVerdict(status().apiVersion, CLIENT_API_VERSION) and holds the mount OFFLINE on a mismatch. F2 LOW — fetchVerified checked hash but not size on the BUFFERED path (which mobile mounts always take; streamed path already checks both); fix: reject a FileMeta whose declared size disagrees from the assembled bytes (per-file isolated integrity hardening). NOT fixed (noted): F3 LOW — a hand-edited config dropping a shared source's owner mis-routes to your own namespace (UI never produces it; parseMounts can't distinguish a valid own-vault owner:'' from a dropped one; impact = your-own-other-vault, not a leak). Guards: full client vitest 703 (reconcile + mountsync + real-server e2e green — the size check didn't disturb happy paths) + tsc + build clean; F1 is main.ts glue + F2 mirrors an existing checked path — live behaviour un-verified without an on-device run against a version-mismatched/size-lying source. Realizes nComposedVaults (hardening)."; }
        part mountHardeningR7DoDR1 : TestResult { :>> id = "a1b2c3d4-3911-4a10-9b20-d3911c0de062"; :>> outcome = VerdictKind::pass; :>> judgedAgainst = "8550563"; :>> judgedAt = "2026-08-10"; :>> judgedBy = "claudeOpus"; }
        action mountHardeningR8;
        verification mountHardeningR8DoD : Test { :>> id = "a1b2c3d4-3912-4a10-9b20-d3912c0de063"; :>> method = VerificationMethod::test; :>> procedureText = "Hardening Round 8 (independent critique, lens: PERSISTENCE & STATE DURABILITY). ENGINE-INTERNAL, NO release. VERIFIED clean (traced): cursor never persisted ahead of base (onEvent only after a full pass; no onBaseChanged wired for mounts); coalesced persist re-snapshots base+mountState+settings (no lost write); a live mount prunes base on a source delete; a remove-during-in-flight-pass can't resurrect the key. FIXED: F1 MED — mountStateStore orphaned keys were never GC'd (only removeMount prunes), so a mount identity change outside the UI (hand-edit → new mountKey, future edit-in-place, an old-format key) stranded a full base snapshot in data.json forever → bloat; fix: loadSettings prunes mountStateStore to currently-configured keys (this.mounts()); a dropped key re-first-contacts (non-destructive). F3 LOW — parseMountState cast normHash/size/mtime unchecked (a type-wrong normHash can flip edit-wins→delete-local); fix: rebuild a clean BaseEntry, keeping only string hash/text/normHash + finite ≥0 size/mtime. F2 LOW (latent, unreleased) — documented mountKey as a PERSISTENCE CONTRACT (a shape change once shipped must bump dataSchemaVersion + migrate); the F1 prune degrades a future format change to first-contact, not bloat. NOT fixed (tracked): F4 LOW — a mount dormant because the primary switched onto its source, reactivated after switching back, restores a stale base → spurious conflict copies (recoverable); recorded as issueMountDormantStaleBase (follow-up mountBaseFreshness). Guards: full client vitest 703 (parseMountState field-validation extended) + tsc + build clean. F1 is loadSettings glue — live prune-on-load un-verified without an on-device restart with a stale key. Realizes nComposedVaults (hardening)."; }
        part mountHardeningR8DoDR1 : TestResult { :>> id = "a1b2c3d4-3912-4a10-9b20-d3912c0de064"; :>> outcome = VerdictKind::pass; :>> judgedAgainst = "351fc2c"; :>> judgedAt = "2026-08-10"; :>> judgedBy = "claudeOpus"; }
        action mountHardeningR9;
        verification mountHardeningR9DoD : Test { :>> id = "a1b2c3d4-3913-4a10-9b20-d3913c0de065"; :>> method = VerificationMethod::test; :>> procedureText = "Hardening Round 9 (independent critique, lens: CORRECTNESS OF THE RECONCILE-ENGINE REUSE over a prefix-translated subtree). ENGINE-INTERNAL, NO release. VERIFIED clean (traced): the filtered manifest never false-infers a deletion (a source-present base path is always in the filtered manifest); cursor/versionOf + failed-pull hold behave with source-global versions + filtered manifest; config path is dead code in mount space; the concurrency pool + reconcile state are per-call/per-runtime (only the content-addressed cache is shared); scan-skip stamps are per-store. FIXED: Finding C Low/Med — a mount discarded reconcileAll's response + hardcoded reset:false, so a source reindex/version-REWIND could leave it stale; fix: pollMount detects delta.version<cursor → routes through the engine reset → full reconcile (re-pull the subtree); full D0019 reset-detection stays tracked (issueMountResetDetection). Finding B Low — documented (by design): the timestamp-ignore patterns apply in a mount but the primary's excludedFolders per-folder opt-out does not (primary-relative paths, not translatable to a source subtree) → a mount masks all .md uniformly (churn/cosmetic only). SURFACED, NOT unilaterally changed — Finding A Med: the bulk-delete guard is whole-vault-calibrated, so on a small mount SUBTREE the empty-manifest override + 0.5 ratio over-block NORMAL source deletions (non-convergent) while a <6-file mount is under-guarded — a data-safety POSTURE tradeoff recorded as issueMountDeleteGuardCalibration with the options, for the maintainer to decide (mitigations present: R4-F4 readiness check, .trash, R2-F2 onGuard). Guards: full client vitest 704 (new R9-C rewind→full-re-pull test) + tsc + build clean; keel validate/guard ALL PASS. Rewind fix unit-verified against a fake source; live reindex un-verified. Realizes nComposedVaults (hardening)."; }
        part mountHardeningR9DoDR1 : TestResult { :>> id = "a1b2c3d4-3913-4a10-9b20-d3913c0de066"; :>> outcome = VerdictKind::pass; :>> judgedAgainst = "d23fb6d"; :>> judgedAt = "2026-08-10"; :>> judgedBy = "claudeOpus"; }
        action mountHardeningR10;
        verification mountHardeningR10DoD : Test { :>> id = "a1b2c3d4-3914-4a10-9b20-d3914c0de067"; :>> method = VerificationMethod::test; :>> procedureText = "Hardening Round 10 / FINAL (independent critique, lens: UX/interaction exhaustiveness + fresh eyes). ENGINE-INTERNAL, NO release. Main cluster the prior 9 rounds missed: the status LIGHT folds mount health but the settings tab's own surfaces didn't. FIXED: F1 MED — the settings Status HERO was primary-only (green 'Fully synced' while a mount was down); fix: the hero dot paints the FOLDED phase (plugin.lightPhase(), same as the ribbon) + the desc names the mount problem, live via statusListener. F2 MED — per-mount rows weren't live; fix: a debounced settings re-render (bumpMountUi) on each mount onEvent. F3 MED — the 'no mounts active' banner was false for a partially-invalid set; fix: base it on the real in-effect set (activeMounts()) + report only the inactive COUNT ('N of M inactive — the rest still syncing'). F4 MED — 'Add mount' had no in-flight guard (double-click → duplicate); fix: claim the submit + disable before the await, re-enable on failure. F6/F7 LOW — a row now reads 'waiting to connect' or names why it's inactive (invalid/overlap, or source==primary) not a bare 'Not started'. F3b LOW — corrected a stale comment. VERIFIED clean: zero-mount fold, busy-never-escalates, Esc/Cancel/backdrop (onDone only on a real save), add-then-remove race, remove-confirm copy, path sanitization/i18n. NOTED not changed: F5 (stale add-modal dropdown if the vault list changes while open) + F8 (a FAILED mount's light escalation masked while the primary is transiently busy — tooltip still shows it). Guards: full client vitest 706 (new settings-ui.dom tests: inactive-count banner + hero mount sub-line) + tsc + build clean; keel validate/guard green. Settings-surface changes DOM-tested via happy-dom; live on-device rendering un-verified. Realizes nComposedVaults (hardening — the owner-directed second 5-round sweep, R6-R10, complete)."; }
        part mountHardeningR10DoDR1 : TestResult { :>> id = "a1b2c3d4-3914-4a10-9b20-d3914c0de068"; :>> outcome = VerdictKind::pass; :>> judgedAgainst = "6c1f239"; :>> judgedAt = "2026-08-10"; :>> judgedBy = "claudeOpus"; }
        // Backlog: full D0019 reset-detection for mounts (resolver for issueMountResetDetection, R2-F3 follow-up).
        action mountResetDetection;
        verification mountResetDetectionDoD : Test { :>> id = "bb440682-a5a3-4212-b39f-050f94c677f3"; :>> method = VerificationMethod::test; :>> procedureText = "DONE (green @ e288ed4): resolves issueMountResetDetection (R2-F3) — full D0019 source deletion-history reset detection for mounts, the per-mount analogue of the primary's historyResetDetected. A mount polls its source via changes(since) and previously detected ONLY a version-REWIND reset (delta.version < cursor); it MISSED a history_floor ADVANCE — when the source truncates its deletion history (a reindex), tombstones for files deleted before the new floor are gone, so a delta poll silently misses those deletions and the files linger (a sync mount could even re-push them). FIX: track a per-mount historyFloor (added to MountPersist {base,version,historyFloor} + parsed defensively; MountRuntime historyFloor()/noteHistoryFloor()/toPersist), and in pollMount route floorAdvanced (priorFloor!==undefined && delta.history_floor > priorFloor) OR rewound to a FULL reconcile (decideReconcileMode reset->full even with noChange). reconcileAll then re-scans and KEEPS absent-without-tombstone files via onKeptAbsent (per-file user Notice) instead of trusting the truncated delta. The first floor observation just SEEDS (priorFloor===undefined guard), never a false reset; old data.json without historyFloor -> undefined -> seed (backward-compatible superset, no destructive migration). INDEPENDENT CRITIQUE (findings-only, no overall verdict per owner instruction) drove three fixes, each with a regression test: F1 (Med-High) advance the floor ONLY after a SUCCESSFUL reconcile so a failed/partial reset pass re-fires next poll instead of spending the one-shot signal (mounts have no periodic full-scan; mirrors the primary's floor-after-reconcile); F3 (Low) noteHistoryFloor is MONOTONIC (a lower reported floor can't arm a spurious later reset); F4 (Low) parseMountState drops a sub-genesis floor (0/negative; server genesis is 1). F2 (a sync mount re-pushing a peer-deleted absent-without-tombstone file) was assessed PRE-EXISTING D0019 behavior on every mount full pass with a per-file Notice — not introduced here, left to the reconcile semantics that match the primary. Client-only, NO release (batched with the composed-vaults cluster). DoD MET: tsc clean, full client vitest 768 passed (6 new: 3 reset-detection [floor-advance full pass, seed-not-reset, floor round-trips persist] + 3 critique fixes [F1 re-fire on failure, F3 monotonic, F4 parse]), production build clean, keel validate + guard green."; }
        part mountResetDetectionDoDR1 : TestResult { :>> id = "dc5160b1-06cb-4b66-97dd-135337e27e29"; :>> outcome = VerdictKind::pass; :>> judgedAgainst = "e288ed4"; :>> judgedAt = "2026-08-12"; :>> judgedBy = "claudeOpus"; }
        // Backlog: cross-boundary rename/move safety for sync mounts (resolver for issueMountCrossBoundaryMove, R5-MED-2 follow-up). RESOLVED by DECISION (D0044, accept-as-is), not a build.
        action mountMoveSafety;
        verification mountMoveSafetyDoD : Test { :>> id = "e45693f1-016e-4de4-8366-f08195cdbf7f"; :>> method = VerificationMethod::confirmation; :>> procedureText = "OWNER DISPOSITION (D0044, accept-as-is): whether a cross-boundary MOVE-OUT of a sync mount (dragging a note out of the mounted folder) should be prevented from deleting the file on the possibly-shared SOURCE. The AI presented three options (hold+confirm / auto-keep-on-source / accept-current) with an initial 'a move isn't really a delete' framing; the owner (2026-08-13) challenged it ('it really is [a delete] for the source, no? ... practical counterexamples? If not, delete is fine'). The AI justified that for shared-folder membership leaving the folder IS leaving the source, that a MOVE (vs COPY) is the explicit remove gesture, found NO compelling counterexample, and the owner's conditional 'delete is fine' resolved it to ACCEPT — delete-remote on move-out is correct sync semantics; no move-detection or confirmation added, no code change. Companion Decision D0044 records the full rationale. Resolves issueMountCrossBoundaryMove."; }
        part mountMoveSafetyDoDR1 : TestResult { :>> id = "cd9fcf51-2074-41ce-94b3-a95ba0a4564c"; :>> outcome = VerdictKind::pass; :>> judgedAgainst = "e288ed4"; :>> judgedAt = "2026-08-13"; :>> judgedBy = "wweatherholtz"; }
        // Backlog: per-mount base-freshness stamp (resolver for issueMountDormantStaleBase, R8-F4 follow-up).
        action mountBaseFreshness;
        verification mountBaseFreshnessDoD : Test { :>> id = "21fdff4b-3aad-48ac-87c8-289d47b34519"; :>> method = VerificationMethod::test; :>> procedureText = "DONE (green @ 492bfac): resolves issueMountDormantStaleBase (R8-F4). A mount whose SOURCE is the current primary vault is self-referentially dormant (activeMounts excludes it, R5-LOW-3), and while it is dormant the PRIMARY sync owns + rewrites that same local folder — so the mount's persisted base (mountStateStore[mountKey]) silently goes STALE. Restoring that stale base when the mount reactivates (the primary switches away) made reconcile see BOTH local AND source diverged from base -> SPURIOUS conflict copies. FIX: invalidateSelfReferentialMountBases(owner, vaultId) drops the persisted base of every configured mount whose source matches, so reactivation re-first-contacts (non-destructive: matching local content is adopted as base, only real divergence makes a real copy). Called CENTRALLY in rebuildMountScopes — reached by EVERY repoint via reconnect (switchToVault, the setup-wizard direct-sets, a redeem, a pendingSwitch replay) and AFTER doTeardown has cleared mountScopes, so an in-flight pass of the now-dormant mount cannot resurrect the dropped base (its write-back guard finds no live scope) — plus explicitly in loadSettings for the cross-session case (booting already ON the source). INDEPENDENT CRITIQUE (findings-only, no overall verdict per owner instruction) ran pre-commit: drove the central relocation, which closes F1 (Medium — the setup-wizard adoptRedeemed/finish direct-set paths that bypass switchToVault) and F2 (Low-Med — a write-back race that could resurrect the dropped base); over-dropping (an extra non-destructive first-contact) + owner-matching + data-loss were checked clean. Client-only, NO release (batched with the composed-vaults cluster). DoD MET: tsc clean, full client vitest 762 passed (2 new mountBaseFreshness plugin-wiring tests: rebuildMountScopes central drop + loadSettings cross-session drop), production build clean, keel validate + guard green."; }
        part mountBaseFreshnessDoDR1 : TestResult { :>> id = "5da75c59-ac7c-4411-8815-3c935277783c"; :>> outcome = VerdictKind::pass; :>> judgedAgainst = "492bfac"; :>> judgedAt = "2026-08-12"; :>> judgedBy = "claudeOpus"; }
        // ===== D0041 — user-configurable incoming bulk-delete confirmation (resolves the R9-A calibration issue). NO release (staged). =====
        action bulkDeleteConfirm;
        verification bulkDeleteConfirmDoD : Test { :>> id = "a1b2c3d4-4100-4a10-9b20-d4100c0de069"; :>> method = VerificationMethod::test; :>> procedureText = "Realizes D0041 (owner-directed + accepted): replace the fixed bulk-delete ratio/empty-manifest guard + the cumulative DeleteRateGuard with a user-configurable INCOMING-delete confirmation, and make OUTGOING deletes exact. (1) Outgoing (local→server) propagates exactly — no bulk gate; the per-file absence re-probe stays. (2) Incoming (server/source tombstone batch) is gated by settings.bulkDeleteStrategy (off|count|percent) + bulkDeleteThreshold (default count/10): over threshold ⇒ HELD (not applied) + surfaced non-blockingly (Conflicts section: Delete-them=apply / Keep-them=re-push-or-keep-local, both converge). Global policy per scope (primary + mounts — supersedes the R9-A mount calibration issue). The not-ready-source FLOOR is unchanged. reconcile.ts: bulkDeleteHold (pure, fail-CLOSED on invalid threshold); finalize drops the outgoing guard; reconcileAll/Delta gate the incoming batch (count only tombstoned-and-local); DeleteRateGuard+runDeleteGuard removed (isSuspiciousBulkDelete retained for switch/single-path); applyHeldDeletions/keepHeldDeletions. settings/main/mountengine/mountsync: the 2 settings + Advanced control + review surface + the per-scope pending set + Accept/Keep. INDEPENDENT CRITIQUE (engine + full D0041 review) run pre-commit; FIXED F1 HIGH (the pending review was cleared by the next poll → vanish + re-nag + click-race; now PERSISTS — full pass replaces, delta unions, toast on growth), F2 MED (Keep now forces a full re-push pass), F3 MED (single-path guard toast is log-only, no dead-end review claim), F4/F5/F6/F7 LOW (predicate fail-closed; count only tombstoned; mount Accept/Keep refresh mountStateStore; feedback when a scope isn't live); CONFIRMED direction split + primary-Accept convergence + strict `>` threshold. Guards: full client vitest 712 (bulkDeleteHold table incl. fail-closed; finalize direction; reconcileDelta hold-over/apply-below; e2e delete-last-file now PROPAGATES; review-surface + Advanced-control DOM; MountRuntime held-collection) + tsc + esbuild build clean; keel validate/guard green. NO release (staged with composed vaults). BEHAVIOUR CHANGE to the primary sync — un-verified on-device."; }
        part bulkDeleteConfirmDoDR1 : TestResult { :>> id = "a1b2c3d4-4100-4a10-9b20-d4100c0de070"; :>> outcome = VerdictKind::pass; :>> judgedAgainst = "74e4ce7"; :>> judgedAt = "2026-08-10"; :>> judgedBy = "claudeOpus"; }
        verification sittingReview20260807b : Test { :>> id = "7a0d8f07-0807-4a10-9b20-a1b2c3d40809"; :>> method = VerificationMethod::confirmation; :>> procedureText = "Per-sitting human review (D0049) for the 2026-08-07 SECOND sitting — the composed-vaults Phase 2 engine-adapter work begun after the owner signed off the first 08-07 sitting and directed 'proceed'. Covers the composed-vaults (D0039) engine build, driven autonomously after the owner directed 'proceed until finished, I'll critique later': mountIoAdapters (the MountedIo/MountedApi two-sided prefix-translating adapters + the isDataPath data-only boundary), mountEngineCore (the MountRuntime structural base/state isolation + per-mount FSM + aggregate status fold), and mountEngine (the live sync loop + main.ts wiring — a second concurrent, POLL-DRIVEN [D0040], fail-isolated sync scope, DORMANT until a mount is configured). Each behaviour/data-touching increment went through an independent antagonistic security critique (+ a re-verify pass on the live glue) that caught + fixed real defects — a deleteFile data-only asymmetry, a normFolder round-trip bug, a fileMeta config-leak, a case-fold bypass, and — the big one — a HIGH A1 where the mount had reused the primary's filtered io (mount writes dropped + a reconnect would delete-remote the SOURCE vault), now fixed with a separate data-only mount io; issueMountBaseIsolation is resolved (per-mount base isolation structurally enforced + critique-re-confirmed). ALL engine-internal — no user-facing behaviour, NO release yet (the Phase 4 UI is the first consumer). HONESTLY PENDING: the owner has NOT reviewed any of this on-device; R1 stamped only on that explicit review. Each increment's closeOut/retro runs autonomously (D0049); this single confirmation is the sitting's human gate."; }
        action wireSignatureServer;
        verification wireSignatureServerDoD : Test { :>> id = "54e3b306-09cb-4e9d-bdce-6a6eff520123"; :>> method = VerificationMethod::test; :>> procedureText = "DONE (green @ c7e41ff): Sprint 1 of 2 for D0042 (client<->server wire compatibility) — the SERVER half. The server DERIVES a canonical wire-contract signature from its own serde types via schemars (the 13 core sync/auth/status protocol types in protocol.rs get #[derive(JsonSchema)]); wire_signature.rs builds a normalized, deterministic document {endpoints[] (the client-facing route set), types{name -> [{name,type,required}]}} and a cached sha256 schema_hash. StatusResponse gains schema_hash (#[serde(default)] so an OLDER server decodes as an empty string and the client FAILS CLOSED); GET /schema (unauthenticated, every surface) returns the full signature; schemaHash added to /status (3 construction sites) + /health liveness. Committed artifact server/wire-signature.json + a drift-gate cargo test (committed_artifact_matches_generated) that fails CI on any unreviewed wire change (srContractDriftGate; regenerate via UPDATE_WIRE_SIGNATURE=1 cargo test). ADDITIVE + backward-compatible — no sync behaviour change; the accept/reject verdict is the client Sprint 2 (wireCompatClient). Satisfies srWireSignature + srContractDriftGate. DoD: full server cargo test (222 passed) + clippy -D warnings clean + coverage floor --fail-under-lines 89 holds + keel validate/guard green. Shared server-shape change -> server-image redeploy required at release; NOT yet released (ships with the client half + an independent pre-release critique)."; }
        part wireSignatureServerDoDR1 : TestResult { :>> id = "351680b6-15b3-4736-a022-3b587e146dea"; :>> outcome = VerdictKind::pass; :>> judgedAgainst = "c7e41ff"; :>> judgedAt = "2026-08-11"; :>> judgedBy = "claudeOpus"; }
        action composedMountPathUx;
        verification composedMountPathUxDoD : Test { :>> id = "3be42a58-d838-43f6-8f1a-23986894221a"; :>> method = VerificationMethod::test; :>> procedureText = "BACKLOG (owner field feedback 2026-08-11): composed-mount PATH handling — autofill + validate the source subfolder, create the local target, add folder-existence sane defaults. Today the source subfolder is free text with NO existence validation (mountsettings.ts:107-108); the source folder set IS derivable from a source-scoped changes(0) listing (transport.ts:271, mountio.ts:64) but nothing uses it, so a mistyped sourcePath silently pulls an empty set and can trip the bulk-delete guard (main.ts:2257). The local mount-point folder is created only LAZILY on first write (main.ts:251-252), so an empty or mistyped source never materializes it. FIX (needs a short design pass first — this is the nComposedVaults spike): populate/validate the source subfolder from the derived folder list so the user picks a KNOWN-VALID path; eagerly ensure the local mount point exists when a mount is added; warn or block before activating a mount whose source path matches nothing. Resolves issueMountPathValidationAndDefaults. DoD: source subfolder chosen-from or validated-against real source folders + local target created on add + invalid path prevented/warned; client vitest + keel validate/guard green."; }
        part composedMountPathUxDoDR1 : TestResult { :>> id = "7ca431e9-fae9-4b14-9dd6-87398127cac0"; :>> outcome = VerdictKind::pass; :>> judgedAgainst = "97b59d5"; :>> judgedAt = "2026-08-11"; :>> judgedBy = "claudeOpus"; }
        action composedMountPermissions;
        verification composedMountPermissionsDoD : Test { :>> id = "dda83314-0101-45ba-8f1a-239871c096ca"; :>> method = VerificationMethod::test; :>> procedureText = "BACKLOG (owner field feedback 2026-08-11): composed-mount PERMISSION + read-only edit semantics. (a) There is NO in-place change of a mount from read-only (pull) to read-write (sync) — the only ops are add + remove (main.ts:2332-2349), and remove+re-add DROPS the persisted base/cursor (main.ts:2349); add an edit/permission-change path that flips direction without losing sync state. (b) On a READ-ONLY mount, a local edit to a composed file whose source is unchanged is KEPT on disk and only REPORTED (reconcile.ts:79-81 reportReadOnly then onReadOnly), never pushed and never reverted — so it lingers as an un-syncable local divergence that re-notifies every poll and never converges (a conflict copy only appears if the source later diverges, reconcile.ts:118). Decide + implement the intended behavior (e.g. offer discard-my-edit or fork-to-a-writable-copy, or make the non-syncing state unmistakable) rather than a silent perpetual divergence. Resolves issueMountRoToRwChange + issueMountRoLocalEditBehavior. DoD: a mount permission can change RO to RW in place keeping its base; the RO local-edit outcome is a defined, user-legible behavior; client vitest + keel green."; }
        part composedMountPermissionsDoDR1 : TestResult { :>> id = "1b50cb49-dba2-4d01-9124-6052d75e2c2b"; :>> outcome = VerdictKind::pass; :>> judgedAgainst = "df66c61"; :>> judgedAt = "2026-08-12"; :>> judgedBy = "claudeOpus"; }
        action pluginSyncSettingsHierarchy;
        verification pluginSyncSettingsHierarchyDoD : Test { :>> id = "64fda774-6f16-4dba-8f1a-23987a324c72"; :>> method = VerificationMethod::test; :>> procedureText = "BACKLOG (owner field feedback 2026-08-11): plugin-sync settings UX hierarchy + note placement. (a) The Synced community plugins group (settings.ts:722, renderPluginChecklist) and the actual synced-plugin list (settings.ts:790, the N-synced collapsible in renderPluginRows) are FLAT SIBLINGS in the same container, not a hierarchy — nest the plugin list UNDER the community-plugins section so the toggle owns its list. (b) The Greyed Push/Pull already-in-sync note (settings.ts:764-766) sits in the community-plugins summary group, one section ABOVE the collapsible list that actually holds the per-row Push/Pull buttons it explains (settings.ts:828-829); the PushPreviewModal already states it inline next to the disabled action (pushpreviewmodal.ts:39-40,59). Move the note next to the buttons (it rides along once the list is nested). Resolves issuePluginListHierarchy + issueGreyedNoteWrongSection. DoD: the synced-plugin list renders nested under the community-plugins section and the greyed note sits with the Push/Pull controls; settings-ui.dom test + client vitest + keel green."; }
        part pluginSyncSettingsHierarchyDoDR1 : TestResult { :>> id = "bd80e57b-3883-4581-9b3e-dbbfaa1b80bf"; :>> outcome = VerdictKind::pass; :>> judgedAgainst = "373ac91"; :>> judgedAt = "2026-08-12"; :>> judgedBy = "claudeOpus"; }
        action wireCompatClient;
        verification wireCompatClientDoD : Test { :>> id = "07f2aac3-fa8b-49ab-a51d-372f7522d329"; :>> method = VerificationMethod::test; :>> procedureText = "DONE (green @ 93ec089): Sprint 2 of 2 for D0042 — the CLIENT half + independent pre-ship critique addressed. The client decides compatibility by a DIRECTIONAL diff of the server wire-contract signature (fetched via GET /schema, VERIFIED against the /status schemaHash before trust — F1) against the embedded signature this build was compiled against, replacing the single-integer versionVerdict. Response types: a read field removed/retyped/newly-omissible (required->optional, F2) is breaking, new fields additive; request types: a field the server now requires that the client does not send, or a retype of a sent field, is breaking. API_VERSION is folded into the signature as a SEMANTIC EPOCH (F3) so a shape-identical semantic bump is caught. Refuse on breaking with the SPECIFIC field/endpoint (surfaced on the status card), proceed on additive/identical (a bugfix never rejects); fail CLOSED on an absent hash or a /schema whose self-declared hash does not match the advertised one. An independent antagonistic critique (7 findings) ran before ship: F1/F2/F3 fixed, F6/F7 doc-synced, F4+F5 backlogged (issueEndpointsRouterDrift + issueSharingResponseTypesUncovered via wireSignatureCoverageHardening). Satisfies srCompatVerdict + srCompatFailClosed. DoD: server 225 tests + clippy clean, tsc clean, full client vitest 734 passed incl. real-server e2e (the wrapped /schema handshake works live), production build clean, keel validate/guard green. Ships as a PLUGIN release WITH the server-image redeploy (D0042 rollout: server exposes /schema before/with clients)."; }
        part wireCompatClientDoDR1 : TestResult { :>> id = "17e49b8f-1cc3-4974-99af-ed9f125a358c"; :>> outcome = VerdictKind::pass; :>> judgedAgainst = "93ec089"; :>> judgedAt = "2026-08-11"; :>> judgedBy = "claudeOpus"; }
        action wireSignatureCoverageHardening;
        verification wireSignatureCoverageHardeningDoD : Test { :>> id = "f15b13f9-58e2-4c5f-a51d-372f7c837b41"; :>> method = VerificationMethod::test; :>> procedureText = "DONE (green @ 79151e9): the D0042 critique follow-ups F4+F5 — wire-signature COVERAGE hardening. F4 (issueEndpointsRouterDrift): the ENDPOINTS list (wire_signature.rs) is hand-maintained and the drift gate is generated FROM it, so it could silently diverge from the real axum router (a removed route left in the list -> the client proceeds -> a runtime 404 loop). Exposed wire_signature::declared_endpoints() and added server/tests/wire_signature_routes.rs, which probes every declared endpoint on the built app() router (path params concretized) and asserts not-404 (route exists). F5 (issueSharingResponseTypesUncovered): the field-level types map covered the 13 core protocol types but NOT the sharing responses the client consumes (SharedVault via /api/shared, VaultShares+GrantView via /api/admin/vaults, LinkInfo via /api/share-links). Added schemars::JsonSchema to those types (+ Perm) and brought them into the signature types map; regenerated both wire-signature.json artifacts. Added client-side runtime validators (validateSharedVaults/validateVaultShares/validateShareLinks + validateRedeemedVault/validateRedeemedRegister), wired into the transport, so a malformed/hostile body throws instead of reaching the vault-switcher/share UI as an unchecked cast. Compat consequence (intended): a post-F5 client now expects the server to DECLARE the sharing types, so it refuses-safe against a pre-F5 server ('update whichever is older', notes untouched) — consistent with the existing 'server missing an embedded type = breaking' rule; ships as a plugin release WITH the server-image redeploy. Resolves issueEndpointsRouterDrift + issueSharingResponseTypesUncovered. DoD MET: server 147 tests + clippy clean, tsc clean, full client vitest 754 passed (incl. 8 new sharing-validate), production build clean, keel validate + guard green."; }
        part wireSignatureCoverageHardeningDoDR1 : TestResult { :>> id = "06d85f75-e837-4452-81a2-abfafc0e223a"; :>> outcome = VerdictKind::pass; :>> judgedAgainst = "79151e9"; :>> judgedAt = "2026-08-12"; :>> judgedBy = "claudeOpus"; }
        action mountSyncPushLocal;
        verification mountSyncPushLocalDoD : Test { :>> id = "a11fe2e6-0348-4a7e-a7a5-84efc528d792"; :>> method = VerificationMethod::test; :>> procedureText = "BUG (owner field report 2026-08-11, CONFIRMED by trace): a SYNC (read-write) composed mount does not PUSH local edits back to the source in steady state. Root cause: pollMount (mountsync.ts:30-44) is SOURCE-driven — it calls changes() on the source, then reconcileDelta (applies the source delta = pull) when the source changed, or noop+returns when it did not; only a FORCED FULL pass (reconcileAll, on first-mount/reconnect/Keep) scans LOCAL files. So a local edit in a sync-mount folder whose source is unchanged is never scanned or pushed — mounts react to source changes, never to local changes (unlike the primary, which is driven by local file events). FIX: make a local file event under a mount point trigger a full (local-scanning) reconcile for that mount (forceFull), mirroring the primary's local-event handling, so a sync mount pushes local edits promptly. DoD: a local create/edit/delete in a sync-mount folder propagates to the source vault (headless mount sync test with a fake source api asserting a commit/deleteFile on a local-only change); client vitest + keel green. Resolves issueMountRwPushBack."; }
        part mountSyncPushLocalDoDR1 : TestResult { :>> id = "2de405f7-c391-44dc-9dd6-873987678790"; :>> outcome = VerdictKind::pass; :>> judgedAgainst = "97b59d5"; :>> judgedAt = "2026-08-11"; :>> judgedBy = "claudeOpus"; }
        action mountLiveSubscription;
        verification mountLiveSubscriptionDoD : Test { :>> id = "cce55fb7-1b14-4cd6-a7a5-84efd0882a66"; :>> method = VerificationMethod::test; :>> procedureText = "DONE (green @ c5fa7d6): resolves issueMountPollNotEventDriven — realizes D0039's deferred per-mount 'own subscription' (D0040 kept it deferred, explicitly behind the MountRuntime/MountScope seam). Each HEALTHY active mount opens a live WS to its SOURCE vault (buildMountApi().connectWs) so a source change syncs PROMPTLY instead of on the ~60s poll; the poll stays the backstop. CLIENT-ONLY — the server /api/ws handler already authorizes a shared-source Read subscription (authorized(owner,vault,user,Access::Read)) and re-checks the ACL per notification, so no server change. syncMountSubscriptions() (run AFTER the scope pass each reconcile cycle) keeps the socket set: closes sockets for mounts leaving the healthy+active set, opens one per healthy active mount, poke -> reconcileMounts (re-entrancy-guarded + fail-isolated; an own-push echo converges to a noop). Sockets also close on token rotation, doTeardown, and remove-last-mount. INDEPENDENT CRITIQUE (findings-only, no overall verdict per owner instruction) drove the gating, each with a test: F1 (Medium) gate on the PRIMARY link being up (engine connecting/reconciling/idle), not just unloading — else a user disconnect/pause + a mount-setting change would silently reopen a source subscription while the primary is intentionally offline; F3 (Low-Med) only a HEALTHY scope (live/diverged) holds a socket — a failed/offline source is driven by the poll's backoff, not an unbounded per-cycle WS reconnect; F4 (Low) buildMountApi throws (not just null) on an insecure remote -> caught. F2 (half-open, no per-mount liveness): the primary WS's liveness->reconnect cycles the mount sockets (spinUpWs -> closeMountSockets), recovering the correlated same-server half-open; the poll backstop keeps data correct meanwhile. F5 (own-push echo) converges via the re-entrancy guard; F6 (vault-level poke) noops for out-of-subtree changes — both bounded/inherent, noted. Client-only, released with the composed-vaults cluster. DoD MET: tsc clean, full client vitest 771 passed (3 mountLiveSubscription plugin-wiring tests: open/poke/close, drop-reopen, and the F1/F3/F4 gates), production build clean, keel validate + guard green."; }
        part mountLiveSubscriptionDoDR1 : TestResult { :>> id = "d7845738-deb7-4ccf-8934-f454128b0cce"; :>> outcome = VerdictKind::pass; :>> judgedAgainst = "c5fa7d6"; :>> judgedAt = "2026-08-13"; :>> judgedBy = "claudeOpus"; }
        action mountOutgoingDeleteDecision;
        verification mountOutgoingDeleteDecisionDoD : Test { :>> id = "fea701c8-c4bb-4410-a642-aaa7b162abdc"; :>> method = VerificationMethod::confirmation; :>> procedureText = "DECISION NEEDED (owner disposition): whether an OUTGOING delete from a SYNC composed mount to a possibly-shared source vault should require a confirmation. Surfaced by the mountSyncPushLocal critique (F1). The push-back nudge makes a local delete under a sync-mount folder propagate to the source PROMPTLY (a full pass on the local delete event) instead of only on the next reconnect. This is CONSISTENT with D0041 (outgoing deletes are honored exactly, no bulk gate, by owner decision) and receiving peers are still protected by THEIR incoming bulk-delete confirmation (D0041) before their local copies go — but the immediacy + the shared-source blast radius are new. OPTIONS: (a) accept as-is (outgoing-exact per D0041; peers gated on receive) — record a Decision; (b) add a confirmation for a mount OUTGOING delete-remote to a NON-owned (shared) source over the user's bulk threshold. Resolves issueMountOutgoingDeleteImmediate once the owner picks (a Decision, and a guard if (b))."; }
        part mountOutgoingDeleteDecisionDoDR1 : TestResult { :>> id = "f4b1363e-345e-4960-bbd2-4bf20ca57f78"; :>> outcome = VerdictKind::pass; :>> judgedAgainst = "5b0b66c"; :>> judgedAt = "2026-08-11"; :>> judgedBy = "wweatherholtz"; }
        action mountNudgeHardening;
        verification mountNudgeHardeningDoD : Test { :>> id = "f06e2737-e73b-40c0-a642-aaa7bc7bc74c"; :>> method = VerificationMethod::test; :>> procedureText = "DONE (green @ f9e6542): the mountSyncPushLocal critique follow-ups F4+F7 — test + micro-optimize the push-back nudge. F4: extracted the nudge DECISION into a pure mounts.nudgeTarget (the claimsLocal filter + the recentSelfWrites echo-skip) and refactored nudgeMountForLocalPath onto it — direction-agnostic on purpose (a sync mount pushes the edit; a PULL mount surfaces it promptly as a read-only conflict, the read-only io still can't write the source, so both want the prompt local scan). Tests: a nudgeTarget unit table (claims-a-sync-mount, claims-a-pull-mount, outside-every-mount, empty set, own-pull-write echo-skip) + a plugin-wiring test that fires a REAL modify event under a configured mount and asserts the scope goes forceFull (and an echo / an outside path do NOT). F7: memoized activeMounts() (runs on every primary file event; validMounts is O(n^2)) on a cheap signature of the raw mount set + primary identity, so a burst of saves recomputes at most once; self-invalidating (any add/remove/edit/switch changes the signature) so there is no scattered invalidation to keep in sync — plugin-wiring test asserts same-reference on a cache hit + a recompute after the set changes. Resolves issueMountNudgeCoverage. Client-only, NO release (batched). DoD MET: tsc clean, full client vitest 760 passed (26 mounts + 44 plugin-wiring incl. the new 6), production build clean, keel validate + guard green."; }
        part mountNudgeHardeningDoDR1 : TestResult { :>> id = "5226a401-a10d-47db-ac9c-22ef65b88166"; :>> outcome = VerdictKind::pass; :>> judgedAgainst = "f9e6542"; :>> judgedAt = "2026-08-12"; :>> judgedBy = "claudeOpus"; }
        action mountFolderDeleteGuard;
        verification mountFolderDeleteGuardDoD : Test { :>> id = "294b94c1-92ad-4e8e-9324-694b0d751b7a"; :>> method = VerificationMethod::test; :>> procedureText = "BUG/HAZARD (owner-raised 2026-08-11): deleting the LOCAL mount-point FOLDER (the whole container) on a SYNC mount currently propagates as a full source-subtree delete-remote — wiping the mounted subtree from the (possibly shared) source vault. Enabled by the mountSyncPushLocal push-back + D0043 (outgoing exact): deleting the folder fires a delete per child -> nudge -> forceFull -> delete-remote each. A container deletion reads as remove/reset-the-mount, NOT delete-all-these-shared-files, so this must never wipe the source. FIX (owner chose flag-and-choose): detect the mount-point folder is gone while the mount had content (base non-empty) -> do NOT reconcile/propagate (the critical safety) -> flag the mount (new state, surfaced on the status + settings) as local-folder-deleted with two actions: Reinstate (drop base + re-create folder + full re-pull from source) and Remove mount (detach, source preserved). No automatic action. Distinguish from a fresh never-materialized mount (base empty -> normal pull, creates the folder). DoD: a headless test that a mount whose local root is deleted with a non-empty base does NOT delete-remote (source untouched) and flags; a fresh mount still pulls; Reinstate re-pulls; client vitest + keel green. Resolves issueMountFolderDeletedWipesSource."; }
        part mountFolderDeleteGuardDoDR1 : TestResult { :>> id = "ba85804f-9e63-4dea-ad92-dff4cddda6a6"; :>> outcome = VerdictKind::pass; :>> judgedAgainst = "f570917"; :>> judgedAt = "2026-08-12"; :>> judgedBy = "claudeOpus"; }
        action mountDeleteGuardHardening;
        verification mountDeleteGuardHardeningDoD : Test { :>> id = "7e5d4824-3fa1-4695-af51-4417d03de8ef"; :>> method = VerificationMethod::test; :>> procedureText = "DONE (green @ 308c6a7): resolves issueMountDeleteGuardResiduals (mountFolderDeleteGuard re-critique residuals). FINDING 5 (transient/partial list -> spurious localGone) FIXED: massLocalDeletion trusted io.list() at face value — a transient empty/partial listing (adapter hiccup, mid-write, unhydrated cloud placeholder) looked like a mass deletion and held the mount as localGone (fail-safe, but a needless manual Reinstate). Now RE-PROBES each list-absent path via io.exists (indeterminate-treat-as-present): a file still on disk is not counted absent, so a partial/empty list can't trip the guard — mirroring reconcileAll's own per-file false-absence re-probe (issueFalseAbsenceDelete) that backstops the actual delete-remote. Cheap in the common case (few absent -> tiny loop); the full re-probe only runs when a mass deletion is SUSPECTED (rare), where confirming absence before a possible shared-source wipe is worth the stat calls. Self-critiqued: the change only REDUCES false-positive holds (never enables a wipe — if io.exists false-positived a deleted file, reconcileAll would also see it present and not delete; the mass-guard is an ADDITIONAL coarse gate, the per-file re-probe is the real delete gate). FINDING 2 (paced sub-floor drain) MOOTED by D0043: outgoing deletes are exact/immediate, so each sub-floor batch is a legitimate exact deletion (gated on the receive side by each peer's incoming bulk-delete confirmation, D0041); the proposed outgoing-hold would re-introduce exactly the outgoing gate D0043 rejected. The mass-guard's job is only the one-shot catastrophic wipe — recorded in the guard comment, no outgoing hold added. Client-only, released with the composed-vaults cluster. DoD MET: tsc clean, full client vitest 774 passed (2 new: a transient-empty list + a partial list do NOT flag localGone; the genuine-wipe guards still fire), production build clean, keel validate + guard green."; }
        part mountDeleteGuardHardeningDoDR1 : TestResult { :>> id = "07de31cd-219f-459a-a8a9-ddf4041b4873"; :>> outcome = VerdictKind::pass; :>> judgedAgainst = "308c6a7"; :>> judgedAt = "2026-08-13"; :>> judgedBy = "claudeOpus"; }
        action mountSharedDirectionToggle;
        verification mountSharedDirectionToggleDoD : Test { :>> id = "f0241cab-2ba6-4ab4-810f-74ef58bc4290"; :>> method = VerificationMethod::test; :>> procedureText = "DONE (green @ 7e8dc44): resolves issueMountSharedDirectionToggle (composedMountPermissions critique F5). The in-row direction toggle (Pull<->Sync) was offered only for OWN-vault sources (source.owner === empty); a SHARED source that is legitimately read-WRITE (grant perm=readWrite) mounted as Pull for safety then couldn't be switched to Sync in the UI — conflating direction (whether to push) with permission (whether the grant allows writing). FIX: the settings tab lazily loads which shared sources are read-write (listSharedVaults, once per tab lifetime; SAFE non-writable default until it resolves, then a re-render), and canToggleDirection(m) offers the toggle when the source is OWN or shared-readWrite. A shared read-ONLY source stays fixed at Pull (the grant forbids pushing). Client-only UI (the server still enforces the grant on any push). DoD MET: tsc clean, settings-ui.dom 24 passed (new test: a shared read-write mount gets the toggle, a shared read-only one does not), full client vitest + keel green. Released with the composed-vaults cluster."; }
        part mountSharedDirectionToggleDoDR1 : TestResult { :>> id = "88b75c10-7c55-4793-b18c-298bc181c729"; :>> outcome = VerdictKind::pass; :>> judgedAgainst = "7e8dc44"; :>> judgedAt = "2026-08-13"; :>> judgedBy = "claudeOpus"; }
        // ===== 1.27.1 — hardening from the owner-requested 5-pass critique of the 1.27.0 cluster (2026-08-13). =====
        action v1271CritiqueHardening;
        verification v1271CritiqueHardeningDoD : Test { :>> id = "32f31a71-56c4-448e-b2eb-cd6bca103ac4"; :>> method = VerificationMethod::test; :>> procedureText = "DONE (green @ 3a3d2fa): the owner requested a 5-PASS independent critique of the shipped 1.27.0 composed-vaults/wire cluster (lenses: data-loss, concurrency/lifecycle, wire-compat, state/persistence, security/trust-boundary), then an independent VERIFY pass over the fixes. FIXED (each with a regression test): (1) WIRE GATE was refusing ALL sync against a 1.24-1.26 server merely because it didn't DECLARE the additive sharing types/endpoints — made the sharing TYPES + share/admin ENDPOINTS non-gating (core sync proceeds; drift still hash-detected; runtime validators still reject bad share data; only the share UI degrades). (2) FLOOR RE-BASELINE: the monotonic history-floor stayed at high-water after a source version-rewind, leaving a blind band where a later truncation was missed (a push mount could resurrect a peer's deletions) — a rewind is AUTHORITATIVE, re-baseline to observed (clearing if the source stops reporting a floor). (3) DELETE-GUARD conservative bias: the io.exists re-probe had collapsed the listing+exists oracles, so a flapping exists could split below threshold and wipe a subset from a shared source — now the LISTING decides suspected-mass, then HOLD if ANY path is confirmed-absent, suppress only on a clean all-present transient. (4) MOUNT WS DEBOUNCE: a per-notification poke fragmented a PACED incoming deletion below the D0041 bulk-delete threshold so the confirmation never fired — coalesce a burst into one pass. (5) removeMount now closes its WebSocket (was leaked). (6) activeMounts() memo array frozen (latent aliasing); (7) parseMountState floor tightened to a >=1 safe integer; (8) router-drift test guards against a future router fallback silently no-opping it; corrected the mountBaseFreshness comments to name the real re-entrancy invariant. VERIFY pass refined 3 more: the wire-gate endpoint symmetry (share endpoints non-gating too), the rewind clearing an undefined floor, and the parseMountState comment honesty. DEFERRED (owner not directed to fix; tracked as backlog issues + resolvers): issueMountSharedSourceResurrection (D0019 keep-and-push on a shared source — a design call), issueWirePermVariantBlindSpot (Perm variants invisible to the hash — loud-fail, share-UI-only after the non-gating fix), issueMountReadOnlyRailDirectionKeyed (readOnly rail keyed on direction not grant — server-enforced), issueMountHalfOpenSocketLiveness (no per-mount WS liveness — poll-backstopped). Security lens found NO breach. Client-only (+ a server TEST; the server binary is unchanged from 1.27.0 → 1.27.1 is a PLUGIN-ONLY release). DoD MET: tsc clean, full client vitest 779 passed, production build clean, keel validate + guard green."; }
        part v1271CritiqueHardeningDoDR1 : TestResult { :>> id = "c611c81f-d805-4243-8675-b498fd4ebc3e"; :>> outcome = VerdictKind::pass; :>> judgedAgainst = "3a3d2fa"; :>> judgedAt = "2026-08-13"; :>> judgedBy = "claudeOpus"; }
        // Backlog resolvers for the deferred 5-pass critique findings (design-calls / hardening, not directed this pass):
        action mountSharedSourceResurrectionPolicy; // resolver for issueMountSharedSourceResurrection
        verification mountSharedSourceResurrectionPolicyDoD : Test { :>> id = "e4969c6d-d65c-42c1-ad12-e74839b7054a"; :>> method = VerificationMethod::test; :>> procedureText = "DONE (green @ 5013007): resolves issueMountSharedSourceResurrection AND the owner-directed EXPANSION of its resolution (2026-08-14). The prior noResurrect flag kept an absent-without-tombstone SHARED-source file local without re-pushing, but an independent critique of the batch found it covered only ONE of the three paths a peer-deleted file can take. Owner chose EXPAND SCOPE, accepting a shared-mount behavior change. FULL fix (client-only, all in reconcile.ts + the mount/plugin/settings wiring): (F1) a LOCAL EDIT to a file the source deleted (edit-wins-keep-local, which fires ONLY when the remote is absent, so live collaboration never routes through it) is KEPT LOCAL, never re-pushed. (F2) a MASS batch of local-only-new files bound for a shared source (a base-loss re-first-contact would resurrect a peer's whole tombstone-pruned deletion set; equally a legitimate large seed) is HELD via a new Settings->Conflicts review row (Keep-local / Push them), mirroring the D0041 bulk-delete guard and reusing its threshold; resolved by applyHeldPushes (upload) / keepHeldPushes (stabilize kept-local). Incremental adds stay below threshold and push normally; own vaults (noResurrect false) seed freely; read-only (pull) mounts still win over the push guard. THREE independent antagonistic critique passes each caught a HIGH, each fixed + regression-tested: (H1) a LIVE (un-pruned) tombstone is definitive deletion evidence, so such a path routes straight to keep-local in finalize (never held, never pushed, never deleted) BEFORE the guard check, keeping the held set tombstone-free; (H2 resolve-time race) keepHeldPushes SCREENS current source tombstones before stamping a base, so a peer deletion becoming visible between the hold and the users Keep-local choice can never re-assert as removeLocal; computeBulkPushHold excludes tombstoned paths from both numerator and percent denominator. DEFERRED lower findings tracked as issues (issueMountPushGuardThresholdCoupling, issueMountReconcilePathPushUnguarded, issueMountHeldResolverSerialization). Client-only, PLUGIN-ONLY release (no server change). DoD MET: tsc clean, full client vitest 795 passed (+ finalize F1/F2 table, mountsync F1/F2/live-tombstone/resolve-race, settings-ui held-push row), production build clean, keel validate + guard green."; }
        part mountSharedSourceResurrectionPolicyDoDR1 : TestResult { :>> id = "0fadd4f0-8471-4adc-83db-7c0b2f810b44"; :>> outcome = VerdictKind::pass; :>> judgedAgainst = "5013007"; :>> judgedAt = "2026-08-14"; :>> judgedBy = "claudeOpus"; }
        action wirePermVariantCoverage;             // resolver for issueWirePermVariantBlindSpot
        verification wirePermVariantCoverageDoD : Test { :>> id = "8ca9ed90-e03e-4e9a-995e-a11a55c07bd6"; :>> method = VerificationMethod::test; :>> procedureText = "DONE (green @ 5013007): resolves issueWirePermVariantBlindSpot. transport.asPerm previously THREW on any permission value other than read/readWrite, which rejected the WHOLE shared-vault / share-link list (the share + vault-switch UI failed to load) whenever a server sent an unknown/future Perm variant - and Perm variants are invisible to the wire signature (an enum has no fields), so the compat gate cannot pre-empt it. FIX (client-only): asPerm now FAILS CLOSED - readWrite maps to readWrite, and EVERYTHING else (a hostile string OR a future variant like admin) degrades to the least-privilege read rather than throwing. A new variant is treated as read-only until the plugin is updated, never escalated. Identity fields (owner/vault/grantee) stay strict (still throw on a non-string). Client-only, PLUGIN-ONLY. DoD MET: tsc clean, sharing-validate vitest updated (unknown perm coerces to read, whole list no longer rejected), full client vitest 795 passed, production build clean, keel validate + guard green."; }
        part wirePermVariantCoverageDoDR1 : TestResult { :>> id = "825d4bef-7681-4f14-804d-9024f80785dc"; :>> outcome = VerdictKind::pass; :>> judgedAgainst = "5013007"; :>> judgedAt = "2026-08-14"; :>> judgedBy = "claudeOpus"; }
        action mountReadOnlyRailFromGrant;          // resolver for issueMountReadOnlyRailDirectionKeyed
        verification mountReadOnlyRailFromGrantDoD : Test { :>> id = "ed8827c9-2a3f-4a27-a493-d8e2f7aa72a0"; :>> method = VerificationMethod::test; :>> procedureText = "DONE (green @ da2b6cd): resolves issueMountReadOnlyRailDirectionKeyed (5-pass critique, security lens F1). A mount's write hard-refuse keyed only on direction==='pull', so a shared source held under a READ grant but driven as 'sync' (hand-edited past the UI, or a grant downgraded RW->R after the toggle) ran the read-WRITE path and 403'd every push — a stuck-failing scope with the read-only UX (keep-my-edits) lost. FIX (client-only): the plugin caches each shared source's write-grant (refreshSourceGrants from /api/shared, refreshed on connect when shared mounts exist) and the mount readOnly is now `direction==='pull' || mountSourceReadOnly(mount)`, evaluated PER reconcile pass (deps() is per-call) so a downgrade is honored on the next pass with no scope rebuild. FAIL-CLOSED: own source (owner '') always writable; a shared source writable ONLY on a known readWrite grant (unknown/read -> read-only, never push into a source we can't prove we may write). The ctx callback is OPT-IN (runtimes not passing it keep the direction-only behavior, so the reconcile tests are unaffected). SELF-CRITIQUED (not a full independent pass — the change is strictly MORE conservative: it only ADDS read-only conditions, never enables a write, and the server enforces the grant regardless, so it cannot cause a wrongful write; worst case is an over-conservative delay if the grant fetch fails, self-healing on the next connect). Client-only, 1.27.4 plugin-only. DoD MET: tsc clean, full client vitest 785 passed (new: deps().readOnly honors the sourceReadOnly callback per-pass; mountSourceReadOnly own/readWrite/read/unknown), production build clean, keel validate + guard green."; }
        part mountReadOnlyRailFromGrantDoDR1 : TestResult { :>> id = "cc23677b-5a50-4ceb-bacd-749972bbfd37"; :>> outcome = VerdictKind::pass; :>> judgedAgainst = "da2b6cd"; :>> judgedAt = "2026-08-14"; :>> judgedBy = "claudeOpus"; }
        action mountSocketLiveness;                 // resolver for issueMountHalfOpenSocketLiveness
        verification mountSocketLivenessDoD : Test { :>> id = "fa5b0118-5d83-4e86-afa3-408714078ba5"; :>> method = VerificationMethod::test; :>> procedureText = "DONE (green @ 5013007): resolves issueMountHalfOpenSocketLiveness. A per-mount WebSocket can HALF-OPEN independently of the primary (its own source subscriptions TCP dies while the primary stays healthy); the server keepalive is a protocol Ping invisible to JS onmessage and JS cannot send pings, so the client cannot detect a zombie socket directly, and recovery previously depended on the PRIMARY also going stale. FIX (client-only): syncMountSubscriptions periodically RECYCLES the mount sockets (close -> reopened by the loop) about every 15 min so any zombie recovers within one interval; the ~60s poll is the backstop meanwhile. Wall-clock (Date.now) based and piggybacked on the poll-driven sync - NOT a per-mount setTimeout (D0040), so it is resilient to Obsidian mobile timer suspension - and seeded on first use (no churn at t0). Client-only, PLUGIN-ONLY. DoD MET: tsc clean, plugin-wiring vitest added (an old recycle clock closes+reopens the sockets; within-interval does not), full client vitest 795 passed, production build clean, keel validate + guard green."; }
        part mountSocketLivenessDoDR1 : TestResult { :>> id = "8b5a87c0-2805-458c-b57b-fa23a900f087"; :>> outcome = VerdictKind::pass; :>> judgedAgainst = "5013007"; :>> judgedAt = "2026-08-14"; :>> judgedBy = "claudeOpus"; }
        // Deferred resolvers for the F1/F2 expansion critique findings (2026-08-14) — tracked, not fixed this pass.
        action mountPushGuardDedicatedControl;      // resolver for issueMountPushGuardThresholdCoupling
        verification mountPushGuardDedicatedControlDoD : Test { :>> id = "6cb3b571-cd2e-45f8-a745-6e13784ee023"; :>> method = VerificationMethod::test; :>> procedureText = "DONE (green @ 9df35d4): resolves issueMountPushGuardThresholdCoupling. The F2 bulk-push-to-shared guard reused the INCOMING bulk-delete strategy/threshold, so setting that to 'off' silently disabled the push guard AND a partial base loss below a HIGH user threshold slipped un-held - both resurrecting a peer's deletions. FIX (client-only, reconcile.ts): computeBulkPushHold now holds if the user's ACTIVE incoming-delete gate trips OR the raw local-only-new count exceeds a built-in floor SHARED_PUSH_FLOOR (10 files), whichever is stricter - a TRUE floor that 'off', a higher user threshold, or percent mode cannot weaken, because it protects a PEER's vault. Own-vault mounts (noResurrect false) short-circuit before the floor, so seeding your own vault is untouched; live-tombstoned paths stay excluded from both numerator and percent denominator. INDEPENDENT CRITIQUE (findings-only) drove the true-floor rewrite (the initial version applied the floor only as an 'off' fallback, leaving the high-threshold hole) and confirmed no under-hold vs prior + no spurious over-hold. Client-only, PLUGIN-ONLY. DoD MET: tsc clean, mountsync vitest added (mass push held with strategy 'off' AND with an active higher threshold), full client vitest green, production build clean, keel validate + guard green."; }
        part mountPushGuardDedicatedControlDoDR1 : TestResult { :>> id = "0f5af856-b34f-4955-a6d8-e294a9ecc4d4"; :>> outcome = VerdictKind::pass; :>> judgedAgainst = "9df35d4"; :>> judgedAt = "2026-08-14"; :>> judgedBy = "claudeOpus"; }
        action mountReconcilePathPushUnreachable;   // resolver for issueMountReconcilePathPushUnguarded — a not-reachable ANALYSIS (no code), self-evidencing (D0051)
        verification mountReconcilePathPushUnreachableDoD : Test { :>> id = "c6cfbc7d-67f2-4809-ad0f-a302f793c18c"; :>> method = VerificationMethod::analyze; :>> procedureText = "DONE (green @ 9df35d4): resolves issueMountReconcilePathPushUnguarded by a not-reachable ANALYSIS (no code change; a clarifying comment only). The critique flagged that the F2 bulk-push-to-shared guard is not threaded into the single-event route reconcilePath. Trace shows the premise does not hold: (a) reconcilePath is invoked ONLY as reconcilePath(this.deps(), path, size) (reconcilePathOnce) — the PRIMARY vault deps, which never set noResurrect; (b) noResurrect is assigned ONLY in mountengine.ts MountRuntime.deps() (a shared MOUNT source, owner != ''); (c) composed-mount folders are excluded from the primary accepts() filter and are POLL-driven (D0040) — a mount-folder local edit nudges the mount subsystem (nudgeMountForLocalPath => reconcileAll/reconcileDelta), never reconcilePath; (d) reconcileDelta emits no local-only-new push (not in a server delta), so a mount's local-only-new push is emitted ONLY by reconcileAll, which already carries computeBulkPushHold + the H1 live-tombstone screening. Therefore d.noResurrect is always false in every reconcilePath call and the F2 guard is unreachable there. The initially-drafted defensive reconcilePath change (a per-event manifest/tombstone probe on a base-null noResurrect case) was REVERTED as dead code; reconcile.ts now carries a one-line comment stating reconcilePath is primary-only. If a future change routes a noResurrect scope through reconcilePath, that is the trigger to add the guard. method=analysis is self-evidencing (D0051) — the trace is the evidence, no human attestation required. Client-only, no behavior change vs the F1/F2 release."; }
        part mountReconcilePathPushUnreachableDoDR1 : TestResult { :>> id = "c1291413-c2f3-4375-a561-ebb63618f050"; :>> outcome = VerdictKind::pass; :>> judgedAgainst = "9df35d4"; :>> judgedAt = "2026-08-14"; :>> judgedBy = "claudeOpus"; }
        action mountHeldResolverSerialize;          // resolver for issueMountHeldResolverSerialization
        verification mountHeldResolverSerializeDoD : Test { :>> id = "9ee7af5c-176e-4860-86b5-d86c6f427a15"; :>> method = VerificationMethod::test; :>> procedureText = "DONE (green @ 9df35d4): resolves issueMountHeldResolverSerialization. The held-review resolvers (accept/keep bulk push + bulk delete) and keepRoMountEdits mutated a MOUNT scope's base directly from settings-UI button callbacks, able to interleave with an in-flight poll-driven reconcile pass touching the same base. FIX (client-only, main.ts): a chained-promise mutex (mountWork) shared by mount reconcile PASSES (reconcileMounts body wrapped) and the resolvers (runScopeExclusive) - a mount resolver waits behind any in-flight pass and vice-versa; the pre-existing mountReconciling flag still coalesces fire-and-forget pass requests. runScopeExclusive ALSO re-resolves depsForScope INSIDE the lock (a rebuild during the wait may recreate the scope's BaseStore, else the mutation hits an orphaned base). keepRoMountEdits's whole base-mutating section (base.delete, mountStateStore, clearRoMountEdits, persist, io.remove) is wrapped too. INDEPENDENT CRITIQUE drove three fixes: the true mutex (F2), the keepRoMountEdits wrap (F1 coverage gap), and the fresh-deps re-resolve (F4 stale-deps window); VERIFY confirmed no deadlock (persist/io/applyHeld* never re-enter), chain liveness on throw (release in finally, mountWork resolve-only), and the !ok path is correct (fn never ran -> review persists). The PRIMARY-scope analogue is a distinct, pre-existing gap tracked as issuePrimaryHeldResolverSerialization (deferred). Client-only, PLUGIN-ONLY. DoD MET: tsc clean, plugin-wiring vitest added (runMountExclusive serialises overlapping work), full client vitest green, production build clean, keel validate + guard green."; }
        part mountHeldResolverSerializeDoDR1 : TestResult { :>> id = "726d86d7-df9b-4290-92b6-160a57453869"; :>> outcome = VerdictKind::pass; :>> judgedAgainst = "9df35d4"; :>> judgedAt = "2026-08-14"; :>> judgedBy = "claudeOpus"; }
        action primaryHeldResolverSerialize;        // resolver for issuePrimaryHeldResolverSerialization (primary analogue)
        verification primaryHeldResolverSerializeDoD : Test { :>> id = "79f2c3d6-e816-4dea-b975-45c8df7aeda0"; :>> method = VerificationMethod::test; :>> procedureText = "DONE (green @ 62169e8): resolves issuePrimaryHeldResolverSerialization - the primary analogue of the mount held-resolver race. The primary-scope accept/keep bulk-delete resolvers mutated this.base from a settings-UI callback OUTSIDE the engine's serial event queue, able to interleave with an in-flight primary reconcile pass. FIX (client-only): a new {kind:'task'} SyncEngine event runs a resolver's base mutation run-to-completion, serialized with reconciles (the primary has no boolean guard - its passes ARE serialized by the engine, so the resolver joins that queue via enqueuePrimaryTask); runScopeExclusive's primary branch routes through it, the mount branch keeps its runMountExclusive mutex. INDEPENDENT CRITIQUE + a VERIFY pass caught two ways a queued task could be DROPPED (-> the resolver's promise hangs forever + a silent no-op): (HIGH) failWith (any reconcile failure) dropped the task -> now PRESERVES it (local base work, safe after a link failure; pump drains it, the promise settles); (MEDIUM) the disconnect handler's blanket queue-clear dropped it -> now preserves tasks too; plus an unloading pre-check that returns false (-> the 'reconnecting' notice) instead of enqueuing into a torn-down queue. VERIFY confirmed the HIGH closed on the failWith path + all six lenses (preserved task actually runs, ordering, no re-processing loop, safe-while-disconnected, unloading pre-check race-free, no other queue-clearing path). Client-only, PLUGIN-ONLY (1.29.1). DoD MET: tsc clean, full client vitest 808 passed (+ syncengine task-serialises / survives-failure / survives-disconnect / isolated-throw), production build clean, keel validate + guard green."; }
        part primaryHeldResolverSerializeDoDR1 : TestResult { :>> id = "373e9970-1a1a-4c11-973b-5783067a1441"; :>> outcome = VerdictKind::pass; :>> judgedAgainst = "62169e8"; :>> judgedAt = "2026-08-14"; :>> judgedBy = "claudeOpus"; }
        // ===== 1.27.2 — field bug fix: the self-redeem "revoked"-and-block-all-sync trap (owner-reported 2026-08-14). =====
        action selfRedeemVaultOwnerFix;
        verification selfRedeemVaultOwnerFixDoD : Test { :>> id = "6602ae1c-54a9-43b2-a0f7-f3ef9d20016f"; :>> method = VerificationMethod::test; :>> procedureText = "DONE (green @ f999dc4): resolves issueSelfRedeemVaultOwnerTrap — an OWNER FIELD REPORT (sharing to a new mobile device blocked with 'permissions revoked'). ROOT CAUSE: a self-redeem (redeeming a share link for a vault the SAME account owns) makes the server mint NO grant but return {owner:<you>,...}; the client stamped settings.vaultOwner with the user's OWN username, and refreshShareGrant (every connect, non-empty vaultOwner) then queried /api/shared (OTHERS' vaults only), didn't find it, and threw 'share access revoked' — blocking ALL sync (own vaults synced fine via /api/vaults). FIX (client-only): (1) refreshShareGrant SELF-HEALS — a vaultOwner naming this account is corrected to an OWNED, read-WRITE vault (already-stuck devices recover on the next connect; also clears a stale vaultReadOnly a read-only self-redeem left behind, which would else block pushes to your own vault); (2) adoptRedeemed + startRedeem treat a self-redeemed ref as your OWN vault (never poison vaultOwner) + message it plainly; (3) all three comparisons use a new isOwnAccount() helper that is CASE-INSENSITIVE — the server lowercases usernames (auth.rs to_ascii_lowercase) but the client persists them as-typed, so without this the fix silently no-ops for a capitalized username. INDEPENDENT CRITIQUE (findings-only, no verdict per owner instruction) drove F1 (case-insensitivity — the fix would else miss capitalized-username users, the exact devices the self-heal must rescue) + F2 (the vaultReadOnly reset); it confirmed NO security regression (usernames are unique per server; vaultOwner is not a security boundary) + cleared the base-key + other-poison-vector concerns. The related pre-existing username-case bug in the RCE-adjacent plugin-autopilot gate is DEFERRED to issueUsernameNotCanonicalized (broader username canonicalization). ALSO answered the owner's recursion question: a mount whose SOURCE is the current primary vault is already prevented (activeMounts self-reference exclusion, R5-LOW-3 — it never activates + Settings shows 'inactive — its source is your current primary vault'). Client-only, 1.27.2 plugin-only (no server change). DoD MET: tsc clean, full client vitest 780 passed (new: self-heal with a capitalized username + read-only reset + isOwnAccount case-insensitivity), production build clean, keel validate + guard green."; }
        part selfRedeemVaultOwnerFixDoDR1 : TestResult { :>> id = "a417b20d-b723-4a3b-87ff-3d558f69d758"; :>> outcome = VerdictKind::pass; :>> judgedAgainst = "f999dc4"; :>> judgedAt = "2026-08-14"; :>> judgedBy = "claudeOpus"; }
        action usernameCanonicalization;            // resolver for issueUsernameNotCanonicalized
        verification usernameCanonicalizationDoD : Test { :>> id = "c0fe0ecd-169c-408a-8954-dfe4935753fc"; :>> method = VerificationMethod::test; :>> procedureText = "DONE (green @ 6b0ee4a): resolves issueUsernameNotCanonicalized. The server lowercases usernames on register + login (auth.rs to_ascii_lowercase; SafeName rejects uppercase, so no mixed-case account can exist) but the client persisted them AS-TYPED, so every `x === settings.username` comparison against a server-authenticated value silently broke for a capitalized username — the plugin-autopilot 'is this plugin mine?' gate (RCE-adopt gate: own plugins gated as a peer's; fail-safe but annoying), the config-change 'who changed this?' author check (own edits flagged as another person's), and the self-owned-vault check. FIX (client-only): (1) parseSettings canonicalizes username to lowercase at the persistence boundary — fixes every load AND migrates an existing as-typed name; (2) the setup wizard lowercases at input (echoing the corrected value back), setup-link parse, and both persist points; (3) the autopilot gate uses the case-insensitive isOwnAccount (no widening — usernames are unique per server, so a case-insensitive author match IS your account); (4) configsync shouldNotifyConfigChange + changeSourceLabel compare the author case-insensitively too (defense-in-depth for a change stamped as-typed by an older server). Login/register/redeem still work (the server lowercases identically). INDEPENDENT CRITIQUE confirmed NO login/security regression + cleared the RCE gate, missed-sites, and setup-link roundtrip; it also flagged a SEPARATE latent SERVER bug (bootstrap SYNC_USER not lowercased) → tracked as issueBootstrapSyncUserNotLowercased, not touched here (server change). Client-only, 1.27.3 plugin-only. DoD MET: tsc clean, full client vitest 783 passed (new: parseSettings lowercasing, autopilot capitalized-username adoption, configsync case-insensitive author), production build clean, keel validate + guard green."; }
        part usernameCanonicalizationDoDR1 : TestResult { :>> id = "1633cfcb-7571-4bbc-881b-79d00abfa053"; :>> outcome = VerdictKind::pass; :>> judgedAgainst = "6b0ee4a"; :>> judgedAt = "2026-08-14"; :>> judgedBy = "claudeOpus"; }
        action bootstrapSyncUserLowercase;          // resolver for issueBootstrapSyncUserNotLowercased
        verification bootstrapSyncUserLowercaseDoD : Test { :>> id = "a88f1e7b-26b8-4790-ab97-7727810e5209"; :>> method = VerificationMethod::test; :>> procedureText = "DONE (green @ 9316652): resolves issueBootstrapSyncUserNotLowercased (found by the username-canonicalization critique). config.rs read SYNC_USER as-typed, but every account path canonicalizes to lowercase and SafeName rejects uppercase — so SYNC_USER=Admin failed safe_name() in state.rs (bootstrap admin never seeded, can't log in) AND the `user == cfg.user` bootstrap-admin password-change protection (auth.rs) never matched, silently disabling it. FIX: canonicalize the value at config load via a small canon_user helper (trim + to_ascii_lowercase), matching account creation. SERVER-ONLY — ships as a server-image redeploy, no plugin change. DoD MET: full server cargo test 147 passed + the new config::tests::canon_user_trims_and_lowercases, clippy -D warnings clean, keel validate + guard green."; }
        part bootstrapSyncUserLowercaseDoDR1 : TestResult { :>> id = "e6674f25-adf5-4c38-8a3c-d1381ae01a65"; :>> outcome = VerdictKind::pass; :>> judgedAgainst = "9316652"; :>> judgedAt = "2026-08-14"; :>> judgedBy = "claudeOpus"; }
        action coversEdgesHoisted;
        verification coversEdgesHoistedDoD : Test { :>> id = "041d5afa-e5e0-49ea-a0e2-66ae515cd168"; :>> method = VerificationMethod::inspect; :>> procedureText = "DONE 2026-09-07 (same commit as the engine resync). The 74 `#Covers dependency` edges (per-sitting review -> the sprint tasks it covers, D0049/issue040) sat INSIDE `action def SelfSyncDelivery`, and keel-parser records a dependency statement nested in an action body as SKIPPED - so every one of them was invisible: `keel show marker-census` counted Covers edges = 0 against 74 in the text, `keel show sitting-coverage` reported 0 covered, and the parser-coverage guard's 81 skipped statements were exactly these 74 plus the engine's own 7 legacy successions. Fix: hoist the 74 edges verbatim (same source, same target, same order) to package level in delivery.sysml, where dependency statements parse - the #Verify edges in acceptance.sysml were counted for exactly that reason. Nothing was re-judged. DoD: marker-census Covers edges = 74; parser-coverage skipped = 7 (the stock baseline, which the parser-coverage-baseline.toml ratchet is set back to); sitting-coverage covered > 0; keel validate / guard green under keel 0.3.1. Upstream note carried to the keel toolkit: a nested dependency statement is skipped SILENTLY by `keel check` (four probe files, including a nested one, all 'checked clean'), so only the parser-coverage census reveals the loss - the parser should either accept the nested form or reject it as a parse error. Resolves issueNestedCoversEdgesSkipped."; }
        // RAN: keel show marker-census: Covers edges 0 -> 74; keel guard parser-coverage: skipped 81 -> 7 (succession x7, the stock baseline); keel show sitting-coverage: covered 0 -> 1 readReviewed; keel validate 14 files clean; keel check on 4 probe files (nested, two-per-line, trailing-comment, bare) all 'checked clean' - the nested skip is silent
        part coversEdgesHoistedDoDR1 : TestResult { :>> id = "debe49e6-f091-4d8b-8723-0820204292e4"; :>> outcome = VerdictKind::pass; :>> judgedAgainst = "fdbbc3ce"; :>> judgedAt = "2026-09-07"; :>> judgedBy = "claudeOpus"; }
        action e2eObsidianVersionGate;           // resolver for issueE2eObsidianBelowMinAppVersion
        verification e2eObsidianVersionGateDoD : Test { :>> id = "619c11a9-70a4-4de2-b734-694e1ce940f2"; :>> method = VerificationMethod::test; :>> procedureText = "The real-Obsidian e2e layer (client/e2e-obsidian, Playwright over CDP) refuses to demonstrate against an Obsidian OLDER than manifest.json's minAppVersion: obsidianDriver.ts reads the running app's version from its renderer user agent (obsidianBelowMinAppVersion) and every spec skips LOUDLY - naming both versions - after its vault-ready wait. Why: the machine's install is Obsidian 1.5.8 while the plugin declares minAppVersion 1.11.0 and uses APIs (SettingGroup) that do not exist there; Obsidian itself refuses to enable a plugin below minAppVersion, so a green run on 1.5.8 was demonstrating a configuration no user can have, and a settings-tab demo there would have thrown. Found while trying to automate l3GuiPass. DoD: `npx tsc -p tsconfig.e2e.json` clean; `npm run test:obsidian-e2e` on this machine reports the three specs SKIPPED with the version message (not passed, not failed); on an install >= minAppVersion they run as before (the gate returns false; unknown UA => runs). Resolves issueE2eObsidianBelowMinAppVersion."; }
        // RAN: RAN 2026-09-07: cd client && npx tsc -p tsconfig.e2e.json -> clean; npm run test:obsidian-e2e on this machine (Obsidian 1.5.8 installed, manifest minAppVersion 1.11.0) -> 'Running 3 tests using 1 worker ... 3 skipped', exit 0 - configsync, convergence and smoke each skipped at the post-vault-ready gate (previously all three PASSED on the same 1.5.8 install).
        part e2eObsidianVersionGateDoDR1 : TestResult { :>> id = "7d7e7fa5-c99f-4c45-a165-019faa9d3d43"; :>> outcome = VerdictKind::pass; :>> judgedAgainst = "468027ac"; :>> judgedAt = "2026-09-07"; :>> judgedBy = "claudeOpus"; }
        action conflictDiffSideLegend;           // resolver for issueConflictDiffSidesUnlabeled
        verification conflictDiffSideLegendDoD : Test { :>> id = "7b9dfaad-d7a7-4883-a7aa-53f58c0bf533"; :>> method = VerificationMethod::test; :>> procedureText = "The Resolve-conflicts modal says which side is which, concisely, in three places that agree: (1) the header sentence ends '− lines are the other device's version, + lines are this device's'; (2) the legend above the diff is two bold coloured spans - red '− other device's version', green '+ this device's version' - in the diff rows' own colours, 12px, not faded fine print (it was an 11px 70%-opacity line '− the other version + this device's' that nobody saw); (3) the keep-buttons carry the same signs: 'Keep − other device's' / 'Keep + this device's', so the irreversible choice reads straight off the colours. Guard (D0047): modals-ui.dom 'the diff legend and the keep-buttons both carry the − other / + this signs' asserts the legend text + colours and both button labels. DoD: full client vitest + tsc + build green; PATCH release (client-only). Resolves issueConflictDiffSidesUnlabeled."; }
        // RAN: RAN 2026-09-07: cd client && npx tsc --noEmit -> clean; npx vitest run -> 53 files passed / 1 skipped, 883 tests passed / 2 skipped (new: modals-ui.dom 'the diff legend and the keep-buttons both carry the − other / + this signs'); npm run build -> ok; released 1.30.8 (node scripts/check-release.mjs: git tag + GitHub release with main.js, manifest.json, styles.css present).
        part conflictDiffSideLegendDoDR1 : TestResult { :>> id = "de5ed813-d5bd-4490-83c7-a9b06950aa3d"; :>> outcome = VerdictKind::pass; :>> judgedAgainst = "743d26ae"; :>> judgedAt = "2026-09-07"; :>> judgedBy = "claudeOpus"; }
        action rejectedPushHold;                // resolver for issueRejectedPushRetriedEveryPass
        verification rejectedPushHoldDoD : Test { :>> id = "93614e91-85cf-4506-bca0-1f8df63cb8df"; :>> method = VerificationMethod::test; :>> procedureText = "Ships PATCH 1.30.9 (client-only). (1) The server's rejection reason reaches the user: transport.commit throws a typed CommitRejectedError(status) for any 4xx that is not a CAS race (409) or a swept chunk (404), carrying the server's own body text (the server returns validation failures verbatim - e.g. 'a path differing only in case already exists', 'file exceeds the server's size limit'); meta/getChunk/putChunk/deleteFile likewise surface errText instead of a bare 'HTTP n'. (2) A rejected push is HELD while its content is unchanged: reconcile keeps a caller-owned memo (rejectedPushes: path -> refused local hash) - the same (path, hash) is not re-chunked/re-uploaded/re-refused on later passes (onPushHeld); an edit changes the hash and the push is tried again; a success clears the entry; a plugin reload starts fresh. A CAS 409 is NOT a rejection and stays retryable. main.ts logs the first refusal with the server's reason ('the server refused it - <reason> - not retried until the file changes') and ONE coalesced summary line per burst for held files, never one line per file per pass. Guards (D0047): reconcile.test 'a server-REJECTED push is held while the file is unchanged' (3 tests: refused once then held twice with the reason logged once; edit retries and success clears; 409 stays retryable), transport.test 400-with-body -> CommitRejectedError(reason) + 400-empty-body -> status fallback. DoD: full client vitest + tsc + build green; release published. Resolves issueRejectedPushRetriedEveryPass. NOTE: the ROOT CAUSE of the ~500 refusals in the owner's vault is not yet known - the client had thrown the reason away; 1.30.9's log will name it (the case-collision hypothesis - PARA folders differing only in capitalisation from the server's keys - is recorded on the issue)."; }
        // RAN: RAN 2026-09-07: cd client && npx tsc --noEmit -> clean; npx vitest run -> 53 files passed / 1 skipped, 888 tests passed / 2 skipped (new: reconcile 'a server-REJECTED push is held while the file is unchanged' x3, transport 400-with-body -> CommitRejectedError(reason), 400-empty -> status); npm run build -> ok; released 1.30.9 (Release SelfSync plugin + CI workflows success at 653a03f4; check-release: tag + GitHub release with main.js, manifest.json, styles.css present).
        part rejectedPushHoldDoDR1 : TestResult { :>> id = "dbf88e19-7d96-4c70-986e-16af7f99d0d1"; :>> outcome = VerdictKind::pass; :>> judgedAgainst = "6b872940"; :>> judgedAt = "2026-09-07"; :>> judgedBy = "claudeOpus"; }
        action casePathAlias;                   // resolver for issueCasePathDivergence
        verification casePathAliasDoD : Test { :>> id = "a7aa9f9b-7b9c-43e8-9f11-135093e20a78"; :>> method = VerificationMethod::test; :>> procedureText = "Ships PATCH 1.30.10 (client-only). On a case-insensitive filesystem (Windows, macOS, iOS - reconcile deps caseInsensitivePaths, set from Platform in main.ts) a local path with NO exact server/base key but a case-fold match is ALIASED to that existing key for sync identity: reconcileAll and reconcileLocalConfig re-key the local listing (aliasLocalPaths, against remote+base / base keys), reconcilePath canonicalises the vault-event path (canonicalLocalPath, against base keys). Reads/writes/removes go through the adapter, which resolves either spelling on such a filesystem, so NOTHING is renamed on disk or on the server and no peer sees churn; the server keeps its spelling. Off on Linux/Android, where the spellings are two files and a case-only rename correctly propagates as delete + create. main.ts logs ONE coalesced line per burst ('N local paths differ from the server's only in capitalisation - treated as the same files, keeping the server's spelling (e.g. ...)'). Guards (D0047): reconcile.test 'case-aware path identity on a case-insensitive filesystem' - full pass: nothing pushed/refused/deleted, one alias event, one spelling on the server, local file untouched; an EDIT under the local spelling reaches the existing server key via the full pass AND the event path, never a second key; a server tombstone for the canonical key removes the locally re-capitalised file; on a case-SENSITIVE io nothing is aliased and the rename propagates as delete + create. DoD: full client vitest + tsc + build green; release published. Resolves issueCasePathDivergence. Effect on the owner's vault: the ~500 refused pushes stop being decided at all - the pass returns to scan-hit speed - and edits in those folders sync again. NOT covered (follow-up if it bites): a NEW file created under the re-capitalised folder has no fold match and is pushed under the local spelling, so the server can hold a folder in two capitalisations; a Linux peer would then see two folders."; }
        // RAN: RAN 2026-09-07: cd client && npx tsc --noEmit -> clean; npx vitest run -> 53 files passed / 1 skipped, 892 tests passed / 2 skipped (new: reconcile 'case-aware path identity on a case-insensitive filesystem' x4); npm run build -> ok; released 1.30.10 (Release SelfSync plugin + CI success at 2761d2c8; check-release: tag + GitHub release with main.js, manifest.json, styles.css present).
        part casePathAliasDoDR1 : TestResult { :>> id = "15f2bb5b-a9c0-46fd-bfd4-13a8d7c1ef0c"; :>> outcome = VerdictKind::pass; :>> judgedAgainst = "6c1cdd08"; :>> judgedAt = "2026-09-07"; :>> judgedBy = "claudeOpus"; }
        action busyStateGating;                 // resolver for issueBusyStateNotSurfaced
        verification busyStateGatingDoD : Test { :>> id = "a9d32bbc-77d5-46cc-9612-f75bc08fe243"; :>> method = VerificationMethod::test; :>> procedureText = "Ships PATCH 1.30.12 (client-only; 1.30.11 carried a first cut with a prose banner, which the owner rejected the same evening: 'show don't tell. just disable the resolve button and change the text to analyzing files' - 1.30.12 is that design). The plugin's BUSY state is a tracked, pure projection - main.ts busyState(): the raw engine phase + the live connect stage (connecting -> 'SelfSync is connecting - <stage>'; a syncing/check pass -> 'SelfSync is syncing - N pending' or 'SelfSync is checking your files for changes'); never a stored flag - with onBusyChange() subscription notified on every status repaint and connect-stage change. busygate.ts is the ONE way a surface shows it, SHOW DON'T TELL: each COMMITTING button is disabled and wears the short state label ('Analyzing files...' / 'Syncing...') with the fuller reason on its native tooltip, and gets its own label back the moment the plugin reports settled; no banner, no prose; non-committing actions (Copy, Close, Open both) stay live. Gated: NoteConflictModal (Keep -/+), ConfigConflictModal (Use this device's / Use the server's version), SwitchVaultModal (Switch, Fork, Use, Leave, Merge, Download, Upload) and the settings tab's Conflicts 'Resolve' entry points; the modal actions also refuse with the reason as belt-and-braces. Guards (D0047): modals-ui.dom 'busy-state gating' x3 - the committing buttons read 'Analyzing files...' + disabled with the reason as tooltip while Copy stays enabled, no prose banner, a tap on a gated button resolves nothing, settling (fireBusy) restores the labels, unsubscribe on close; settings-ui.dom - the Conflicts 'Resolve' button wears the state and returns; the obsidian test stub's ButtonComponent.setDisabled made real so gating is testable. DoD: full client vitest + tsc + build green; release published. Resolves issueBusyStateNotSurfaced."; }
        // RAN: RAN 2026-09-07: cd client && npx tsc --noEmit -> clean; npx vitest run -> 53 files passed / 1 skipped, 896 tests passed / 2 skipped (new: modals-ui.dom 'busy-state gating' x3 button-as-indicator, settings-ui.dom Conflicts Resolve wears the state); npm run build -> ok; released 1.30.12 (Release SelfSync plugin + CI success at ad81f414; check-release: tag + GitHub release with main.js, manifest.json, styles.css present). 1.30.11 (banner cut) superseded the same evening on the owner's 'show don't tell'.
        part busyStateGatingDoDR1 : TestResult { :>> id = "3a9b0f63-1664-448c-856e-e7409e23fbe0"; :>> outcome = VerdictKind::pass; :>> judgedAgainst = "2c752d35"; :>> judgedAt = "2026-09-07"; :>> judgedBy = "claudeOpus"; }
        action conflictModalBinaryView;          // resolver for issueConflictModalHangsOnBinary
        verification conflictModalBinaryViewDoD : Test { :>> id = "71645fc6-3e25-448f-988c-434689903da9"; :>> method = VerificationMethod::test; :>> procedureText = "Ships PATCH 1.30.13 (client-only). The Resolve-conflicts modal decides from fileStat (size + mtime, no read) whether a conflict can be diffed: a non-text extension (isTextExt false on either side) or a text file over MAX_DIFF_BYTES (4 MB) gets the NO-DIFF view - header naming why ('a binary file, so there is no text diff' / 'too large to diff (N MB)'), one line per side in the diff's own -/+ colours with size + modified date, and the same gated keep choices (Keep - other device's / Keep + this device's); Copy/Open-both are absent because there is nothing textual. NOTHING is read from disk in that branch, and resolve() runs with no previewedOther (nothing displayed to go stale against). A small text conflict still gets the real diff. Guards (D0047): modals-ui.dom - an .mp4 conflict shows sizes/dates + keep choices and calls neither readTextOrEmpty nor readBytesOrNull, Keep - resolves 'theirs' with previewedOther undefined; a 6 MB .md gets the same view with the size as the reason; a small .md still gets the diff (two reads, Copy present). DoD: full client vitest + tsc + build green; release published. Resolves issueConflictModalHangsOnBinary."; }
        // RAN: RAN 2026-09-08: cd client && npx tsc --noEmit -> clean; npx vitest run -> 53 files passed / 1 skipped, 899 tests passed / 2 skipped (new: modals-ui.dom 'a binary or oversize conflict is not read or diffed' x3); npm run build -> ok; released 1.30.13 (Release SelfSync plugin + CI success at 8da34de8; check-release: tag + GitHub release with main.js, manifest.json, styles.css present).
        part conflictModalBinaryViewDoDR1 : TestResult { :>> id = "db79b78d-1005-4c15-99d8-bffe81fd2a81"; :>> outcome = VerdictKind::pass; :>> judgedAgainst = "588c29b0"; :>> judgedAt = "2026-09-08"; :>> judgedBy = "claudeOpus"; }
        action resolutionStateMachine;          // resolver for issueResolutionHadNoState
        verification resolutionStateMachineDoD : Test { :>> id = "f814d4db-bb0a-4b4b-943a-1b7e7884ce42"; :>> method = VerificationMethod::test; :>> procedureText = "Ships PATCH 1.30.14 (client-only). Resolution in the Resolve-conflicts modal is a PROPER finite state machine - client/src/resolvefsm.ts, pure: ResolveState {idle | local(step) | uploading(sawBusy) | done | stale | failed}, ResolveEvent {start, step, localDone, stale, error, engineBusy, engineIdle, graceElapsed, capElapsed, reset}, one transition function resolveNext, one projection resolveLabel(state, ownLabel), resolveInFlight. The modal holds the state, feeds it events from three sources - the plugin's TYPED steps (resolveNoteConflict onStep: checking | reading | writing | keepingBoth | removingCopy), the engine (busyState via onBusyChange -> engineBusy/engineIdle), the clock (600 ms grace if busy never appears, 8 s cap) - and paints the pressed button from the projection; it never composes status strings. The dimmed body (opacity .55 + pointer-events none) is gone: during resolution the other keep-buttons are disabled, Copy / Open both / Close stay live. 'Updating the server…' is real - the written path is enqueued for sync and the machine waits for the engine to pick it up and settle (or the grace/cap, so it never blocks on the network). Owner's first cut ('step by step status') was string stages; the owner correctly called it an FSM and this is that. Guards (D0047): resolvefsm.test (pure transition table: happy path, grace-only completion, busy-waits-for-idle, cap, stale/error terminal + reset, no-op events; every label); modals-ui.dom (typed steps land on the pressed button, other keep disabled, Copy live, no opacity; 'Updating the server…' holds while busy and releases on idle; Keep both narrates 'Keeping both versions…'). DoD: full client vitest + tsc + build green; release published. Resolves issueResolutionHadNoState."; }
        // RAN: RAN 2026-09-08: cd client && npx tsc --noEmit -> clean; npx vitest run -> 54 files passed / 1 skipped, 912 tests passed / 2 skipped (resolvefsm.test transition table + labels; modals-ui.dom typed steps / Keep both; plugin-wiring real body 'both'; base keptBothName); npm run build -> ok; released 1.30.14 (Release SelfSync plugin + CI success at 734aaba4; check-release: tag + GitHub release with main.js, manifest.json, styles.css present).
        part resolutionStateMachineDoDR1 : TestResult { :>> id = "596f8888-c6a7-4094-9df8-09c829862c1f"; :>> outcome = VerdictKind::pass; :>> judgedAgainst = "f15fda65"; :>> judgedAt = "2026-09-08"; :>> judgedBy = "claudeOpus"; }
        action keepBothResolution;              // resolver for issuePreserveBothRequiredEditorMerge
        verification keepBothResolutionDoD : Test { :>> id = "f8e56522-44e5-46f6-8538-f73edfe88e65"; :>> method = VerificationMethod::test; :>> procedureText = "Ships PATCH 1.30.14 (client-only). A 'Keep both' choice on the Resolve-conflicts modal (diff view and no-diff view), placed FIRST among the choices as the safe, data-preserving default: resolveNoteConflict(choice 'both') renames the conflict copy into an ORDINARY note beside the original - keptBothName(original, today) = '<stem> (this device's version YYYY-MM-DD)<ext>', disambiguated ' 2', ' 3'… if taken - by read + write + remove through the vault io, enqueues both paths for sync, and leaves the original untouched. Both versions survive as two synced files; nothing is opened in an editor, nothing is merged by hand; the new name is outside the strict conflict scheme (no 14-digit timestamp) so the conflict ends the moment it is renamed. 'Open both to merge' stays, moved LAST (slow: opens both files in the editor; rarely what is wanted). Guards (D0047): base.test keptBothName (naming, disambiguation, not a conflict copy); plugin-wiring real body - original untouched, kept file holds this device's bytes and is not a conflict, copy removed, typed steps keepingBoth -> removingCopy; modals-ui.dom - 'Keep both' calls choice 'both' and narrates 'Keeping both versions…'. DoD: full client vitest + tsc + build green; release published. Resolves issuePreserveBothRequiredEditorMerge."; }
        // RAN: RAN 2026-09-08: cd client && npx tsc --noEmit -> clean; npx vitest run -> 54 files passed / 1 skipped, 912 tests passed / 2 skipped (resolvefsm.test transition table + labels; modals-ui.dom typed steps / Keep both; plugin-wiring real body 'both'; base keptBothName); npm run build -> ok; released 1.30.14 (Release SelfSync plugin + CI success at 734aaba4; check-release: tag + GitHub release with main.js, manifest.json, styles.css present).
        part keepBothResolutionDoDR1 : TestResult { :>> id = "16aa4e06-dac4-4391-90b3-a8dacd0a5687"; :>> outcome = VerdictKind::pass; :>> judgedAgainst = "f15fda65"; :>> judgedAt = "2026-09-08"; :>> judgedBy = "claudeOpus"; }
        action stpaProcessAndFsmModule; // owner directive 2026-09-08: FSM module everywhere hazard-bearing state exists + STPA as a process
        verification stpaProcessAndFsmModuleDoD : Test { :>> id = "713fdd3f-d1fb-45ef-8256-3f878ef4d90f"; :>> method = VerificationMethod::test; :>> procedureText = "Ships PATCH 1.30.15 (client-only code; plus engine process + safety model). (1) client/src/fsm.ts is THE state-machine primitive: defineMachine(spec) - pure (state, event) -> state [+ effects as data], total and conservative (no rule => unchanged, never throws), declared terminal states with explicit exits, tableCoverage() test helper; each machine is NAMED by the STPA process model it realizes. (2) The four pure machines are on it with their exported signatures unchanged: resolvefsm (resolveMachine, pmResolver), mountfsm (mountMachine, pmSyncEngine), transportstate (transportMachine with effects, pmSyncEngine), connstate (linkMachine, pmSession); syncengine's class-internal EngineState is registered as STPA-FSM-PENDING (issueEngineFsmNotOnPrimitive, its own sprint). (3) The STPA model registers every machine on its process model ('// STPA-FSM: <module>#<machine>' in control-structure.sysml) and gains the conflict resolver as a controller: c8ConflictResolver, pmResolver, control actions write-chosen-version / remove-conflict-copy / keep-both-rename, feedback fbEngineBusy, UCA-23..25 (four-guide-word pass), C-21..23, S-20 (the 2026-09-07 mid-pass resolution), SR-26 (acts only on a settled, unchanged file) and SR-27 (copy outlives the write; Keep both discards nothing), all edges typed and SR-26/27 #Verify-linked to passed DoDs. (4) STPA is an ACTIVATED PROJECT PROCESS: .engine/processes/stpa.sysml with six ordered steps - Step 1 purpose (losses/hazards/constraints), Step 2 control structure, Step 3 UCAs (four guide words per control action), Step 4 loss scenarios + safety requirements, Step 5 reanalysis-on-change (D0017 trigger), Step 6 hazard-bearing state is an fsm.ts machine registered on a process model - deployed by the project skill safety-analysis (D0059), which wraps the engine's stpa SOP; recorded as project D0053 (PROPOSED). Guards (D0047): fsm.test (primitive contract + every real machine's table is total), fsm-conformance.test (every registered machine exists / imports fsm.ts / names its PM; every module that defines a machine is registered; a PENDING machine is not yet on the primitive), existing per-machine suites unchanged and green, keel validate/guard green with the new safety elements. DoD: full client vitest + tsc + build green; keel green; release published."; }
        // RAN: RAN 2026-09-08: cd client && npx tsc --noEmit -> clean; npx vitest run -> 56 files passed / 1 skipped, 924 tests passed / 2 skipped (new: fsm.test primitive + every real machine's table total; fsm-conformance.test registration <-> primitive both directions + PENDING honesty; existing connstate/mountfsm/transportstate/resolvefsm suites unchanged); npm run build -> ok; keel validate 15 files clean, keel check-engine clean, keel guard ALL PASS with the new process/skill/decision and safety elements; keel activation lists stpa [always]; released 1.30.15 (Release SelfSync plugin + CI success at cac6c092; check-release: tag + GitHub release with main.js, manifest.json, styles.css present).
        part stpaProcessAndFsmModuleDoDR1 : TestResult { :>> id = "1d9c51b9-9885-4d7d-9971-2371a558f0b5"; :>> outcome = VerdictKind::pass; :>> judgedAgainst = "bfbfa401"; :>> judgedAt = "2026-09-08"; :>> judgedBy = "claudeOpus"; }
        action engineFsmOnPrimitive;    // resolver for issueEngineFsmNotOnPrimitive
        verification engineFsmOnPrimitiveDoD : Test { :>> id = "5beb57f2-a077-4b84-8791-e982a10d8474"; :>> method = VerificationMethod::test; :>> procedureText = "Ships PATCH 1.30.16 (client-only). The sync engine's EngineState is on the shared fsm.ts primitive: engineMachine (syncengine.ts, STPA process model pmSyncEngine) with the engine's OWN state events - unload, disconnect, connectStart(linkRetrying), connected(queued), failed, work, drained - as one rule table; SyncEngine.transition(ev) is the single writer of `state` (every former setState()/direct assignment routed through it; the phase projection repaints on a real change), the pump/handlers only decide WHEN an event fires. Behaviour-preserving: syncengine.test untouched and green. ONE deliberate change, found by walking the explicit table (STPA Step 5): `unloading` is TERMINAL with no exits, so a connect()/reconcile effect that resolves or fails AFTER teardown can no longer flip the state back to idle/reconciling/disconnected and repaint a torn-down plugin - recorded as UCA-26 / C-24 / S-21 / SR-28 on c2SyncEngine (#Verify from this DoD). The STPA registration flipped from STPA-FSM-PENDING to STPA-FSM: client/src/syncengine.ts#engineMachine (fsm-conformance.test enforces the flip; no PENDING machine remains). Guards (D0047): fsm.test engineMachine - the whole table total, no state outside the declared set, nothing leaves `unloading`, work/drained rules; fsm-conformance.test; syncengine.test. DoD: full client vitest + tsc + build green; keel green; release published. Resolves issueEngineFsmNotOnPrimitive."; }
        // RAN: RAN 2026-09-08: cd client && npx tsc --noEmit -> clean; npx vitest run -> 56 files passed / 1 skipped, 925 tests passed / 2 skipped (fsm.test engineMachine: whole table total, nothing leaves unloading; fsm-conformance.test with no PENDING machine; syncengine.test untouched and green); npm run build -> ok; keel validate 15 files clean, keel guard ALL PASS; released 1.30.16 (Release SelfSync plugin + CI success at 3604f577; check-release: tag + GitHub release with main.js, manifest.json, styles.css present).
        part engineFsmOnPrimitiveDoDR1 : TestResult { :>> id = "f5fbc9da-76a9-44fd-a77b-7152e9f2be58"; :>> outcome = VerdictKind::pass; :>> judgedAgainst = "ad3d6886"; :>> judgedAt = "2026-09-08"; :>> judgedBy = "claudeOpus"; }
        action stpaStep1Refresh;                // STPA Step 1 redone around the plugin boundary (owner, 2026-09-09)
        verification stpaStep1RefreshDoD : Test { :>> id = "ed8f50ae-2553-4624-aab0-8f69d4fdedc6"; :>> method = VerificationMethod::analyze; :>> procedureText = "STPA Step 1 (stpa1Purpose) re-performed 2026-09-09 with the boundary redrawn around the PLUGIN (owner: 'our system boundary is our plugin. what authorities are present? what systems?'). Recorded in .tracking/safety/safety.sysml: the system under analysis (plugin + the local vault files/config it manages); the server + operator + protocol as OWNED, TRUSTED environment (their existing controllers/UCAs/SRs kept, re-read as commitments/assumptions rather than plugin requirements); an AUTHORITY INVENTORY of every party that can change the controlled processes - inside the plugin (c2/c3/c4/c8, config sync), the user (c1), the host app (NEW - lifecycle, exact-case API, main thread), other plugins writing the same files (NEW), other sync tools on the same directory (NEW), the OS/filesystem, other devices + peers, server + operator, the release channel BRAT/GHCR (NEW), the network path, time; environment assumptions A9-A14 added to A1-A8. Losses L-1..L-5 reviewed and kept (L-6 'performance' stays out per the 2026-08-03 owner call; host unresponsiveness is H-12 under L-3/L-4). Three hazards the inventory exposed, each lived this week before it was named: H-11 identity divergence (one artefact as two / two as one - the case-collision incident), H-12 host unresponsive / controls unreachable (the 200 MB modal freeze, the 152 s pass), H-13 another same-device authority writing the same file (Syncthing conflict files, Linter/Metadata-Menu rewrite loops); inverse constraints SC-11..13; #LeadsTo / #Inverts / #Enforces edges typed. Evidence: keel validate + guard green with the additions; hazards h1..h13 each #LeadsTo >= 1 loss and each has an #Inverts constraint. STEP 2 FOLLOW-UP (not this task): controllers for the four NEW authorities (host app, other plugins, other sync tools, release channel) with their control actions on p1LocalVault / p5LocalRuntime, then Steps 3-4 over them."; }
        // RAN: ANALYSIS 2026-09-09: boundary redrawn around the plugin; authority inventory (11 authorities, 4 NEW without controllers) + A9-A14 recorded in safety.sysml; L-1..L-5 reviewed, kept; H-11..13 + SC-11..13 authored with #LeadsTo/#Inverts/#Enforces; census: 13 hazards, each #LeadsTo >= 1 loss and each with an #Inverts constraint (scripted check, 0 gaps); keel validate 15 files clean, keel guard ALL PASS.
        part stpaStep1RefreshDoDR1 : TestResult { :>> id = "4d2ac9f8-9c77-48a8-831c-2cea3c3b0d4a"; :>> outcome = VerdictKind::pass; :>> judgedAgainst = "ef43ef6f"; :>> judgedAt = "2026-09-09"; :>> judgedBy = "claudeOpus"; }
        action stpaNestingAnalysis;             // STPA of nesting / composed vaults (owner, 2026-09-09)
        verification stpaNestingAnalysisDoD : Test { :>> id = "78217720-c5d6-4fa2-80ee-0fc579e7cb70"; :>> method = VerificationMethod::analyze; :>> procedureText = "STPA of the NESTING functionality (composed vaults / mounts, D0039 + D0040/D0043/D0044) performed 2026-09-09 under the stpa process (owner: 'do an STPA focusing on the nesting functionality. be thorough'). STEP 1 additions (stpa-hazards.sysml): two composition-specific hazards - H-14 content attributed to the wrong scope (primary vs mount vs another mount; the scope BOUNDARY is the load-bearing invariant) and H-15 a write crossing a mount against its direction or the user's grant - with inverse constraints SC-14/SC-15 and #LeadsTo/#Inverts/#Enforces edges. STEP 2 (control-structure.sysml): controllers c9MountEngine (per-mount runtime + mountsync loop), c10MountConfig (settings/validateMounts/validMounts/recipe import) and c11SourceOwner (environment: other writers of the mounted source, untrusted unless the user's own vault); process models pmMount (the mount lifecycle machine mountfsm.ts#mountMachine now registers HERE, moved from pmSyncEngine) and pmMountConfig; controlled processes p6MountFolder, p7SourceSubtree, p8MountState; control actions caMountStart / caMountPull / caMountPush / caMountDeleteOutgoing / caComputeActiveMounts / caMountRemove / caSetMountDirection / caApplyRecipe / caSourceWrite; feedback fbMountStatus / fbSourceReady / fbSourceChanges / fbMountFolderEvents. STEPS 3-4 (new stpa-nesting.sysml, package ProjectStpaNesting): 19 UCAs (UCA-27..45) over the four guide words - boundary case/Unicode leak, shared base/io, first-contact adopt-over, pull-mount source write, not-ready/incompatible source manifest, mount-folder deletion wiping the source, transient-listing false absence, tombstone-pruned resurrection onto a shared source, .obsidian-anchored mount exfiltrating credentials, all-or-nothing invalidation, self-referential mount + stale dormant base, unpolled/unretried/unsurfaced mount, remove/unload lifecycle race, sync-mount edits never pushed, move-out honoured as source deletion (UCA-41, owner-ACCEPTED per D0044 and recorded so the acceptance is visible), recipe beyond the recipient's grant, mobile buffering of a huge source file, held-resolver base race, source version rewind; 19 controller constraints C-25..C-43; 9 loss scenarios S-22..S-30, each a REAL recorded finding from hardening rounds R1-R10 or the mount issue log with the closing mechanism named; 15 safety requirements SR-29..SR-43 each with #Mitigates / #Satisfies / #RealizedBy edges. Every UCA #Analyzes its control action(s) and #Causes its hazard(s); every constraint #Inverts its UCA; every scenario #Explains its UCA and #LeadsTo its hazard. STEP 5 (verification, acceptance.sysml): 28 #Verify edges from DoDs with a RECORDED PASS (mountEngineCore, mountEngine, mountIoAdapters, mountHardeningR1-R7/R9/R10, mountFolderDeleteGuard, mountDeleteGuardHardening, mountBaseFreshness, mountHeldResolverSerialize, mountLiveSubscription, mountSocketLiveness, composeRecipeFeature, composedMountPermissions, mountSharedSourceResurrectionPolicy, mountResetDetection, mountSyncPushLocal, mountMoveSafety, stpaProcessAndFsmModule) - the script asserted each cited DoD carries a pass result before writing its edge. STEP 6 (FSM): mountMachine renamed to 'pmMount' (label only, spec.name has no runtime reader; fsm-conformance.test enforces the bidirectional registration). Evidence: keel validate clean (16 files) + keel guard ALL PASS; fsm + fsm-conformance suites green (13 tests). NO NEW OPEN GAP found: every hazardous cell identified maps to a shipped, passed mitigation or to the owner's recorded acceptance (UCA-41); the residual is the deferred mountHardeningR8 GC + the Step 2 follow-up for the host/other-plugin/other-sync-tool/release-channel controllers, already tracked."; }
        // RAN: RAN: keel validate . (16 tracking files clean) + keel guard . (ALL PASS, 0 violations) after authoring H-14/H-15, SC-14/15, c9-c11, pmMount/pmMountConfig, p6-p8, 9 control actions, 4 feedback, UCA-27..45, C-25..43, S-22..30, SR-29..43, 28 #Verify edges; RAN: npx vitest run test/fsm.test.ts test/fsm-conformance.test.ts (2 files, 13 tests pass) with mountMachine registered on pmMount
        part stpaNestingAnalysisDoDR1 : TestResult { :>> id = "7882b153-050b-461b-ae49-c6b9c9f6c302"; :>> outcome = VerdictKind::pass; :>> judgedAgainst = "07f449e0"; :>> judgedAt = "2026-09-09"; :>> judgedBy = "claudeOpus"; }
        action stpaAuthoritiesAnalysis;         // STPA Step 2 follow-up: host / other plugins / other sync tools / release channel (owner, 2026-09-10)
        verification stpaAuthoritiesAnalysisDoD : Test { :>> id = "e61853a1-0ed3-475a-8ba9-25cb57e7a938"; :>> method = VerificationMethod::analyze; :>> procedureText = "STPA Step 2 follow-up of the 2026-09-09 Step 1 refresh, performed 2026-09-10 (owner: 'continue with step 2'): the four authorities the inventory named NEW are now modelled as ENVIRONMENT controllers in control-structure.sysml - c12HostApp (vault API + file events keyed by exact case, plugin lifecycle, one main thread), c13OtherPlugins (same-file writers and plugin code that arrives through config sync), c14OtherSyncTools (Syncthing / cloud drives on the same directory), c15ReleaseChannel (GitHub Releases via BRAT; GHCR image; CI from tags) - with the host's process model pmHost, control actions caHostLifecycle, caPluginRewrite, caSyncToolWrite, caReleasePluginBuild, caReleaseServerImage, and feedback fbVaultEvents, fbAppLifecycle, fbReleaseAssertion. STEPS 3-4 over the plugin's actions in those environments (new stpa-authorities.sysml, ProjectStpaAuthorities): 12 UCAs (UCA-46..57) - acting after unload / two instances, no re-attempt after mobile suspend, exact-case identity, another plugin's identity-only rewrite, racing write at the seam, synced plugin code executing, another sync tool's artefacts + two-tool rewrite loop, placeholder/lock read as absent or empty, host saturation, version mismatch after an independent update or rollback, inconsistent/unreleased version records, unverified published asset; 12 controller constraints C-44..55; 9 loss scenarios S-31..39 (eight recorded findings with the closing mechanism named; S-39 PROJECTED and unmitigated); 8 safety requirements SR-44..51 with #Mitigates / #Satisfies / #RealizedBy, plus #Mitigates edges from the EXISTING sr2, sr5, sr15, sr23, sr28 to the new UCAs they already cover (no duplicate requirements). STEP 5: 17 #Verify edges in acceptance.sysml, each from a DoD whose recorded pass the script asserted. TWO GAPS FOUND, neither left in prose: UCA-52/SR-47 no coexistence rule for a co-located sync tool (issueSyncToolCoexistenceUnguarded, Medium, resolver task syncToolCoexistence OPEN) and UCA-57/SR-50 published assets checked for presence never integrity (issueReleaseAssetIntegrityUnchecked, Medium, resolver task releaseAssetIntegrity OPEN); sr47 and sr50 therefore carry no #Verify edge yet, by design. Evidence: keel validate clean (17 files) + keel guard ALL PASS + keel gate clean; fsm-conformance suite green (no FSM change - the host has no plugin-side machine; its lifecycle is the engine's existing machine)."; }
        // RAN: RAN: keel validate . (17 tracking files clean) + keel guard . (ALL PASS, 0 violations) + keel gate --workspace . (clean) after authoring c12-c15, pmHost, 5 control actions, 3 feedback, UCA-46..57, C-44..55, S-31..39, SR-44..51, 17 #Verify edges, 2 issues + 2 OPEN resolver tasks; RAN: npx vitest run test/fsm-conformance.test.ts (4 tests pass)
        part stpaAuthoritiesAnalysisDoDR1 : TestResult { :>> id = "949bb9b7-33d0-445a-8f11-49d710c9f8f3"; :>> outcome = VerdictKind::pass; :>> judgedAgainst = "184b499e"; :>> judgedAt = "2026-09-10"; :>> judgedBy = "claudeOpus"; }
        action coexistenceHardening;                 // 2026-09-11 architecture panel — sprint
        verification coexistenceHardeningDoD : Test { :>> id = "421791dc-9953-4901-bb43-5a4e4c364f20"; :>> method = VerificationMethod::test; :>> procedureText = "DONE in 1.30.18: the other-sync-tools critic's findings against the 1.30.17 code (FT1..FT8) + the identity critic's ID3 (loop breaker reach). FT1 MAJOR: the mount runtime captured skipForeignArtefacts as a boolean while the mount io read the live setting, so a mid-session toggle could read a based foreign path as absent and tombstone it on the SOURCE — the ctx field is now a live predicate read by accepts (mountengine.ts). FT2 MAJOR: 'Upload current versions anyway' set a standing override; release() is now one-shot (exactly the current content passes; the next flip re-arms) and the override clears when the flips lapse. FT3: default limit raised 4→6 flips and the burst log hedges (rapid back-and-forth edits are the other explanation). FT4: foreign paths already on the server are their own once-per-set notice with the removal procedure, not 'config files'. FT5: root markers (.stfolder/.stignore/.stversions/.dropbox/.dropbox.cache/.sync) are probed through the adapter each primary listing (the host never indexes dot paths) so the settings row can NAME the tool. FT6: toggling the skip off forces a FULL pass (requestFullReconcile). FT7: dead forget() removed. FT8: header reworded to the honest scope (returning content; a monotonic unmasked stamper is a recorded residual — issueMonotonicRewriteLoopUndetected). ID3: pushFlipHold/onFlipHeld reach mount scopes (callbacks Pick + wiring keyed by the vault-relative path) and the merged-push site. Tests: flipguard.test rewritten for one-shot release + window lapse + default tolerance; settings DOM expects requestFullReconcile; reconcile SR-47 blocks unchanged and green. Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: vitest flipguard.test (one-shot release, window lapse, default tolerance), settings-ui.dom SR-47 (requestFullReconcile), reconcile SR-47 blocks; tsc proves ctx.skipForeignArtefacts is a predicate at every call site.
        part coexistenceHardeningDoDR1 : TestResult { :>> id = "fe2bdd1a-fcfe-439c-aa9b-133343a1df3b"; :>> outcome = VerdictKind::pass; :>> judgedAgainst = "39f31d3d"; :>> judgedAt = "2026-09-11"; :>> judgedBy = "claudeOpus"; }
        action mountScopeBoundaryHardening;                 // 2026-09-11 architecture panel — sprint
        verification mountScopeBoundaryHardeningDoD : Test { :>> id = "cc599030-c363-4de9-a8b7-5bea2ae8d746"; :>> method = VerificationMethod::test; :>> procedureText = "DONE in 1.30.18: the composed-vaults critic's findings CV1..CV5 + CV8 (UCA-58..62 in stpa-nesting.sysml). CV1 MAJOR: the primary's base entries under a mount point froze while the mount owned the folder; on remove the primary compared the mount's content/deletions against that frozen base (push over own copy, delete-remote fleet-wide) — addMount and removeMount now purge those entries (forgetPrimaryBaseUnder) so the primary re-first-contacts the subtree. CV2 MAJOR: renaming/moving the mount-point folder (or an ancestor) left the mount localGone while the PRIMARY uploaded the peer's subtree into the user's vault — the mount point now FOLLOWS the folder (followMountPointRename; refused + explained when the destination is invalid). CV3: a note dragged into a pull mount is said plainly (it left the primary on all devices; it will not be uploaded; the two ways back). CV4 MAJOR: the source grant was read once per connect — a 401/403 on a mount write now re-reads the grants at once so the read-only rail follows on the next pass. CV5: mountMachine is the ONLY lifecycle writer — localGone / conflict / reset edges added, the four direct assignments routed through mountTransition, and fsm-conformance greps for literal state assignment (D0047 guard). CV8: per-device wording on the Local folder field. Tests: plugin-wiring (base purge on add+remove; folder + ancestor rename follow; invalid destination refused), fsm.test (new edges), fsm-conformance grep guard. Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: vitest plugin-wiring 'panel CV1' (base purged on addMount + removeMount, unrelated kept) + 'panel CV2' (folder + ancestor rename follow; .obsidian destination refused with notice), fsm.test mountMachine edges (localGone from every live state, conflict, syncSettled from mounting/diverged/offline, reset), fsm-conformance grep guard (no literal mount state assignment outside mountfsm.ts) — all pass.
        part mountScopeBoundaryHardeningDoDR1 : TestResult { :>> id = "db960f1a-3caa-42a2-867f-932685eae4d8"; :>> outcome = VerdictKind::pass; :>> judgedAgainst = "39f31d3d"; :>> judgedAt = "2026-09-11"; :>> judgedBy = "claudeOpus"; }
        action contentIdentityTwoSided;                 // 2026-09-11 architecture panel — sprint
        verification contentIdentityTwoSidedDoD : Test { :>> id = "2d6cd1f3-fe74-4947-ab12-bd87615882b8"; :>> method = VerificationMethod::test; :>> procedureText = "DONE in 1.30.18: the identity critic's findings ID1/ID2/ID4/ID5/ID6/ID8 (UCA-67..69). ID1 MAJOR: the push→in-sync override stamped the scan-skip hint on a raw-different file; the next full pass trusted it, a remote edit decided pull, and the write seam wrote a conflict copy of a stamp-only local — conflictCopyIfRaced now skips the copy when the current bytes are identity-equal to base. ID2 MAJOR: identity was one-sided — a 'merge' where exactly one side is identity-equal to base (NFD re-save, `key: `→`key:`) is now a plain pull or push, no conflict copy. ID4 MAJOR: adopt-remote dropped a masked timestamp line present on one side only — adopt now requires equal masked-key presence (the auto-sweep's own rule), else the ordinary divergence handling preserves it. ID5: in-fence trailing-whitespace trim stops at indented lines (YAML block scalars keep their whitespace). ID6: maskedForDisplay applies NFC + top-level in-fence trim so the diff shows nothing where identity sees nothing. ID8 MAJOR: hot-load keyed on the vault being private NOW, not on who wrote the code — hotLoadable now requires the recorded committer to be this account (unknown author only in a private vault), matching the autopilot's rule. Tests: reconcile (stamp-only + remote move → pull, no copy; NFD local + remote same-line edit → pull; remote NFD + local edit → push; masked-key presence preserved), content-identity (block scalar distinct; display folds), plugin-wiring (peer-authored plugin not hot-loaded). Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: vitest reconcile 'panel ID1' (stamp-only local + remote move -> pulled, no copy), 'panel ID2' (NFD local + same-line remote edit -> pull; remote NFD + local edit -> push, no copy), 'panel ID4' (masked created: line preserved), content-identity 'panel ID5/ID6' (block scalar distinct; display folds NFC + top-level trim; body/indented whitespace kept), plugin-wiring 'panel ID8' (peer-authored newly-arrived plugin NOT hot-loaded; own code is) — all pass.
        part contentIdentityTwoSidedDoDR1 : TestResult { :>> id = "5c57e5f5-7f57-4add-b9be-947af8e292c2"; :>> outcome = VerdictKind::pass; :>> judgedAgainst = "39f31d3d"; :>> judgedAt = "2026-09-11"; :>> judgedBy = "claudeOpus"; }
        action hostCoexistenceHardening;                 // 2026-09-11 architecture panel — sprint
        verification hostCoexistenceHardeningDoD : Test { :>> id = "00b2c1ac-54b6-4e43-a6ed-9b7782abbe54"; :>> method = VerificationMethod::test; :>> procedureText = "DONE in 1.30.18: the host-coexistence critic's findings H1..H7 (UCA-64..66). H1 BLOCKER: a case-only rename made on a case-SENSITIVE peer arrives as tombstone `Note.md` + upsert `note.md`; on a folding peer both are ONE file — removeLocal deleted the file the upsert had just adopted, and the host's delete event then tombstoned the new key fleet-wide. caseRenamedTombstones now pairs a tombstone with a fold-sibling remote key and the removeLocal effect becomes a base rename (nothing removed, nothing tombstoned) on both the full and the delta path. H2 MAJOR: an in-flight pass ran to completion after onunload — deps.alive is checked between items in isolatedPass; persistence coalesces and is flushed on unload. H3 MAJOR: mobile per-file cap was the desktop default — a hard 100 MB ceiling on mobile regardless of the setting (said on the control). H4 MAJOR: persist() on every setBase — trailing-edge coalescing (1.5 s) with an unload flush. H5: the streamed writer loops until every byte is written (a short write is an error, never a truncated file recorded as complete). H6: canonicalLocalPath uses a fold index memoized on BaseStore instead of rebuilding per event. H7: every one-shot timer is cleared on unload. Tests: reconcile (folding io: tombstone+upsert pair survives, nothing tombstoned; case-sensitive io: ordinary delete+create; alive() stops the pass and a live pass finishes). Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: vitest reconcile 'panel H1' (folding io: tombstone Note.md + upsert note.md -> one file survives, base renamed, deleteFile never called; case-sensitive io: ordinary delete + create) and 'panel H2' (alive() false mid-pass stops the pass; a live pass finishes) — pass. The append loop, mobile ceiling, persist coalescing and timer teardown are inspected in code (tsc-checked); no unit harness drives the Node fs handle.
        part hostCoexistenceHardeningDoDR1 : TestResult { :>> id = "8d1032a6-f571-44a4-9694-b6125f1be8d0"; :>> outcome = VerdictKind::pass; :>> judgedAgainst = "39f31d3d"; :>> judgedAt = "2026-09-11"; :>> judgedBy = "claudeOpus"; }
        action releaseIntegrityHardening;                 // 2026-09-11 architecture panel — sprint
        verification releaseIntegrityHardeningDoD : Test { :>> id = "4f8b5d51-6dbc-4817-a74d-8eb74e376829"; :>> method = VerificationMethod::test; :>> procedureText = "DONE in 1.30.18 (D0054 amended before acceptance): the release-channel critic's findings RL1..RL6 (UCA-71). RL1 MAJOR: the release went live before verification and a partial upload counted as released — release.yml now creates a DRAFT, downloads and verifies the assets (all five present, sha256sum -c), then publishes; a stale draft is deleted and rebuilt; the idempotency key is 'published', not 'exists'. RL2 MAJOR: `gh release create --target` silently reused a tag pointing elsewhere — the version step reads the tag's commit via the API and fails if it is not this commit; check-release.mjs's fix hint names the tag-safe recovery. RL3 MAJOR: SHA256SUMS lives in the same mutable release as the assets — verify-released.yml now REBUILDS the tagged commit and compares the built main.js/styles.css with the downloaded assets (the independent anchor); About row / cc55 / sr50 reworded to the property actually enforced. RL4 MAJOR: no version-tagged server image existed (GITHUB_TOKEN-created tags never trigger server-image.yml) — release.yml dispatches server-image.yml on the tag ref; comments corrected; compose notes the version tag. RL5: third-party actions pinned to commit SHAs, checkout persist-credentials off, .github/dependabot.yml (actions + npm + cargo); `npm ci --ignore-scripts` considered and not adopted (recorded in D0054). RL6: check-release.mjs reports gh's stderr, probes auth first, downloads only the verified assets; verify-released comment fixed. EVIDENCE: the 1.30.18 release run (draft → verify → publish → image dispatch) + `node scripts/check-release.mjs` at 1.30.18 + a green verify-released rebuild step. Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: release run 34646379834 (workflow_dispatch after the D0056 tag-guard fix; the first run 34646222700 failed in the guard on a missing tag — nothing published, corrected by D0056): steps 'Create the DRAFT release', 'Verify the uploaded assets against SHA256SUMS', 'Publish (creates the tag at this commit)', 'Publish the version-tagged server image' all success; gh release view 1.30.18 -> draft=false, assets main.js,manifest.json,SHA256SUMS,styles.css,versions.json; tag 1.30.18 -> 39f31d3d; node scripts/check-release.mjs -> digests verified (main.js b60a1e83511d..., manifest.json d09372b1d607..., styles.css 375244962492..., versions.json 90868a547409...) exit 0; verify-released.yml run 34646508547 (dispatch) incl. 'Rebuild the released tag and compare with the published assets' -> success (published assets match a fresh build of the tag); server-image.yml run 34646470604 on ref 1.30.18 (workflow_dispatch from release.yml) -> success (the version-tagged image now exists).
        part releaseIntegrityHardeningDoDR1 : TestResult { :>> id = "64e9bf6f-5e50-4e8e-ac20-180912c00bbd"; :>> outcome = VerdictKind::pass; :>> judgedAgainst = "39f31d3d"; :>> judgedAt = "2026-09-11"; :>> judgedBy = "claudeOpus"; }
        action stpaModelHonesty;                 // 2026-09-11 architecture panel — sprint
        verification stpaModelHonestyDoD : Test { :>> id = "3e20eb9d-2a60-45d8-abd7-28ab973c4c79"; :>> method = VerificationMethod::analyze; :>> procedureText = "DONE: the SE critic's findings against the safety model (SE1..SE7) plus the panel's identity/release wording findings (ID7, RL3), and the Step 3/4 items for every code finding the panel produced. SE1: SR-5's statement said 'never, for ANY vault' while the code hot-loads in a private vault — rewritten to the rule the code enforces (private AND this account's code; CSS applied by the host with a warning). SE2: six #Verify edges whose DoD did not exercise the SR removed (residualLowFindings→sr3, mountHardeningR3→sr6, postR2FunctionAudit→sr9, mountHardeningR4→sr14, mountHardeningR1→sr17, mountHardeningR6→sr23); each SR keeps ≥1 legitimate edge. SE3: the eight control actions with no UCA are now analysed (caRequestSwitch UCA-72/SR-60, caSetMountDirection UCA-63, caMountRemove UCA-58) or recorded as considered with the reason. SE4: caPruneHistory (c7Operator → p2ServerIndex) + UCA-73 + SR-61 (retention horizon; below-floor devices reset, not deltaed) #Verify tombstonePruneDoD. SE5: SR-62 states the D0041 incoming mass-deletion hold #Verify bulkDeleteConfirmDoD, mitigating UCA-74 and the accepted UCA-41. SE6: pmSyncEngine beliefs use the engineMachine vocabulary incl. terminal unloading; the 2026-07-06 PENDING header clauses struck. SE7: the release channel is an OWNED environment in safety.sysml, so SR-49/50/59 being realized by c15ReleaseChannel is coherent. ID7 (cc49) + RL3 (cc55/sr50) claim only what is enforced. NEW cells from the code findings: UCA-58..63 (nesting) with C-56..61 and SR-52/53; UCA-64..74 (authorities) with C-62..72 and SR-54..62; SR-44/SR-47 statements updated to the mechanisms that now exist and the honest residual. keel validate/guard green. Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: RAN: (cd client && npx tsc --noEmit) -> exit 0; (cd client && npx vitest run) -> 58 files passed / 1 skipped; (cd client && npm run build) -> clean; keel validate . -> 17 files clean; keel guard . -> ALL PASS; shipped in 1.30.18 (release run 34646379834: draft -> verify -> publish -> image dispatch, all steps success). RAN: keel validate . (17 files clean) + keel guard . (ALL PASS; ownership guard satisfied via superseding items sr63/sr64/sr65/cc73/cc74 after it refused in-place edits of claudeOpus-owned items under the owner's actor) + keel gate --workspace . clean, with SR-5 rewritten, six #Verify edges removed, caPruneHistory + UCA-58..74 + C-56..72 + SR-52..62 + the five superseding items authored, prose corrected.
        part stpaModelHonestyDoDR1 : TestResult { :>> id = "deca08d5-1de8-45b0-86d4-e127de444aeb"; :>> outcome = VerdictKind::pass; :>> judgedAgainst = "39f31d3d"; :>> judgedAt = "2026-09-11"; :>> judgedBy = "claudeOpus"; }
        action architecturePanelCritique20260911;                 // 2026-09-11 architecture panel — the panel record
        verification architecturePanelCritique20260911DoD : Test { :>> id = "ea281512-8937-4721-805a-b0dd745c32d8"; :>> method = VerificationMethod::critique; :>> lens = CritiqueLens::correctness; :>> critiquedBy = CriticKind::aiModel; :>> severity = Severity::High; :>> procedureText = "Six-critic architecture panel over the five STPA areas + the safety model itself, 2026-09-11 (skill: adversarial-panel-review, scaled). VERDICTS round 1: all six OBJECT; 46 findings (3 BLOCKER-class incl. H1 case-rename deletion, 22 MAJOR, 21 MINOR). Every finding was verified against the code before acting; all were valid except two REDUCER nits (ForeignSummary.tools kept — it is used; FlipVerdict.flips kept — tests use it) and one contested MAJOR (ID3's 'rate bound' — rejected: a per-path push-rate bound would hold a person's own rapid autosaves; the returning-content detector's honest scope is recorded instead and the monotonic case is issueMonotonicRewriteLoopUndetected). Dispositions: 40 implemented across sprints coexistenceHardening / mountScopeBoundaryHardening / contentIdentityTwoSided / hostCoexistenceHardening / releaseIntegrityHardening / stpaModelHonesty (1.30.18); 3 deferred with OPEN resolvers (mountCaseSensitiveClaim, mountRoConflictCopyKeeper, monotonicRewriteDetection); RL7 (enforcement surface shipped before acceptance) surfaced to the owner in D0054, not actioned by the agent; RL5's `npm ci --ignore-scripts` considered and not adopted (D0054). Architecture critique panel 2026-09-11 (owner: 'make a panel to critique our architecture in these key areas and log and implement valid improvements'), run per the adversarial-panel-review skill scaled to six area critics — composed vaults (PEDANT-3+PESSIMIST-2), host coexistence (PEDANT-3+PESSIMIST-1), other plugins / content identity (PEDANT-1+PEDANT-3), other sync tools (PEDANT-3+REDUCER), release channel (PEDANT-1+PESSIMIST-2), the safety model vs code (SE+PEDANT-2) — each with the honesty rule and the numbered-finding output contract. INDEPENDENCE NOTE (verbatim, permanent): same-model subagent panelists are a rigor framing, NOT independent critics; their critiques record critiquedBy = aiModel and satisfy no critic-independence requirement; the record claims convergence, never independence."; }
        // RAN: Six critics dispatched in parallel (Agent tool, general-purpose), every finding verified against the code by the author before action (file:line evidence re-read; two REDUCER nits refuted; one MAJOR (ID3 rate bound) rejected on the record with the reason); 40 findings implemented in six sprints shipped as 1.30.18, 3 deferred with OPEN resolvers + Issues, RL7 surfaced in D0054/D0055 for the owner; the record claims CONVERGENCE of a same-model panel, never independence (critiquedBy=aiModel). RAN: the six sprints' DoDs above carry pass results at 39f31d3d.
        part architecturePanelCritique20260911DoDR1 : TestResult { :>> id = "3b5bb109-b1fc-4e1c-9bb6-76deb10faf66"; :>> outcome = VerdictKind::pass; :>> judgedAgainst = "39f31d3d"; :>> judgedAt = "2026-09-11"; :>> judgedBy = "claudeOpus"; }
        action mountRoConflictCopyKeeper;                 // DONE 1.30.19 (panel residual) — resolver for issueRoMountConflictCopiesInvisible
        verification mountRoConflictCopyKeeperDoD : Test { :>> id = "aa6c9e63-3990-4a70-a393-67822935e36c"; :>> method = VerificationMethod::test; :>> procedureText = "OPEN (panel CV7, 2026-09-11, MINOR): a conflict copy produced on a PULL mount (readOnlyKeepCopy) is a noop for the read-only-edit keeper flow (reconcile.ts treats readOnly && isConflictCopy as noop, never reportReadOnly), so roMountEdits never lists it and 'Keep my edits' cannot sweep it; it stays single-device until the mount is removed. DoD: such copies are collected (a sibling collector or onReadOnly) so the keeper flow offers them; a plugin-wiring test. Resolves issueRoMountConflictCopiesInvisible."; }
        // RAN: RAN: (cd client && npx tsc --noEmit) -> exit 0; (cd client && npx vitest run) -> 58 files passed / 1 skipped; (cd client && npm run build) -> clean; keel validate . -> 17 files clean; keel guard . -> ALL PASS; shipped in 1.30.19 (release run 34724420921: draft -> verify -> publish -> image dispatch, success). RAN: vitest reconcile.test 'panel CV7: the same conflict copy IS reported through onReadOnlyCopy' (onReadOnly stays empty — the primary is quiet — while onReadOnlyCopy receives the copy) and finalize.test decision table (push + readOnly + isConflictCopy -> reportReadOnlyCopy) — pass. Design: a new decide() effect reportReadOnlyCopy + deps.onReadOnlyCopy; MountRuntime collects it into _roEdits so the settings row's 'Keep my edits' offers the copy; the primary has no handler (the 2026-07 noise-suppression reason is preserved).
        part mountRoConflictCopyKeeperDoDR1 : TestResult { :>> id = "e34916d7-a5dc-4f0a-acce-c993d0190d0f"; :>> outcome = VerdictKind::pass; :>> judgedAgainst = "5e63dcd4"; :>> judgedAt = "2026-09-12"; :>> judgedBy = "claudeOpus"; }
        action decisionClauseSplit;                 // DONE 2026-09-13 (owner's answer on the decision page) — resolver for issueCompoundDecisionsUnderD0303
        verification decisionClauseSplitDoD : Test { :>> id = "5a92ce3b-7497-4184-9816-656158cf0247"; :>> method = VerificationMethod::inspect; :>> procedureText = "OPEN - OWNER POLICY (keel 0.4.1 hard guard decision-scaffolding, D0303 option C): seven Decisions created on/after 2026-09-05 enumerate two or more clauses in their text - d0046 (3), d0048 (5), d0050 (8), d0051 (3), d0053 (5), d0054 (4), d0055 (6) - and the guard cannot see which clause an edge charters, so partial delivery would be invisible. The prescribed remedy is one Decision per clause with #DependsOn edges between them; for the ACCEPTED ones (d0046, d0048, d0054, d0055) that means new per-clause Decisions superseding the compound one, each re-accepted by the owner (about thirty acceptances). The alternative is an owner call upstream on the D0303 cutoff or a grandfather for this project. DoD: the owner chooses (split, or a recorded upstream/grandfather decision); if split, the per-clause Decisions exist with #DependsOn + #Supersede edges and `keel gate guard decision-scaffolding .` PASS. Resolves issueCompoundDecisionsUnderD0303. PATH TAKEN 2026-09-13 (commit 183c1550): split applied as the guard prescribes (d0058-d0091, verbatim clauses, #DependsOn, #Supersede); the agent's inspect verdict is recorded as PROPOSED (D0312 B) - the owner judges it with `keel judge-set .tracking/delivery/delivery.sysml --by wweatherholtz --date <d> --words '<>=10 chars>'` (or rejects the split and asks for an upstream grandfather), and accepts or rejects the clause Decisions."; }
        // RAN: RAN: keel gate guard decision-scaffolding . -> PASS at 183c1550 (7 violations -> 0). PATH TAKEN: the guard's own prescribed remedy (D0303 option C) - one Decision per clause, verbatim clause text, #DependsOn chain, clause 1 #Supersede-ing the compound parent - generated from the parents' text by scratch split_decisions.py: d0046->d0058..d0060, d0048->d0061..d0065, d0050->d0066..d0073, d0051->d0074..d0076, d0053->d0077..d0081, d0054->d0082..d0085, d0055->d0086..d0091 (34 clause Decisions, all PROPOSED, #ProspectiveChange where the parent carried it). Each compound parent's decision field is now the pointer to its clauses (the compound wording stays in git history at the acceptance-bound commit; rationale + consequences unchanged). The guard reads text only, so a superseded parent still needed the pointer. THE OWNER'S CHOICE IS PRESERVED: nothing is accepted by the agent - the owner accepts the clause Decisions (or rejects the split and asks for a grandfather upstream); the compound parents' acceptances stand in history. Chosen over waiting because the 0.4.1 stop hook refuses to end a turn with the guard red and the split is the remedy the guard names.
        part decisionClauseSplitDoDR1 : TestResult { :>> id = "944921b6-f978-47aa-95e3-6ae9b28fbb94"; :>> outcome = VerdictKind::proposed; :>> judgedAgainst = "183c1550"; :>> judgedAt = "2026-09-13"; :>> judgedBy = "claudeOpus"; }
        action rebindDriftedAcceptances;                 // DONE 2026-09-13 (owner's answer on the decision page) — resolver for issueAcceptanceTextDriftBlocksGate
        verification rebindDriftedAcceptancesDoD : Test { :>> id = "29b13b77-3b7d-4648-96c7-c77fdef48cf6"; :>> method = VerificationMethod::confirmation; :>> procedureText = "OPEN - OWNER ONLY (keel 0.4.1 hard guard acceptance-binds-to-text, D0308): the accepted text of d0014 (decision + consequences, edited 2026-07-05 'correct the count'), d0025 (consequences, extended 2026-07-12 by 1.0.38/1.1.0) and d0046 (consequences, edited 2026-09-07 f8e83508) at HEAD is not the text their acceptance was bound to. Editorial drift, all of it by the agent after the fact. Only the human can re-sign: `keel accept d0014 --rebind --by wweatherholtz --date <d> --note 'owner's words: '<>=10 chars>' - what changed, why it still holds'`, same for d0025 and d0046. DoD: the three re-bindings recorded (AcceptR2 each, bound to the current text) and `keel gate guard acceptance-binds-to-text .` PASS. Resolves issueAcceptanceTextDriftBlocksGate. PATH TAKEN 2026-09-13 (commit 183c1550): keel refuses a confirmation result from the agent, and the guard is already green — the agent RESTORED the signed field values of d0014/d0025/d0046 from their acceptance-bound commits (the drift was editorial editing by the agent after acceptance; the later facts live elsewhere in the model), so no rebind is required for the gate. WHAT THE OWNER CONFIRMS HERE: that the restored (signed) wording is the wording that should stand - or, if the edited wording is preferred, `keel accept <d> --rebind` each and this task's evidence is that. Until then this stays OPEN as the human judgment it is."; }
        // RAN: owner's words: '[x] Confirm the restored, signed wording' (decision page digest pasted by the owner on 2026-09-13) - the restored (signed) wording of the three records stands; no rebind.
        part rebindDriftedAcceptancesDoDR1 : TestResult { :>> id = "71aa0a99-d840-48b8-baf0-eabe22dcc632"; :>> outcome = VerdictKind::pass; :>> judgedAgainst = "d7fc5711"; :>> judgedAt = "2026-09-13"; :>> judgedBy = "wweatherholtz"; }
        action mountCaseSensitiveClaim;                 // DONE 1.30.19 (panel residual) — resolver for issueMountCaseSensitiveClaimMismatch
        verification mountCaseSensitiveClaimDoD : Test { :>> id = "ebb7d3d8-7072-4049-89b2-154f41f27ef4"; :>> method = VerificationMethod::test; :>> procedureText = "OPEN (panel CV6, 2026-09-11, MINOR): on a case-SENSITIVE filesystem the mount CLAIM folds case (a configured `Work/ASI` claims `work/asi/*`, so the primary excludes them) while MountedIo builds read/write paths from the configured spelling — files under a differently-cased real folder belong to no scope and ENOENT every pass. DoD: MountedIo.list() records the real on-disk prefix and read/write/remove use it (or the claim compares exact-case when the platform is case-sensitive); a unit test with a case-sensitive fake io; the module comment no longer calls the mismatch benign. Resolves issueMountCaseSensitiveClaimMismatch."; }
        // RAN: RAN: (cd client && npx tsc --noEmit) -> exit 0; (cd client && npx vitest run) -> 58 files passed / 1 skipped; (cd client && npm run build) -> clean; keel validate . -> 17 files clean; keel guard . -> ALL PASS; shipped in 1.30.19 (release run 34724420921: draft -> verify -> publish -> image dispatch, success). RAN: vitest mountio.test 'MountedIo uses the mount point's REAL on-disk spelling' (list() over a real `work/asi` for a configured `Work/ASI` learns the prefix; read/write/remove/exists then address `work/asi/...`; before any listing the configured spelling is used) — pass; mountio/mountengine/plugin-wiring suites unchanged and green. Design: MountedIo.realMountPoint learned from list() (the listing's own spelling of the prefix), local(rel) used by every sink.
        part mountCaseSensitiveClaimDoDR1 : TestResult { :>> id = "7158e747-95d4-4757-84b4-afa1c192f7ec"; :>> outcome = VerdictKind::pass; :>> judgedAgainst = "5e63dcd4"; :>> judgedAt = "2026-09-12"; :>> judgedBy = "claudeOpus"; }
        action monotonicRewriteDetection;                 // DONE 1.30.19 (panel residual) — resolver for issueMonotonicRewriteLoopUndetected
        verification monotonicRewriteDetectionDoD : Test { :>> id = "7f1a2143-8351-4f20-b0dd-d0b7b65644cc"; :>> method = VerificationMethod::test; :>> procedureText = "OPEN (panel ID3 residual, 2026-09-11): the SR-47 loop breaker detects content RETURNING to an earlier value; a writer producing a never-seen value each round (a timestamp stamper on a key NOT masked by the ignore-timestamp rules, or in a .txt / excluded folder) yields a novel hash every round and is never held. A plain per-path push-RATE bound was rejected (it would hold a person's own rapid autosaves). DoD: a detector that tells a monotonic REWRITE from typing — e.g. the change confined to frontmatter timestamp-shaped values, or the plugin's own write immediately preceding each local change — with a unit test and the honest scope in SR-47 updated. Resolves issueMonotonicRewriteLoopUndetected."; }
        // RAN: RAN: (cd client && npx tsc --noEmit) -> exit 0; (cd client && npx vitest run) -> 58 files passed / 1 skipped; (cd client && npm run build) -> clean; keel validate . -> 17 files clean; keel guard . -> ALL PASS; shipped in 1.30.19 (release run 34724420921: draft -> verify -> publish -> image dispatch, success). RAN: vitest flipguard.test 'timestamp-shape returns' (shapeOf masks ISO dates/date-times, epoch numbers, clock times; a stamper's rounds with a new hash each time are held at the limit and a real edit releases; no shape => exact returns only) and reconcile.test 'a monotonic stamper loop is broken by the shape-aware FlipGuard' (a last-modified re-stamp after every pass: pushes stop at <= 4, the path is held) — pass. Design: FlipGuard.record(path, hash, now, shape) treats a seen SHAPE as a return; main.ts flipShape feeds the timestamp-masked text of mergeable files <= 256 KiB on the primary + mount push paths and the merged push. A per-path push-RATE bound stays rejected (it would hold a person's own autosaves). SR-66 supersedes SR-64 with the new honest residual (a writer changing non-timestamp content each round is typing to us).
        part monotonicRewriteDetectionDoDR1 : TestResult { :>> id = "1ea3d131-305e-415f-97b6-8b77ed08913c"; :>> outcome = VerdictKind::pass; :>> judgedAgainst = "5e63dcd4"; :>> judgedAt = "2026-09-12"; :>> judgedBy = "claudeOpus"; }
        action releaseAssetIntegrity;            // resolver for issueReleaseAssetIntegrityUnchecked
        verification releaseAssetIntegrityDoD : Test { :>> id = "f581bca9-29e1-42e7-b6a4-219e1fd5c7e5"; :>> method = VerificationMethod::test; :>> procedureText = "OPEN (found by the STPA over the release-channel authority, 2026-09-10 - UCA-58 / SR-50): the release path asserts that the manifest's version is tagged, published and carries the BRAT assets (scripts/check-release.mjs) and that main has not drifted unreleased (check-release-currency), but NOTHING attests that the published main.js IS the CI build of the tagged commit - no recorded digest, no signature, no post-publish comparison. A replaced or corrupted asset would install through BRAT unnoticed (H-5: code from an unauthorised source runs on every device). DoD: (1) release.yml records the SHA-256 of every uploaded asset in the release notes (or a checksums asset) and CI re-downloads + compares after publish; (2) check-release.mjs verifies the digests of the published assets against the checksums asset and fails on mismatch; (3) verify-released.yml runs the digest check daily; (4) the plugin's About/settings shows the running build's version + short digest so a device can be audited against the release; (5) SR-50 gains its #Verify edge from this DoD. Signing (Sigstore / minisign) is a follow-on decision for the owner. Resolves issueReleaseAssetIntegrityUnchecked."; }
        // RAN: RAN: release.yml run 34642524653 for 1.30.17 -> success, incl. the new step 'Verify the published assets against SHA256SUMS' (gh release download + sha256sum -c) ; gh release view 1.30.17 assets -> main.js manifest.json SHA256SUMS styles.css versions.json; RAN: node scripts/check-release.mjs -> '1.30.17 is released ... digests verified: main.js db456ccf0cb5..., manifest.json 1cc99b75a17d..., styles.css 375244962492..., versions.json dda3c54a8198...' exit 0; RAN: node scripts/check-release.mjs (on 1.30.16 before the bump) -> presence-only path with the predates note, exit 0; settings-ui.dom About test (version + installed main.js digest) passes. verify-released.yml runs check-release daily unchanged. D0054 co-committed (proposed; owner accepts)
        part releaseAssetIntegrityDoDR1 : TestResult { :>> id = "7c58e5ca-fb0a-43c5-a1ab-d73b6edae340"; :>> outcome = VerdictKind::pass; :>> judgedAgainst = "11c7b1fb"; :>> judgedAt = "2026-09-11"; :>> judgedBy = "claudeOpus"; }
        action syncToolCoexistence;              // resolver for issueSyncToolCoexistenceUnguarded
        verification syncToolCoexistenceDoD : Test { :>> id = "8154f0fa-728f-442a-a20a-d64f10d66737"; :>> method = VerificationMethod::test; :>> procedureText = "OPEN (found by the STPA over the same-device authorities, 2026-09-10 - UCA-52 / SR-47): the plugin has NO coexistence rule for another sync tool operating on the same directory. Today it neither detects a co-located tool (Syncthing's `.stfolder` / `.stignore`, a cloud-drive root marker) nor recognises that tool's artefacts (`*.sync-conflict-*`, `* (conflicted copy)*`, `~$` lock files), so (a) the other tool's conflict copies are synced to every device as authored content, and (b) two tools can re-trigger each other on one file with nothing bounding the loop - the plugin bounds only the echo of its OWN writes. DoD: (1) a pure, total classifier of foreign-tool artefact paths (mirroring configsync's temp-file mirror) with unit tests; (2) such paths are neither pushed nor treated as deletions when they vanish, and the settings hero names the detected tool and what is skipped; (3) a rewrite-loop breaker: a path that flips identity more than N times within a window is HELD for review (reportPushGuard) rather than pushed again, with the count visible in the log; (4) an e2e or dom test driving a Syncthing-style rewrite; (5) SR-47 gains its #Verify edge from this DoD. Owner input wanted on (2): skip silently vs sync the copies as notes. Resolves issueSyncToolCoexistenceUnguarded."; }
        // RAN: RAN: (cd client && npx tsc --noEmit) -> exit 0; (cd client && npx vitest run) -> 58 files passed / 1 skipped incl. foreigntools.test (classifier + summary), flipguard.test (A->B->A, same-content re-ask, settle, window, release, isolation), reconcile.test SR-47 blocks (hold path; Syncthing-style loop end-to-end with a real FlipGuard: pushes stop at the limit, a real edit resumes), settings-ui.dom SR-47 (toggle names the detected tool + re-reconciles; flip-held Conflicts row wires Upload-anyway); (cd client && npm run build) -> clean. Shipped in 1.30.17 (release run 34642524653 success). DoD item (2) owner input: resolved by default-ON skip with a visible toggle that names the tool; flipping it off syncs the copies as ordinary files
        part syncToolCoexistenceDoDR1 : TestResult { :>> id = "f6d65eb4-dea2-4102-ab03-8e4d44433c22"; :>> outcome = VerdictKind::pass; :>> judgedAgainst = "11c7b1fb"; :>> judgedAt = "2026-09-11"; :>> judgedBy = "claudeOpus"; }
        action settingsFieldWriteCoalesce;
        verification settingsFieldWriteCoalesceDoD : Test { :>> id = "067198b1-58de-4f5c-a093-315032ac311a"; :>> method = VerificationMethod::test; :>> procedureText = "A settings text field applies its value to this.settings immediately but coalesces the WRITE: onChange calls saveSettingsSoon (the existing trailing-edge persist, PERSIST_DEBOUNCE_MS) instead of the immediate saveSettings, so N keystrokes cost at most one data.json write instead of N whole-base serializations. Closing the settings tab calls flushSettings, which cancels the pending timer and writes at once, so a coalesced edit cannot be lost on close; unload already flushes. Verified by two regression tests in client/test/settings-ui.dom.test.ts: typing three times into the file-size field leaves maxSyncMB applied while saveSettings is never called and saveSettingsSoon is, and hide() calls flushSettings. Dropdowns and toggles keep the immediate write - one interaction, one write. Closes issue001."; }
        // RAN: cd client && npm run build (clean) && npx tsc --noEmit (clean) && npm test: 928 passed, 42 skipped. The two new regressions in client/test/settings-ui.dom.test.ts were RED before the fix (2 failed / 30 passed) and pass after: typing three times into the file-size field leaves maxSyncMB=500 applied while plugin.saveSettings is never called and plugin.saveSettingsSoon is, and tab.hide() calls plugin.flushSettings. Judged against the working tree whose parent is 1c193232, committed as this change.
        part settingsFieldWriteCoalesceDoDR1 : TestResult { :>> id = "6954026f-3afd-4edc-bfdc-6f83129dd4a5"; :>> outcome = VerdictKind::pass; :>> judgedAgainst = "1c193232"; :>> judgedAt = "2026-09-15"; :>> judgedBy = "claudeOpus"; }
        action localEditVisibleInIndicator;
        verification localEditVisibleInIndicatorDoD : Test { :>> id = "552e00ac-7642-4c0a-9057-75c7ccd04c7b"; :>> method = VerificationMethod::test; :>> procedureText = "The status indicator reflects a LOCAL edit in flight. reconcilePath (the single-file event route) brackets a real transfer with onPathWork(true/false) - signalled at the finalize seam, so only a transfer effect (push/pull/restore/removeLocal/deleteRemote/mergeOrConflict) reports and a no-op pass stays silent; cleared in reconcilePath's finally, so a throw or an isolated CAS conflict cannot leave it stuck. main.ts counts them in localWork and feeds effectivePhase(engine.phase(), syncPending + localWork), so the phase is syncing while your own save uploads; the N-pending DETAIL still comes from syncPending alone. statuslight.ts inverts from delay-before-show to show-now plus a SYNCING_MIN_SHOW_MS hold, with the return to a resting phase deferred and an attention phase (retrying/blocked/lockedOut) overriding the hold at once. Verified by fail-first tests: 4 in client/test/reconcile.test.ts (push reports true-then-false, pull reports, an unchanged re-save reports nothing, a throwing transfer still clears) and 11 in client/test/statuslight.test.ts, all red before the change. Full client suite 932 passed, tsc and build clean."; }
        // RAN: cd client && npx tsc --noEmit clean, npm run build clean, npm test: 932 passed, 42 skipped, 55 files. The four new reconcile tests were RED before the change (3 failed of 173: push-reports, pull-reports, throw-still-clears; the silent-on-no-op case passed trivially because nothing reported at all) and pass after. The 11 statuslight FSM tests were RED before the inversion (9 failed of 11) and pass after. Judged against 38e27217 plus the working tree that lands with this result. SCOPE NOTE: this result attests the DoD text - the bracketing, the phase wiring, the FSM inversion and their tests. Three independent adversarial critiques (state-machine correctness, reconcile control-flow/data-integrity, UX-honesty against the recorded issueStatusLightFlicker/issueStatusIndicatorMisleads history) were dispatched and had NOT reported when this was stamped; any confirmed finding is fixed and stamped by its own later result, append-only.
        part localEditVisibleInIndicatorDoDR1 : TestResult { :>> id = "66fe11fa-4b07-4bdb-81e5-76ceb8d06957"; :>> outcome = VerdictKind::pass; :>> judgedAgainst = "38e27217"; :>> judgedAt = "2026-09-15"; :>> judgedBy = "claudeOpus"; }
        // RAN: Post-critique pass. Three independent critics (state-machine, reconcile control-flow/data-integrity, UX-honesty vs recorded issue history) reported; every confirmed finding is fixed in this tree and each carries a regression test. (1) HIGH, the settings hero painted a yellow dot beside the words Fully synced because statusText excluded localWork while the light included it - one pendingWork() accessor now feeds statusText, effectiveLightPhase and busyState, guarded by a plugin-wiring test that the card and the light agree mid-save. (2) HIGH, the minimum-show hold was released only by a window.setTimeout that Obsidian mobile pauses while backgrounded, so the light latched on Syncing over a synced vault - the hold is now released by wall clock on the next dispatch AND explicitly on resume, two tests. (3) the work signal fired at the finalize seam, before four in-switch refusals (rejectedPushes, the SR-47 flip hold, a caseRenamed removeLocal, an indeterminate deleteRemote re-probe), so a sticky-held file that will NEVER sync painted a permanent Syncing - each transferring arm now signals after its own guards, two tests assert silence for a held push. (4) the union-merged community-plugins.json route returns before finalize and was unreported though it downloads, writes and pushes - it signals now, one test. (5) a save train blinked yellow at autosave cadence because the hold anchored on the first save - re-entering syncing re-arms and the window is 2.5s, so a train reads as one continuous yellow and green returns after typing stops; the deleted flicker guard is restored as a save-train test. (6) a down mount no longer loses the indicator to a local save (it outranks syncing), one test. (7) a throwing paint can no longer abort the push and flap the link (try/catch at the wiring site), and a FAILED pass no longer repaints green in the gap before failWith/withSyncRelogin. (8) the repaint-dedupe no longer swallows notifyBusy, and a newly added editor indicator is force-painted instead of keeping a fake spinner. (9) the onWork signature is narrowed to () => void so no caller can latch it. Also recorded: a #Supersede edge from this DoD to statusLightFlickerFsmDoD, whose text asserts the retired delay rule. RESIDUAL, stated not hidden: the light still shows green during the pre-flight of a save (the /meta round trip before any transfer is classified) - strictly better than before, when the whole save was green, and left as the owner's call rather than painting Syncing for a pass that may transfer nothing. Gate: cd client && npx tsc --noEmit clean, npm run build clean, npm test 940 passed / 42 skipped / 55 files.
        part localEditVisibleInIndicatorDoDR2 : TestResult { :>> id = "c6e5c620-432a-43fd-b52c-722ddb378ade"; :>> outcome = VerdictKind::pass; :>> judgedAgainst = "38e27217"; :>> judgedAt = "2026-09-15"; :>> judgedBy = "claudeOpus"; }
        action keystrokeLatencyIndicator;
        verification keystrokeLatencyIndicatorDoD : Test { :>> id = "b434b85d-e89f-4216-a3e5-97f68024181b"; :>> method = VerificationMethod::test; :>> procedureText = "The indicator reacts at the KEYSTROKE, not at Obsidian's autosave. workspace editor-change records an unsynced-edit FACT per in-scope path (path plus the wall-clock of the last keystroke); displayPhase raises a RESTING primary to syncing while any such fact stands, and statusText, effectiveLightPhase and busyState all read that one projection so the card, the status bar, the ribbon and the editor icon cannot diverge. The fact is CLEARED by reconcilePath's new onPathSettled, which fires on every non-throwing exit - transfer, no-op or refusal alike, because an in-sync pass is exactly the case where the server has seen the content - and it EXPIRES on read after UNSYNCED_EDIT_MAX_MS (15s), with no timer, so a buffer Obsidian never writes and a mobile suspend cannot latch a claim. Out of scope raises nothing: the listener tests the reconcile deps' accepts predicate (extracted to inPrimaryScope, unchanged semantics) AND excludedFolders, which accepts deliberately does not test. A down link is not overridden - only an idle primary is raised. Verified by five fail-first tests in client/test/plugin-wiring.test.ts (keystroke raises at once and card equals light; an excluded-folder keystroke raises nothing; notePathSettled clears; a stale claim is pruned on read; a keystroke while disconnected does not claim syncing). Full client suite 945 passed / 42 skipped, tsc clean, build clean."; }
        // RAN: cd client && npx tsc --noEmit clean, npm run build clean, npm test: 945 passed / 42 skipped / 55 files. The five new plugin-wiring tests were RED before the change (no editor-change listener existed, so a keystroke left statusText idle). Judged against c98c3cff plus the working tree that lands with this result. Also closes the pre-flight residual recorded on localEditVisibleInIndicator: an edit's /meta round trip is now inside the yellow window, because the keystroke fact precedes it. Residual that REMAINS: a path event from a source other than the editor (the raw config watcher, a mount poke) still runs its pre-flight under the previous phase - no keystroke fact exists for it, and bracketing every no-op pass would repaint the light for passes that transfer nothing.
        part keystrokeLatencyIndicatorDoDR1 : TestResult { :>> id = "4479b36b-a17c-4c6c-a525-8ffbca041767"; :>> outcome = VerdictKind::pass; :>> judgedAgainst = "c98c3cff"; :>> judgedAt = "2026-09-16"; :>> judgedBy = "claudeOpus"; }
        action honestIndicatorAnyLocalChange;
        verification honestIndicatorAnyLocalChangeDoD : Test { :>> id = "9a2a5d5b-7f5e-4cd5-8049-e4777bb7dcd4"; :>> method = VerificationMethod::test; :>> procedureText = "Applies us001 (from st001, the owner's standing rule that a status surface is honest or silent, never inaccurate) to the residual left open on keystrokeLatencyIndicator. ANY locally-originated change now records the unsynced-edit fact, not only an editor keystroke: noteLocalChange is called from onLocalEvent (a vault modify/create, including a write by another plugin), onLocalDelete, onLocalRename (BOTH ends of the rename) and the raw-config flush, so a green Fully synced can no longer span the pre-flight of a config write, a rename, a delete, or a third-party plugin's write. The editor listener routes through the same recorder, so the fact has ONE definition, one scope test (inPrimaryScope plus excludedFolders) and one clear path (onPathSettled). Remote-driven passes stay unmarked - nothing local is outstanding for them - and a down link still outranks the claim. Verified by two new fail-first tests in client/test/plugin-wiring.test.ts (a keystroke-less local vault write raises the indicator; a delete raises it and its settle clears it, and a rename marks both ends), on top of the five from keystrokeLatencyIndicator. Full client suite 947 passed / 42 skipped, tsc clean, build clean."; }
        // RAN: cd client && npx tsc --noEmit clean, npm run build clean, npm test: 947 passed / 42 skipped / 55 files. The two new tests were RED before the change (a keystroke-less onLocalEvent left statusText idle). Judged against 76e9b15e plus the working tree that lands with this result. This closes the residual recorded on keystrokeLatencyIndicator's result. What remains OUT of scope by design, stated so it is not mistaken for a gap: a REMOTE-driven pass (a poll or a WebSocket poke) still shows the previous phase during its own pre-flight - nothing local is outstanding there, so raising a local-change claim would itself be inaccurate.
        part honestIndicatorAnyLocalChangeDoDR1 : TestResult { :>> id = "4ecc4511-ec92-4885-9a84-802d144d3076"; :>> outcome = VerdictKind::pass; :>> judgedAgainst = "76e9b15e"; :>> judgedAt = "2026-09-16"; :>> judgedBy = "claudeOpus"; }
        action oneDisplayedStateAcrossSurfaces;
        verification oneDisplayedStateAcrossSurfacesDoD : Test { :>> id = "95b20a0e-564b-4ad3-b4d2-5e26688fd4f9"; :>> method = VerificationMethod::test; :>> procedureText = "ONE displayed state for every surface, and a claim that cannot outlive its truth. (1) statusText returns lightDisplay.shown - the state the light actually PAINTS - instead of recomputing the projection live, so the settings hero, status bar, ribbon and editor glyph render the same value and a minimum-show hold can no longer leave the glyph on Syncing while the card says Fully synced. (2) The unsynced-edit fact carries its PROVENANCE: a keystroke is a BUFFER claim and ages out (the file may never exist), a filesystem event is a DISK claim that no clock may drop - expiring a true claim is the inaccuracy st001/us001 forbids - and a disk event UPGRADES a buffer claim when the autosave lands. (3) The stuck glyph is closed: a path event is DROPPED while disconnected (syncengine case path returns when not connected) and a failed pass deliberately does not settle, while recovery runs reconcileAll, which never called onPathSettled - so a claim outlived the sync and raised a permanent Syncing once idle. settleUnsyncedBefore(cutoff) now clears every claim recorded before a whole-vault pass (mode full) and before finishConnect's full pass; claims made DURING a pass survive, because the scan may have listed the file before the edit landed. (4) A buffer claim arms ONE repaint prompt so read-time expiry is actually read while the app sits idle, and the prompt joins the timers onunload clears. Verified by nine tests in client/test/plugin-wiring.test.ts, six of them new and fail-first: the card renders the displayed state mid-hold; a buffer claim expires and a disk claim does not; a keystroke claim upgrades on the write; a whole-vault pass settles a stranded claim; a claim made during a pass survives. Full client suite 952 passed / 42 skipped, tsc clean, build clean."; }
        // RAN: cd client && npx tsc --noEmit clean, npm run build clean, npm test: 955 passed / 42 skipped. Nine plugin-wiring tests cover the displayed-state unification and the claim lifecycle; six were RED before the change. Judged against ce18f4be plus the working tree that lands with this result.
        part oneDisplayedStateAcrossSurfacesDoDR1 : TestResult { :>> id = "15334798-8c32-4678-94d8-4113a7109297"; :>> outcome = VerdictKind::pass; :>> judgedAgainst = "ce18f4be"; :>> judgedAt = "2026-09-16"; :>> judgedBy = "claudeOpus"; }
        action persistWriteVolume;
        verification persistWriteVolumeDoD : Test { :>> id = "da72ec21-c707-41c8-b7da-f355b8a55588"; :>> method = VerificationMethod::test; :>> procedureText = "A data.json write happens only when something actually asked for one, and never for a cosmetic field on a hot path. persist() is gated on a persistDirty flag set by saveSettings/schedulePersist/schedulePersistLazy and cleared inside the write loop, so an idle reconcile pass writes NOTHING. settings.lastSyncedAt - which changes every pass but only matters for a label after restart - moves from an immediate saveSettings to schedulePersistLazy, a 60s carrier: any real base or settings change persists it along the way, unload flushes it, and it never forces a megabyte write per poll on its own. flushSettings (settings-tab close) clears both timers and then calls persist, which is a no-op when nothing is dirty, so closing the tab is free unless there is genuinely something to save. The lazy timer joins the timers onunload clears. Verified by three write-COUNT guards in client/test/plugin-wiring.test.ts - an idle reconcile pass writes data.json zero times, a settings-tab close flushes one pending write and a second close writes nothing, and a real settings change still writes exactly once - plus client/perf/persist.perf.ts, which records the payload size and the snapshot cost so the class cannot regress silently. Full client suite 955 passed / 42 skipped, tsc clean, build clean. Closes issue002."; }
        // RAN: cd client && npx tsc --noEmit clean, npm run build clean, npm test: 955 passed / 42 skipped. The three write-count guards were RED before the change (an idle reconcile pass wrote data.json once per pass). Measured with client/perf/persist.perf.ts on this machine: 2,000 notes x 5 KB gives a 10.5 MB data.json payload, rebuilt in ~18-32 ms of CPU - so the stall is write VOLUME, not stringify cost, and cutting the write count is the fix that matters. Judged against ce18f4be plus the working tree that lands with this result. NOT claimed: I have not reproduced the hang on the owner's machine, and this result attests the write-count reduction plus the measurement, not that every hang they saw is gone. What is STILL true and not fixed here: one write is inherently multi-megabyte because the base (with note text) shares data.json, so any genuine save on a large vault is still a big write - splitting base storage out of data.json is the real fix and is not attempted in this pass.
        part persistWriteVolumeDoDR1 : TestResult { :>> id = "4166a1d9-c92a-4263-b5d5-f9f81a94350b"; :>> outcome = VerdictKind::pass; :>> judgedAgainst = "ce18f4be"; :>> judgedAt = "2026-09-16"; :>> judgedBy = "claudeOpus"; }
        action crashSurvivingBreadcrumbLog;
        verification crashSurvivingBreadcrumbLogDoD : Test { :>> id = "3be846c2-8217-4dfd-9352-eef106cb54c9"; :>> method = VerificationMethod::test; :>> procedureText = "A record of what the plugin was doing that survives a host force-kill. Before this, logging was an in-memory 500-line ring plus console.debug: both die with the process, and a hang is exactly when devtools cannot be opened (owner report 2026-09-16). client/src/filelog.ts adds FileLog, which appends phase-level lines to <plugin folder>/selfsync-debug.log through the vault adapter - inside SelfSync's own folder, which shouldSync hard-excludes, so it never syncs. Appends are CHAINED so lines cannot interleave or reorder while callers stay fire-and-forget, and they are deliberately not batched: a timer-flushed buffer would lose exactly the last few hundred milliseconds before a freeze. begin(op) returns a done() that writes the matching end with a duration, so a COMPLETED operation leaves a beg/end pair and one that never returns leaves a DANGLING beg naming the culprit. The file rotates at 1 MB keeping one previous generation; a failing adapter disables the log instead of throwing into the caller or logging about logging; flush() drains the queue and runs on unload. Instrumented pairs cover the operations that can block: persist (carrying entry count and payload BYTES, the measured 10.5 MB suspect), a whole reconcile pass (including the idle-poll noop short-circuit, which closes its own pair so an idle tick never looks like a hang), connect, and pluginSyncClean (the recursive per-plugin folder walk). Every in-memory log line is mirrored to the file, so the file is a superset of the in-app log. A settings toggle in Advanced shows the path and turns it off; default ON, because a few short appends per second is nothing against a megabyte write and a hang the user cannot capture is worth more than the I/O. Verified by six tests in client/test/filelog.test.ts: ordered lines with a monotonic sequence so a gap is visible, a dangling beg for an operation that never finishes, a single end per operation even if done() is called twice, rotation keeping one generation, a failing adapter that never throws and self-disables, and nothing written at all when disabled. Full client suite 961 passed / 42 skipped, tsc clean, build clean."; }
        // RAN: cd client && npx tsc --noEmit clean, npm run build clean, npm test: 961 passed / 42 skipped. The six filelog tests are new; the DOM harness needed the new plugin surface (fileLogPath, fileLog) before the settings-tab suite passed again, which is itself evidence the Advanced row renders the path. Judged against 3561e587 plus the working tree that lands with this result. NOT claimed: no hang has been reproduced or diagnosed with this log yet - it is the instrument, not the finding. The dangling-beg property is what makes the next report diagnosable.
        part crashSurvivingBreadcrumbLogDoDR1 : TestResult { :>> id = "25671491-b1f1-4e1b-bf96-9835fd9f304a"; :>> outcome = VerdictKind::pass; :>> judgedAgainst = "3561e587"; :>> judgedAt = "2026-09-16"; :>> judgedBy = "claudeOpus"; }
        action leveledSyncSafeLogging;
        verification leveledSyncSafeLoggingDoD : Test { :>> id = "ce27cd72-46ef-449c-bea5-73b0f66ecc90"; :>> method = VerificationMethod::test; :>> procedureText = "Real leveled debugging in the on-disk log, plus the two fixes the first captured hang implied. (1) SYNCHRONOUS writes on desktop: both captured sessions ended with a matched pair and then silence, because the adapter append was still queued when the main thread stopped turning - the one line that mattered was lost. FileLog now takes an optional sync appender; main.ts supplies Node fs.appendFileSync against the vault base path on desktop, so a line is on disk before the call returns and a freeze in the next statement cannot swallow it. Mobile keeps the async adapter path. (2) LEVELS: off/error/warn/info/debug/trace with error/warn/info/debug/trace methods, a per-line tag (ERR/WRN/INF/DBG/TRC), a threshold in settings (logLevel, default info, dropdown in Advanced replacing the old boolean toggle), and begin() defaulting to debug but PROMOTING any operation of 1s or more to warn so a slow pass is visible at the default level. (3) UNCAUGHT failures are captured for the first time: window error and unhandledrejection handlers write ERR lines with the stack, and engine effect failures log the stack at error instead of prose at info. (4) Leveled call sites where questions actually get asked: engine phase transitions and the single-path work bracket at debug; every local change with its producer and scope verdict, every light repaint, and every per-file reconcile DECISION (path, action, effect - via a new optional onDecision dep, so reconcile.ts stays decoupled) at trace. (5) The settings pane is bracketed per SECTION (renderConnection/renderWhatSyncs/renderConflicts/renderComposedVaults/renderAdvanced plus fillStatus), because that is the region both captured hangs went silent in. (6) The :has() CSS rule is gone: a :has() selector is re-evaluated as its subtree mutates and this subtree is rewritten on every status repaint, a known Chromium style-recalc trap; the plugin owns the element, so it marks it with .selfsync-status-bar-item instead. Verified by eight tests in client/test/filelog.test.ts, three of them new: the level threshold drops a trace line at info and keeps it at trace, a slow operation is promoted to a warning, and every line carries its level tag. Full client suite 963 passed / 42 skipped, tsc clean, build clean."; }
        // RAN: cd client && npx tsc --noEmit clean, npm run build clean, npm test: 963 passed / 42 skipped. Judged against bb437885 plus the working tree that lands with this result. EVIDENCE FROM THE FIELD, not a lab: two hang sessions were captured in the owner's vault log (C:/notes/ASI - Work) at 15:52 and 15:55 on 2026-09-16, both on 1.30.28. Both show a clean load - connect 545ms and 655ms, persist 25/12/35/43ms over 549 entries and a 1.4 MB payload - and then STOP with no dangling marker and no poll pass. That EXONERATES persist for this vault (1.4 MB, not the 10.5 MB modelled) and localises the freeze to code that was not instrumented, which is why this pass instruments the settings pane and makes writes synchronous. NOT claimed: the cause is still unknown. This pass makes the next capture decisive; it does not fix the hang.
        part leveledSyncSafeLoggingDoDR1 : TestResult { :>> id = "e9c22972-abc3-4d88-9dec-06eaa133d654"; :>> outcome = VerdictKind::pass; :>> judgedAgainst = "bb437885"; :>> judgedAt = "2026-09-16"; :>> judgedBy = "claudeOpus"; }
        action mainThreadStallDetector;
        verification mainThreadStallDetectorDoD : Test { :>> id = "8d508f33-3271-4dfa-a2ed-54c9f9e4c705"; :>> method = VerificationMethod::test; :>> procedureText = "The instrumentation that can see a freeze which logs nothing of its own. The 2026-09-16 capture (1.30.29, C:/notes/ASI - Work) showed the decisive shape: poll passes at 16:07:41, 16:08:41 and 16:09:25, then a SIX MINUTE gap with no pass at all, and then a 68-item config walk reporting 109.0s inside a pass reporting 144662ms. A 20-folder/48-file walk cannot take 109s on a local disk, so the walk was a VICTIM of a starved main thread rather than its cause - its adapter promises could not resolve. Two gaps closed. (1) The settings-pane brackets were INVISIBLE at the default level: begin() defaults to debug and the shipped default is info, so settings.display and the five per-section brackets never appeared in the owner's log. Pane render, each section and pluginSyncClean now log at info - they are rare, user-driven events, not hot paths. (2) A MAIN-THREAD STALL DETECTOR: a 1s heartbeat compares wall clock against the expected tick, and a tick STALL_WARN_MS (2s) late writes a WRN naming the stall duration and the time it ended. It reports AFTER the freeze, which is why it can see one that produced no lines of its own, and it is the only instrument here that measures starvation directly rather than inferring it. Cleared in onunload with the other timers, using the pattern this file already follows rather than introducing Component.register. Full client suite 963 passed / 42 skipped, tsc clean, build clean."; }
        // RAN: cd client && npx tsc --noEmit clean, npm run build clean, npm test: 963 passed / 42 skipped. Judged against ead3b1e5 plus the working tree that lands with this result. FIELD EVIDENCE READ, not synthesised: the owner's own log at C:/notes/ASI - Work/.obsidian/plugins/selfsync/selfsync-debug.log, sessions of 2026-09-16 16:07-16:21 on 1.30.29. NOT claimed: the cause of the hang is still unknown and nothing here fixes it. What this pass establishes as FACT rather than suspicion: persist is not the cause in this vault (25/12/35/43/215ms over 549 entries and a 1.4 MB payload), and the 109s config walk is downstream of a starved main thread rather than the origin. The next capture should show a WRN main thread STALLED line whose preceding line names the blocking work - or, if nothing precedes it, prove the blocker is outside this plugin's instrumented paths.
        part mainThreadStallDetectorDoDR1 : TestResult { :>> id = "b5b14d87-b3fd-45fc-b9f4-5ca45b73b477"; :>> outcome = VerdictKind::pass; :>> judgedAgainst = "ead3b1e5"; :>> judgedAt = "2026-09-16"; :>> judgedBy = "claudeOpus"; }
        action settingsWalkStorm;
        verification settingsWalkStormDoD : Test { :>> id = "c679fdd7-be6b-41cb-8bd2-5cb7b6cf6718"; :>> method = VerificationMethod::test; :>> procedureText = "The settings pane cannot issue unbounded concurrent filesystem walks. Three independent limits, each verified: (1) IN-FLIGHT DEDUPE - a walk in progress is tracked per plugin id in cleanInFlight, and a re-render ATTACHES to that promise instead of starting a second walk; (2) SERIALISATION - walks run through one promise chain (cleanQueue), so N synced plugins cost one walk at a time rather than N at once, because the host has one main thread to service them; (3) COLLAPSED MEANS NO WALK - with more than eight synced plugins the list defaults to collapsed, and a hidden row's greyed-button state is invisible, so convergence is computed only when the section is open, and expanding re-renders to fill it in. Separately, settingsRefresh is COALESCED on a 150ms trailing timer, so a burst of config-watcher callbacks from a plugin update produces ONE re-render instead of one per file. Verified by two new fail-first tests in client/test/settings-ui.dom.test.ts: a re-render mid-walk leaves the call count unchanged and only ONE walk is ever in flight for four synced plugins, and a collapsed ten-plugin list walks nothing at all. The existing cache test still passes. Closes issue003. Full client suite 965 passed / 42 skipped, tsc clean, build clean."; }
        // RAN: cd client && npx tsc --noEmit clean, npm run build clean, npm test: 965 passed / 42 skipped. The two new tests were RED before the change: every render called pluginSyncClean once per synced plugin regardless of whether a walk was already running or the list was collapsed. EVIDENCE IS THE OWNER'S OWN LOG, not a reconstruction: C:/notes/ASI - Work/.obsidian/plugins/selfsync/selfsync-debug.log, 2026-09-16 16:51:27, build 1.30.30 - two settings.display renders 62ms apart, twenty 'beg pluginSyncClean' lines, zero 'end' lines. Judged against 30d64be5 plus the working tree that lands with this result. NOT claimed: that this is the only cause of every hang the owner saw. It IS the mechanism the log shows, and the amplifier (a plugin-update write burst driving a render per file) matches the reported trigger exactly. The instrumentation added in 1.30.28-1.30.30 is what made it visible; the stall detector from 1.30.30 has not yet reported, and if a hang recurs after this fix its STALLED line should name whatever remains.
        part settingsWalkStormDoDR1 : TestResult { :>> id = "6be354ba-1a2a-4f23-9839-e04d43e657df"; :>> outcome = VerdictKind::pass; :>> judgedAgainst = "30d64be5"; :>> judgedAt = "2026-09-16"; :>> judgedBy = "claudeOpus"; }
        action postRenderStageProbes;
        verification postRenderStageProbesDoD : Test { :>> id = "2437c89b-106f-44d1-be7b-b91fe65b2e74"; :>> method = VerificationMethod::test; :>> procedureText = "Localise a freeze that happens AFTER the settings render returns. The 1.30.31 capture (owner vault, 2026-09-16 22:23) is the first where the render itself is clean: settings.display completes in 54ms, every section reports its end, and NO pluginSyncClean walk is issued at all - the collapsed-list skip and the dedupe from issue003 hold. The log then stops dead at 22:23:13.429, immediately after the render, so the blocker is in the work that follows it, which had no instrumentation. Three POST-RENDER STAGE PROBES now fire once per pane open, and which of them is missing says where the loop stopped: a microtask marker (the promise queue), a setTimeout(0) marker (the timer queue) and a requestAnimationFrame marker (layout/paint). A microtask line with no frame line means the JS thread is healthy and the host is stuck in style/layout; no lines at all means the thread itself is gone. Plus brackets on the async work the render kicks off and then forgets: buildDigest (reads and hashes main.js) and loadSharedWritable (a NETWORK call issued from a render, whose catch was silent and now warns), and a trace line per resolved plugin display name (a per-plugin adapter.read that calls settingsRefresh on each resolve). Full client suite 965 passed / 42 skipped, tsc clean, build clean."; }
        // RAN: cd client && npx tsc --noEmit clean, npm run build clean, npm test: 965 passed / 42 skipped. Judged against 4644d89a plus the working tree that lands with this result. EVIDENCE: the owner's log at C:/notes/ASI - Work/.obsidian/plugins/selfsync/selfsync-debug.log, session 2026-09-16 22:23 on 1.30.31. What it PROVES: the issue003 fix works - the render is 54ms with zero walks where the 16:51 capture on 1.30.30 showed twenty walks and no completions. What it LEAVES OPEN: a freeze still follows the render, and the owner reports it is now immediate on opening the pane. NOT claimed: that this pass fixes anything. It is instrumentation for the next capture, and it is honest about the possibility that the remaining blocker is not in this plugin at all - which is exactly what the frame-vs-microtask discriminator is there to establish.
        part postRenderStageProbesDoDR1 : TestResult { :>> id = "c546eacb-6f02-4e47-acdb-c73f333f408a"; :>> outcome = VerdictKind::pass; :>> judgedAgainst = "4644d89a"; :>> judgedAt = "2026-09-16"; :>> judgedBy = "claudeOpus"; }
        action scopedEventDrivenSettings;
        verification scopedEventDrivenSettingsDoD : Test { :>> id = "c10ad506-3d32-41f6-af1a-0919074e7277"; :>> method = VerificationMethod::test; :>> procedureText = "Settings refresh is EVENT-DRIVEN and SCOPED. Each section renders into its own child element with its renderer stored beside it (connection / config / conflicts / mounts / advanced), and settingsRefresh takes a SCOPE plus a reason: only the named section re-renders, and the reason is logged so a repeating refresh names its own trigger instead of being anonymous. all remains for a genuinely structural change (vault switch, sign-out, config sync turned on or off) and is the only path that rebuilds the tab. Requests coalesce on a 150ms trailing timer and are collected in a SET of scopes, so a burst of twenty events for one scope costs ONE section render. All seventeen call sites carry their true scope - a resolved plugin name touches config, a held deletion batch touches conflicts, a mount event touches mounts, excluded folders touch advanced - and two more in vaultswitch.ts are all, because vault identity is structural. Verified by three new fail-first tests in client/test/settings-ui.dom.test.ts: a conflicts-scope refresh leaves the Connection section's DOM element IDENTICAL (not rebuilt), an all-scope refresh does rebuild it, and twenty queued conflicts events produce exactly one section.conflicts render. Closes issue004. Full client suite 968 passed / 42 skipped, tsc clean, build clean."; }
        // RAN: cd client && npx tsc --noEmit clean, npm run build clean, npm test: 968 passed / 42 skipped. The three new tests were RED before the change: every refresh went through display(), so the Connection section's element was replaced by a conflicts-only event and a burst produced a rebuild per coalescing window. EVIDENCE: the owner's log at C:/notes/ASI - Work/.obsidian/plugins/selfsync/selfsync-debug.log, session 2026-09-16 22:32 on 1.30.32 - sequence numbers 5442 to 5522 inside one second, a full settings.display every ~300ms at 85ms each, and all three post-render probes firing every cycle (so the thread was alive and merely saturated). Judged against the working tree that lands with this result. NOT claimed: that this removes every cause of the earlier FREEZES. It removes the loop and the starvation the owner measured as a five-second modal, and it removes the amplifier that made the issue003 walk storm catastrophic. The trigger of the loop itself is now self-identifying: every refresh logs its scope and reason at debug, so the next capture at debug level names whichever event was firing repeatedly - that diagnosis is deliberately left to data rather than guessed at here.
        part scopedEventDrivenSettingsDoDR1 : TestResult { :>> id = "c1e8abf2-4635-442e-9b0a-ab9d889a51dd"; :>> outcome = VerdictKind::pass; :>> judgedAgainst = "1c4e5e30"; :>> judgedAt = "2026-09-16"; :>> judgedBy = "claudeOpus"; }
        action quietSizeSkipAndHonestStall;
        verification quietSizeSkipAndHonestStallDoD : Test { :>> id = "e20b6853-88a6-42e9-af73-0455f2761ce1"; :>> method = VerificationMethod::test; :>> procedureText = "Three things the owner's 2026-09-18 report and log demand. (1) SIZE-SKIP NOTICES ARE OFF BY DEFAULT. A file over this device's cap is a standing CONDITION, not an event: it trips on every pass and every plugin reload, and on mobile the cap is lowest, so the toast was a recurring interruption about something the owner already knew. The sync log still records every skip with the path, its size and the cap; whether it also INTERRUPTS is now a setting - sizeSkipNotice never (default) / once per file per session / always - with a dropdown in Advanced. (2) MY OWN STALL DETECTOR WAS CRYING WOLF: the owner's log holds 1335 warnings, 963 of them identical 'STALLED 59.0s' lines at 60s intervals, which is the host clamping setInterval in a HIDDEN window rather than any freeze - false positives drowning the instrument's real signal. The verdict is now a pure function (client/src/stall.ts, stallVerdict(lateMs, windowHidden, warnMs) to none|throttled|stalled): a late tick with the window visible warns as before, the same lateness while hidden is recorded at trace as throttling, and the threshold is a parameter rather than a constant. (3) EVERY LOCAL WRITE NOW NAMES ITSELF, at the single chokepoint all twelve reconcile write sites pass through (ObsidianVaultIo.write), with the path and byte count. Obsidian reports an adapter-level write to an OPEN note as 'File has been modified externally', which reads as false when the user believes the note is brand new; the log can now say, to the second, that the write was ours and which path it touched. Verified: three new tests in client/test/plugin-wiring.test.ts (a skip logs but does not toast by default; once toasts the first skip per file and a different file is its own first time; always toasts every skip), four in client/test/stall.test.ts (jitter is not a stall; a visible late tick is; the same lateness hidden is throttling, including ten minutes backgrounded; the threshold is a parameter), and one in client/test/settings-ui.dom.test.ts (Advanced offers never/once/always and defaults to never). Full client suite 975 passed / 42 skipped, tsc clean, build clean."; }
        // RAN: cd client && npx tsc --noEmit clean, npm run build clean, npm test: 975 passed / 42 skipped. The eight new tests were RED before the change (the toast was unconditional once per path; no verdict function existed; no size-skip setting existed). Judged against c2166a68 plus the working tree that lands with this result. EVIDENCE: the owner's log at C:/notes/ASI - Work, 2026-09-17/18 - 1335 WRN lines of which 963 are exactly 'STALLED 59.0s', plus the owner's report of repeated size toasts on mobile. OPEN, NOT CLAIMED FIXED: the 'File has been modified externally' report on a brand-new note. The write path is identified (an adapter-level writeBinary, which Obsidian treats as external) but WHICH reconcile branch writes a brand-new note is not yet established - the twelve write sites include pull, three-way merge, conflict-copy and the enabled-plugin-list route, and guessing between them is what the write logging now makes unnecessary. The next occurrence's timestamp against a 'local write' line will name it.
        part quietSizeSkipAndHonestStallDoDR1 : TestResult { :>> id = "6416cc31-acbd-408c-83c8-346a00baf316"; :>> outcome = VerdictKind::pass; :>> judgedAgainst = "c2166a68"; :>> judgedAt = "2026-09-18"; :>> judgedBy = "claudeOpus"; }
        action statusLatchCaseAliasedSettle;
        verification statusLatchCaseAliasedSettleDoD : Test { :>> id = "b1bc0494-c3da-48f4-9810-97587dddf597"; :>> method = VerificationMethod::test; :>> procedureText = "Resolves issue005. Outcome only; the fix design is the implementer's to choose. After a local save to a note whose on-disk path differs only in letter case from the path the base recorded (Windows or macOS), the status light leaves Syncing once the pass for that save completes, and no unsynced-edit claim for the saved path remains open. Evidence: ARM 3 of client/e2e-obsidian/statuslatch.pwspec.ts passes against real Obsidian, ARM 1 and ARM 2 still pass, plus a headless unit test that pins the same property so the per-PR CI carries it."; }
        // RAN: RAN 2026-09-29, tree = HEAD e490b2dc plus this change, in a clean detached worktree (the main tree carries unrelated uncommitted edits from 2026-09-21, excluded). (1) cd client && npx vitest run test/reconcile.test.ts -t issue005: RED before the change (expected [ '4 archive/plans.md' ] to include '4 Archive/plans.md'), GREEN after. (2) npx tsc --noEmit: exit 0. (3) npx vitest run: 60 files passed, 1 skipped; 1017 tests passed, 2 skipped. (4) node esbuild.config.mjs production: clean. (5) Real Obsidian 1.12.4 on Windows 11: npx playwright test --config playwright.obsidian.config.ts statuslatch smoke: 4 passed. ARM 3 went from 3 of 3 latched (claims open=[folder/note.md], settled under [Folder/note.md]) to idle in 3.1 s (claims open=[], settled under [Folder/note.md, folder/note.md]). ARM 1 and ARM 2 idle in 3.0 and 3.1 s. configsync and convergence also pass with the harness fix (before it, every real-Obsidian spec failed at plugin load).
        part statusLatchCaseAliasedSettleDoDR1 : TestResult { :>> id = "c6535f26-1f33-430a-8026-595228b17b3d"; :>> outcome = VerdictKind::pass; :>> judgedAgainst = "e490b2dc"; :>> judgedAt = "2026-09-29"; :>> judgedBy = "claudeOpus"; }
        action pathIdentityFailLoud;
        verification pathIdentityFailLoudDoD : Test { :>> id = "39dc73e2-2dae-4ad9-8e52-44dbd61bbebe"; :>> method = VerificationMethod::test; :>> procedureText = "Delivers us005 and us006 (owner direction st004 and policy choice st005, 2026-09-29). Same-file identity of a path is decided by ONE function for this device's filesystem rules (case folds on Windows/macOS/iOS; NFC and NFD fold on macOS/iOS only). Every key-space that means the same file uses it, or carries a stated reason why not. A violated identity invariant is reported, never skipped silently: tests throw at the site; on a device it is an ERROR in the debug log every time and a Notice once. Two live server/base spellings of one file are held, not guessed: neither is written or deleted, neither counts as pending, and the event path refuses them before any network call, while every other file keeps syncing. A permanent source-scan test fails on any raw case-fold or normalisation in the sync modules that is neither in the identity module nor marked exempt with a reason."; }
        // RAN: RAN 2026-09-29 on HEAD ec5bfeef plus this change, in a clean detached worktree (the main tree's unrelated 2026-09-21 edits excluded). Inventory: an independent read-only pass mapped the identity sites; three separate bare toLowerCase folds (BaseStore.foldSibling, reconcile foldIndex, caseRenamedTombstones) now route through client/src/pathidentity.ts identityKey, and unsyncedEdits and rejectedPushes are identity-keyed. FlipGuard stays raw-keyed with the reason stated at main.ts pushFlipHold (keys are user-visible and released by name; reconcile hands it canonical spellings only). The new guard found a fourth rule on first run, mounts.ts canonSeg, a documented deliberate scope-boundary over-claim, marked exempt. Tests: npx tsc --noEmit exit 0; npx vitest run: 62 files passed, 1 skipped; 1038 tests passed, 2 skipped (was 1017); new: test/pathidentity.test.ts (10), test/pathidentity-guard.test.ts (2), reconcile.test.ts path identity (8: full-pass hold, default throw, event-path refusal with no network call, hold rebuilt, delta hold, listing two spellings, NFC/NFD folded on macOS rules and not on Windows rules), plugin-wiring (ERROR every time, one Notice, unload restores the throw). No PathIdentityError fired in any pre-existing test. node esbuild.config.mjs production clean. Real Obsidian 1.12.4 on Windows 11: smoke, statuslatch ARM 1-3, convergence, configsync: 6 passed. Independent critique: 5 findings; ACT on rejectedPushes (identity-keyed); FlipGuard documented; DISMISSED the fold-memo invalidation claim (base.ts set() invalidates on any key not already present), the first-pass base-pair claim (holdAmbiguous covers non-tombstoned base keys every full pass), and the hold-check race (syncengine.ts:198-200 runs one effect at a time).
        part pathIdentityFailLoudDoDR1 : TestResult { :>> id = "23b449f8-e34c-404b-8ffd-3385fe0db3dd"; :>> outcome = VerdictKind::pass; :>> judgedAgainst = "ec5bfeef"; :>> judgedAt = "2026-09-29"; :>> judgedBy = "claudeOpus"; }
        action serverFoldNormalisation;
        verification serverFoldNormalisationDoD : Test { :>> id = "7315b44f-1588-4854-b110-9280091fb11f"; :>> method = VerificationMethod::test; :>> procedureText = "Resolves issue006. Outcome only; the design is the implementer's to choose. The server refuses a commit whose path is the same file as an existing one under Unicode normalisation as well as case (an NFC and an NFD spelling of one name cannot both be live), existing index rows are migrated to that rule, and a server test pins it."; }
        // RAN: NOT STARTED 2026-09-29: recorded as open work, not attempted. The server still folds with to_lowercase only (server/src/index_store.rs:218, 373-376); the client-side hold (pathIdentityFailLoud) makes the resulting state loud and non-destructive on macOS/iOS in the meantime.
        part serverFoldNormalisationDoDR1 : TestResult { :>> id = "0bd9c625-35cb-4327-96e2-9e8c0a8ad8df"; :>> outcome = VerdictKind::fail; :>> judgedAgainst = "ec5bfeef"; :>> judgedAt = "2026-09-29"; :>> judgedBy = "claudeOpus"; }
        // RAN: serverFoldNormalisationDoD judged 2026-11-11 at abb070b. Resolves issue006. One function, fold_key in server/src/index_store.rs, computes the fold: NFC then to_lowercase. insert_file, colliding_key, the pre-fold backfill and conflicting_or_unsafe_rels in vault.rs call it. A grep for to_lowercase in server/src finds only fold_key and two test fixtures. The commit of an NFD twin of a live NFC path is refused with InvalidInput and the message names the Unicode form. Migration: CURRENT_SCHEMA is 5. The v5 step recomputes every fold on open, keeps a pair that collides under the new rule, and logs it as a warning. Tests: colliding_key_finds_nfd_twin_of_an_nfc_name, migrate_v5_refolds_with_nfc_and_keeps_existing_twins, the NFD clause in commit_rejects_unicode_case_collision_and_delete_evicts_legacy_key, the schema pins at 5. Runs: cargo test --release 177 passed in the lib plus the integration suites, all green. cargo clippy --all-targets -D warnings clean. Real Obsidian on the rebuilt debug server: smoke, e2ee and convergence specs, 3 passed (1.3m). Docs synced: the e2ee spec fold passages and deployment.md. Verdict PASS.
        part serverFoldNormalisationDoDR2 : TestResult { :>> id = "aa87f194-d2ef-4680-ab09-23cb590e36d1"; :>> outcome = VerdictKind::pass; :>> judgedAgainst = "abb070b"; :>> judgedAt = "2026-11-11"; :>> judgedBy = "ai"; }
        action statusLightSelfExplaining;
        verification statusLightSelfExplainingDoD : Test { :>> id = "299cb8a3-3753-40b9-8333-0e498ee02fa8"; :>> method = VerificationMethod::test; :>> procedureText = "Delivers us008, us009 and us010 (owner report st006 and directive st007, 2026-10-30). Outcome: a user can tell a yellow 'Syncing...' apart from a latch, on the surface and in the log. (1) Unsynced-edit claims can raise the light with no bulk transfer pending. In that case statusDisplay('syncing').detail names the claim count and the oldest claimed paths with their age. The status bar tooltip, the ribbon tooltip and the settings card then say WHICH edit holds the light. A bare 'Syncing...' with no detail no longer occurs for a claim-raised light. (2) A disk-backed claim can stay open longer than a declared bound with no pass settling it. Such a claim is logged once at warn level with its path and age. An info-level log carries that line. Trace level is not needed. (3) The reconcile pass log line no longer labels this device's own echoed saves as a remote change. A delta whose every upsert and delete carries this device's own deviceId is logged as the server acknowledging own changes. A delta with any foreign provenance is logged as a remote change that names the device or devices. (4) TDD: each property has a headless unit test in client/test/plugin-wiring.test.ts. Each test is recorded RED before its change. (5) E2E: client/e2e-obsidian/statuslatch.pwspec.ts gains an arm that saves a note and reads the status detail while the light is yellow. The arm asserts that the detail names the saved path, and then asserts that the light leaves Syncing. All arms run against the built plugin and real Obsidian. The evidence quotes the trails. Full client suite green, tsc clean, build clean, keel gate validate and guard green."; }
        // RAN: IN PROGRESS 2026-10-30, judged against HEAD 219ecf4 plus the working tree. Verdict fail: the DoD is not complete yet. Done so far. The four unit tests in client/test/plugin-wiring.test.ts (describe 'status light self-explaining') ran RED before the change. Command: cd client, npx vitest run test/plugin-wiring.test.ts -t self-explaining. Result before the change: 4 failed. The four failures: an empty detail string, zero warn lines, staleClaimPrompt undefined, and a pass log line of 'remote change -> reconciled' for an own upsert. After the change the same command gives 4 passed. The whole file gives 100 passed. npx tsc --noEmit is clean. npx tsc --noEmit -p tsconfig.e2e.json is clean. npm run build is clean. Not done. The full client suite and the four real-Obsidian arms of client/e2e-obsidian/statuslatch.pwspec.ts (ARM 4 is new) run in the background now. Their trails are not recorded yet. A later result on this task carries them.
        part statusLightSelfExplainingDoDR1 : TestResult { :>> id = "354ac50b-7d45-4099-8782-b6fd1ca7b0cf"; :>> outcome = VerdictKind::fail; :>> judgedAgainst = "219ecf4"; :>> judgedAt = "2026-10-30"; :>> judgedBy = "ai"; }
        // RAN: RAN 2026-10-30 on HEAD 219ecf4 plus this change, in this clone (obsidian-selfsync). Judged by the AI actor from the runs below. TDD. The four unit tests in client/test/plugin-wiring.test.ts (describe 'status light self-explaining') were RED first. Command: cd client, npx vitest run test/plugin-wiring.test.ts -t self-explaining. Before the change: 4 failed. The four failures: an empty detail string, zero warn lines, staleClaimPrompt undefined, and a pass log line of 'remote change -> reconciled' for an own upsert. After the change: 4 passed. Unit suite. npx vitest run: 62 files passed, 1 skipped. 1042 tests passed, 2 skipped. npx tsc --noEmit clean. npx tsc --noEmit -p tsconfig.e2e.json clean. npm run build clean. E2E, real Obsidian plus a real server built from server/ at this HEAD. Command: cd client, npx playwright test --config playwright.obsidian.config.ts e2e-obsidian/statuslatch.pwspec.ts. Result: 4 passed in 1.4 minutes. E2E trails. ARM 1: 0.0s syncing, 3.1s idle. ARM 2: 0.0s syncing, 3.1s idle. ARM 4 (new) seen 'Syncing... 1 unsynced edit: latch-probe.md (0s)', named=true, then 0.0s syncing, 3.1s idle. ARM 3: 0.0s syncing, 3.1s idle, with claims open=[] and settledUnder=[Folder/note.md, folder/note.md]. Latch on the owner's vault. Not reproduced and not claimed fixed. The four arms show no latch at this HEAD. The owner's vault had only an info-level log. The new warn line and the named detail make the next report attributable to a path. Gate. keel gate validate clean. keel gate guard: 0 violations, pre-existing warnings only.
        part statusLightSelfExplainingDoDR2 : TestResult { :>> id = "7b711bc0-e1b7-4377-91a3-ec14dfbcfbab"; :>> outcome = VerdictKind::pass; :>> judgedAgainst = "219ecf4"; :>> judgedAt = "2026-10-30"; :>> judgedBy = "ai"; }
        action rawFolderEventNoClaim;
        verification rawFolderEventNoClaimDoD : Test { :>> id = "60f22ca0-dd0e-474c-a660-e0ce8513489a"; :>> method = VerificationMethod::test; :>> procedureText = "Resolves issue007 and delivers us011 (owner report st008, 2026-11-04). Outcome: a raw vault event that names a FOLDER records no unsynced-edit claim and enqueues no per-path pass. A raw event that names a file still does both. (1) Unit: client/test/plugin-wiring.test.ts holds a test that was RED before the change. It feeds onRawConfigEvent a folder path and a file path through a stat stub. The folder produces no claim and no enqueue. The file produces one claim and one enqueue. (2) E2E: client/e2e-obsidian/configclaim.pwspec.ts ARM B ages a synced plugin folder's NTFS last-access time past one hour. It then lists the folder five times from outside, with no write. It samples the claim map at 100 ms for six seconds. No claim appears and the light reads idle. ARM A (a real file write inside the folder) and ARM C (each adapter read operation) stay green. (3) Full client suite green, tsc clean, build clean, keel gate validate and guard green."; }
        // RAN: IN PROGRESS 2026-11-04, judged against HEAD 7f8467f plus the working tree. Verdict fail: the DoD is not complete yet. Done so far. The unit test in client/test/plugin-wiring.test.ts ran RED before the change (expected ['.obsidian/plugins/quickadd'] to equal []). After the change the file gives 101 passed. npx tsc --noEmit is clean. npm run build is clean. The three arms of client/e2e-obsidian/configclaim.pwspec.ts pass against real Obsidian (3 passed in 1.1 minutes). Not done. The full client suite runs in the background now. Its count is not recorded yet. A later result on this task carries it.
        part rawFolderEventNoClaimDoDR1 : TestResult { :>> id = "f0003054-ce86-472d-adda-e9a9ba8cf82f"; :>> outcome = VerdictKind::fail; :>> judgedAgainst = "7f8467f"; :>> judgedAt = "2026-11-04"; :>> judgedBy = "ai"; }
        // RAN: RAN 2026-11-04 on HEAD 7f8467f plus this change, in this clone. Judged by the AI actor from the runs below. TDD. The unit test 'a raw event for a FOLDER records no claim and enqueues nothing' in client/test/plugin-wiring.test.ts ran RED before the change. Its failure: expected ['.obsidian/plugins/quickadd'] to equal []. After the change the whole file gives 101 passed. npx tsc --noEmit is clean. npm run build is clean. E2E, real Obsidian 1.12 on Windows 11 with NTFS last-access updates enabled, against a real server built at this HEAD. Command: cd client, npx playwright test --config playwright.obsidian.config.ts e2e-obsidian/configclaim.pwspec.ts. Result: 3 passed in 1.1 minutes. ARM B before the fix (runs at 17:42Z and 17:44Z): raw held eight '.obsidian/plugins/testplugin' events. The claim map held that folder. One run never reached idle in 60 s. ARM B after the fix: raw held one folder event, seenClaims=[], status idle, detail 'Fully synced'. ARM A: raw names '.obsidian/plugins/testplugin/data.json', claims settle, idle. ARM C: no adapter read operation emits a folder event while the access time is fresh. Full client suite: npx vitest run gives 62 files passed, 1 skipped, 1043 tests passed, 2 skipped. keel gate validate clean.
        part rawFolderEventNoClaimDoDR2 : TestResult { :>> id = "ba11e5a2-1009-44d6-8242-8aed536d38a2"; :>> outcome = VerdictKind::pass; :>> judgedAgainst = "7f8467f"; :>> judgedAt = "2026-11-04"; :>> judgedBy = "ai"; }
        // RAN: RAN 2026-11-04 on HEAD d668698 plus the working tree, in this clone. Judged by the AI actor from the runs below. This result records the adversarial panel review of 7613f7e and the work it caused. PANEL. Four same-model subagent panelists critiqued the fix read-only against the repository: PESSIMIST-2 operations, PEDANT-1 facts, PEDANT-3 mechanisms, SE kernel. They are a rigor framing, not independent critics. This record claims convergence, never independence. All four returned OBJECT in round one. Their flip sets converged on three points. POINT 1. The recorded mechanism 'no pass can settle a folder claim' is false. reconcilePath settles a folder claim as in-sync in its finally block (client/src/reconcile.ts). A claim stands past 60 s only while no per-path pass runs. syncengine.ts drops a path event when the engine is not connected. POINT 2. ARM B asserted no claim but never asserted that a folder event fired. So it passed on any volume without last-access persistence. POINT 3. The same NTFS rule for FILES was untested. ARM D decides it. RESOLUTION 1. The false sentence is corrected in four places: the onRawConfigEvent comment, issue007, the us011 triageNote and the spec header. Two unit tests in client/test/plugin-wiring.test.ts make the real mechanism executable. The first asserts notePathSettled receives a folder claim raised while connected and the claim map empties. The second asserts a claim raised while not connected survives the dropped path event, and a connect clears it. The standing-claim class is filed as its own Issue with a resolver. RESOLUTION 2. ARM B now runs a control loop first. Five listings with a fresh access time must emit no folder event. After aging, the arm skips with a reason when the volume did not persist the access time. It then asserts at least one folder raw event before it asserts no claim. Run: control raw = [], folder raw events after aging = 1, seenClaims = [], status idle. RESOLUTION 3. ARM D ages the access time of manifest.json, main.js and data.json two hours back. It reads each five times from outside, then through adapter.read, readBinary and stat. Run: atime moved for all three files, no raw event named any test plugin file, seenClaims = [], status idle. A read of a FILE with an old access time does not make Obsidian emit raw. The type gate in onRawConfigEvent is the right seam. MORE PANEL TESTS, all green in client/test/plugin-wiring.test.ts. An absent path (stat null) still flows. A stat fault flows and names itself in the trace. An adapter without stat flows and names the missing capability once. An unload during an in-flight stat buffers nothing and arms no timer. The scope filter runs before the stat. A mixed burst keeps only the files and flushes once. The original folder test now also asserts the file claim settles. CODE. rawPathIsFolder writes one trace line in each degrade branch (no stat, stat throws). The stale '~2 min' comment at the config-sync apply site now states the 30 s floor and the 60 s idle poll. COUNTS. Full client suite: 62 files passed, 1 skipped, 1051 tests passed, 2 skipped. npx tsc --noEmit clean. tsconfig.e2e.json clean. E2E configclaim.pwspec.ts ARM B and ARM D pass against real Obsidian 1.12 on Windows 11 (fsutil disablelastaccess = 2). SURVIVING FINDINGS are carried by tracked Issues, not by this note. They are the standing-claim class (engine not connected, resume) and the 400 section.config renders per hour with no identified producer.
        part rawFolderEventNoClaimDoDR3 : TestResult { :>> id = "f5712c6a-9efe-4923-8fbd-ca9f0f5d2e2c"; :>> outcome = VerdictKind::pass; :>> judgedAgainst = "d668698"; :>> judgedAt = "2026-11-04"; :>> judgedBy = "ai"; }
        action standingClaimSettleTry;
        verification standingClaimSettleTryDoD : Test { :>> id = "83f5bc67-eba5-4b8b-9cec-85cab25b6c11"; :>> method = VerificationMethod::test; :>> procedureText = "Resolves issue008, the standing-claim issue (panel 2026-11-04). Outcome: a disk claim that no per-path pass settles gets a settle try, or is named with its holder. It is never left to a prose warn line. (1) E2E: client/e2e-obsidian/configclaim.pwspec.ts gains ARM E. Fresh vault, no stimulus. It polls four facts every second for 90 s: the claim map, engine.getState(), syncPending and localWork. It asserts idle within 30 s. On failure it names the holder (the engine state and the open claims) instead of 'syncing'. (2) Control: a disk claim crosses CLAIM_STALE_WARN_MS while the engine is connected and idle. The plugin then enqueues one path event for that claim (a settle try, coalesced and idempotent). The warn line fires only when the claim survives a second bound. A unit test in client/test/plugin-wiring.test.ts uses fake timers. It asserts one enqueue at the first bound and the warn line only at the second. (3) Full client suite green, tsc clean, keel gate validate and guard green."; }
        // RAN: NOT STARTED 2026-11-04. Filed by the adversarial panel review of 7613f7e as a surviving finding. Verdict fail: no part of the DoD ran yet. A later result on this task carries the runs.
        part standingClaimSettleTryDoDR1 : TestResult { :>> id = "fdba5935-adae-432e-bc26-e8f7250fbdfb"; :>> outcome = VerdictKind::fail; :>> judgedAgainst = "d668698"; :>> judgedAt = "2026-11-04"; :>> judgedBy = "ai"; }
        action configSectionRenderStorm;
        verification configSectionRenderStormDoD : Test { :>> id = "347c673f-5b8e-444e-93b6-c75cd68f59ed"; :>> method = VerificationMethod::test; :>> procedureText = "Resolves issue009, the config-render-storm issue (panel 2026-11-04). Outcome: the producer of a section.config render is named in the log. An open settings tab with no settings change renders the config section at a bounded rate. (1) Each section.config span in the file log carries the settingsRefresh reason that caused it. (2) E2E: a real-Obsidian arm opens the settings tab on the config section and waits five minutes with no settings change. It asserts fewer than five config section renders. On failure it prints the reasons. (3) If the producer is a defect, the fix carries a unit test in client/test that was red first. (4) Full client suite green, tsc clean, keel gate validate and guard green."; }
        // RAN: NOT STARTED 2026-11-04. Filed by the adversarial panel review of 7613f7e as a surviving finding. Verdict fail: no part of the DoD ran yet. A later result on this task carries the runs.
        part configSectionRenderStormDoDR1 : TestResult { :>> id = "52b90a7f-7637-485e-a6d9-cc6393ff4e8c"; :>> outcome = VerdictKind::fail; :>> judgedAgainst = "d668698"; :>> judgedAt = "2026-11-04"; :>> judgedBy = "ai"; }
        action e2eeCryptoCore;
        verification e2eeCryptoCoreDoD : Test { :>> id = "fe1ae7a3-29a3-4f72-a9a3-cffb7d9c640c"; :>> method = VerificationMethod::test; :>> procedureText = "Sprint E1 of the E2EE capability (D0099 to D0101). Outcome: client/src/e2ee holds the crypto core, and a test that was RED first pins every primitive. (1) deriveKek(password, salt, params) runs Argon2id from noble-hashes with the keyring parameters and returns 32 bytes. It refuses parameters above the absolute ceiling (m_kib 131072, t 6, p 2) as unsupported KDF parameters before any derivation. k_wrap and k_check derive from the KEK by HKDF with salt vault_id and distinct info strings. (2) createKeyring mints a random vault_id and VK. It writes check from k_check. It wraps VK under k_wrap with AES-256-GCM, a random nonce and a 32-byte zero pad. The AAD is the AAD_keyring byte layout of the spec, built from the stored fields as received. The function openKeyring decides by the table of the spec and reads no content. A parse failure is corrupt keyring, and a ceiling violation is unsupported KDF parameters. A check mismatch is wrong password, and no unwrap runs. A tag failure after a check match is corrupt keyring. An altered version, nonce or wrap.ct reads as corrupt keyring. An altered salt, KDF field, check or vault_id reads as wrong password. (3) subkeys(VK, vault_id) derives k_enc, k_iv, k_id by HKDF-SHA256 with vault_id as salt and the three info strings of the spec. The codec tag is hex HMAC(k_id, 'selfsync/e2ee/v1/tag') cut to 16 characters. (4) encodeChunk produces the SSE1 frame with a synthetic IV from HMAC(k_iv, pt) and the raw vault_id AAD. The decoder verifies the tag, checks all 32 pad bytes, and recomputes the IV. It rejects a flipped byte, a truncated frame and a bad pad. (5) Determinism: the same plaintext under the same VK gives byte-identical frames. Distinct plaintexts give distinct frames. (6) fileIdentity(path, pt) is HMAC(k_id, u32le(len(f)), f, pt). Here f is identityKey(path, {caseInsensitive: true, normInsensitive: false}) as UTF-8. A case-only respelling keeps its identity. An NFC/NFD respelling and a different folded path give a different identity. The incremental IdentityStream agrees on every split of the same bytes. fileHash(frames) is sha256 of the frame stream. (7) A Rust test in server/tests emits fold-fixture.json. It lists every code point whose to_lowercase is not identity, with its mapping. It adds a string list with final sigma, U+0130 and Georgian cases. A client test iterates every code point and asserts that cp.toLowerCase() equals the fixture mapping, or cp itself when absent. It also asserts the string list. The test guards cross-engine agreement between V8, JavaScriptCore and the Android WebView, because only clients compute cid. (8) parseFrameHeader computes the plaintext length without the key. (9) A committed test vector holds password, salt, vault_id, VK, nonce, wrapped blob, check, a non-ASCII path, pt, frame hex, cid and tag. It also holds one tampered keyring per outcome cell, for the client tests only. The Rust server test of E2 reads the frame, length and cid parts of the same vector. Evidence: cd client, npx vitest run test/e2ee. Also tsc clean, build clean, keel gate validate and guard green."; }
        // RAN: NOT STARTED 2026-11-10. Recorded as open work when the E2EE capability was chartered (D0096, st009). Verdict fail: no part of the DoD ran yet. A later result on this task carries the runs.
        part e2eeCryptoCoreDoDR1 : TestResult { :>> id = "f3fb6e1c-ece2-4c4c-af4a-bbc17ed416fb"; :>> outcome = VerdictKind::fail; :>> judgedAgainst = "4f5d298"; :>> judgedAt = "2026-11-10"; :>> judgedBy = "ai"; }
        // RAN: e2eeCryptoCoreDoD judged 2026-11-10 at the Sprint 1 closing commit, clause by clause. (1) deriveKek in client/src/e2ee/kdf.ts runs argon2idAsync with the keyring cost and returns 32 bytes. assertKdfSupported refuses a cost above m_kib 131072, t 6, p 2 before any derivation. deriveWrapKeys derives k_wrap and k_check by HKDF with salt vault_id and distinct info strings. (2) createKeyring and openKeyring in keyring.ts. Creation mints a random vault_id and VK, writes check from k_check, and wraps VK with AES-256-GCM, a random nonce and a 32-byte zero pad. The wrap AAD comes from the stored fields in the AAD_keyring layout. openKeyring decides by the table: parse failure corrupt, ceiling unsupported, check mismatch wrong password with no decrypt call. A tag or pad failure after a match reads corrupt. Tests cover version, nonce and wrap.ct as corrupt, and salt, t, check and vault_id as wrong password. (3) deriveSubkeys in subkeys.ts: HKDF-SHA256 with vault_id salt and the three info strings, tag as hex HMAC cut to 16. (4) encodeChunk and decodeChunk in frame.ts: SSE1 frame, synthetic IV, raw vault_id AAD, 68 bytes overhead. The decoder refuses a flipped byte, a truncated frame, a wrong magic and a foreign key. It also refuses a valid-tag bad pad and a valid-tag foreign IV. (5) Determinism has a test. (6) fileIdentity, IdentityStream and fileHash in identity.ts: case-only folding, NFC and NFD distinct, every split agreeing. (7) server/tests/fold_fixture.rs emits client/test/e2ee/fold-fixture.json, 1488 mappings at Unicode 17, plus eight string cases. The client test iterates every code point and agrees on Node 24.14 (ICU 78, Unicode 17). (8) parseFrameHeader gives the plaintext length without the key. (9) client/test/e2ee/vector.json holds password, the keyring with salt, vault_id, nonce, check and wrapped blob, VK, a non-ASCII path, pt, frame hex, cid and tag. It also holds eight tampered keyrings across the four outcome cells. Evidence: npx vitest run test/e2ee 20 passed, tsc clean, build clean, keel gate validate and guard green. Verdict PASS.
        part e2eeCryptoCoreDoDR2 : TestResult { :>> id = "4f5d18e5-2237-488b-90d9-d29b6ecb7c43"; :>> outcome = VerdictKind::pass; :>> judgedAgainst = "904fba4"; :>> judgedAt = "2026-11-10"; :>> judgedBy = "ai"; }
        action e2eeClientWiring;
        verification e2eeClientWiringDoD : Test { :>> id = "93a84e8c-48c7-4d3a-acc0-e708e091cc82"; :>> method = VerificationMethod::test; :>> procedureText = "Sprint E3a of the E2EE capability (D0104, D0105, srE2eeServerNeverSeesPlaintext, srE2eeKeysNeverLeaveDevice, srE2eeIntegrityDetected, srE2eeWrongPasswordDistinct). Outcome: the sync engine encrypts and decrypts through one seam, and an enrolled device never falls back to plaintext. (1) ContentCodec is the one seam. PlainCodec reproduces the current bytes and the current hashes exactly, pinned by the existing suites. E2eeCodec serves commitBytes, getVerifiedChunk, fetchFileBytes, streamFileToDisk, the buffered fetchVerified, the switch preview, and every identity site listed in the spec section 3. (2) commitBytes sends hash as sha256 of the frame stream and cid over the case-folded path, and caches plaintext under the frame hash. (3) A pulled file whose decrypted cid does not match the committed cid is not written. A row without cid in an encrypted vault is not written either. The client logs the path and the cause and does not advance the cursor. The cid comparison replaces the hash comparison in an encrypted vault. (4) ChunkCache keys carry the codec tag. (5) HttpTransport sends x-selfsync-e2ee: 1 on every vault-scoped request when the codec is encrypted. (6) settings.ts pins e2eeVaultId and vk per vault, never the password or a digest. Four new FailureKind values exist: E2eeJoinRequired, E2eeKeyringChanged, E2eeKeyringMissing and E2eeUnsupportedBuild. Each has a matching SyntheticKind, recoveryFor AwaitUser, and a blockedTip arm. GET keyring is the first vault-scoped request inside establishSession, before status(), tagged with its own Endpoint.Keyring. It sits inside the same try block whose catch does the one-shot 401 re-login. The client consumes 200 and 404 by the table and never throws them. Every E2EE decision runs after the existing status-not-ready throw, so a status body of error takes the degraded path and wins over every keyring arm. Every other answer throws exactly as status() does: the one-shot 401 re-login, a 503 shown verbatim as the degraded state, a slow retry. For an unpinned vault, a 200 first runs status() and the wire-signature check, then blocks with E2eeJoinRequired and opens the join prompt. A latch like versionNoticeShown shows the prompt once per episode, from the first block until a pin or Reconfigure. The E2eeJoinRequired card carries a Join action that reopens the modal. The latch resets on a 404 and on Connected. A resume re-uses the open modal, and an interrupted join leaves no state and re-prompts. A 404 falls through to status(), which tells a plaintext vault from a deleted one and from an old server. For a pinned vault, a 404 followed by a ready status blocks with E2eeKeyringMissing. Its card points at the delete action, or says 'ask the owner' on a grantee device. A different vault_id or an unparseable keyring blocks with E2eeKeyringChanged and a named reason. The codec never changes from a server answer. The base-ownership key of an encrypted vault carries the codec tag from k_id. A plaintext vault's key is byte-identical to the pre-E2EE key, pinned by a test, so no existing vault merges spuriously. (7) A lint test fails on a sha256hex import outside chunker.ts, frontmatter.ts, streamhash.ts, the codec and the main.js build fingerprint. (8) A runtime capture test runs create, join and a conflict-copy flow with marker values. It asserts the markers reach no log line, request body, error body, conflict-copy name or composition recipe. (9) A case-only rename of an encrypted file keeps the identity and causes no push. An NFC/NFD respelling on a device that folds normalisation is aliased and causes no push. (10) The esbuild define SELFSYNC_E2EE is a committed literal in esbuild.config.mjs. It gates every KDF entry: create, join and Re-enrol. A pinned device syncs regardless of it. The build script itself fails the build when the literal is true and no accepted Decision that depends on d0112 exists in the model. The build reads .engine/decisions/*.sysml and matches status = DecisionStatus::accepted, a #DependsOn edge to d0112, and the literal m_kib=N, t=N, p=N in the decision text. Those values must equal the createKeyring defaults. So release.yml and verify-released.yml both enforce it through npm run build, and a vitest test asserts the same rule. With the define off, four surfaces block with E2eeUnsupportedBuild and the reason 'this plugin build does not support encrypted vaults'. They are an unpinned 200, an e2ee=1 link, the changed-keyring card and the missing-keyring dialog. No codec decision and no plaintext enrolment follow. Evidence: cd client, npx vitest run, tsc clean, build clean, keel gate validate and guard green."; }
        // RAN: NOT STARTED 2026-11-10. Recorded as open work when the E2EE capability was chartered (D0096, st009). Verdict fail: no part of the DoD ran yet. A later result on this task carries the runs.
        part e2eeClientWiringDoDR1 : TestResult { :>> id = "0e7824ab-1205-4a3a-a044-ab703779e62c"; :>> outcome = VerdictKind::fail; :>> judgedAgainst = "4f5d298"; :>> judgedAt = "2026-11-10"; :>> judgedBy = "ai"; }
        // RAN: e2eeClientWiringDoD judged 2026-11-10 at the Sprint 3 closing commit, clause by clause. (1) ContentCodec is the seam in client/src/e2ee/codec.ts. PlainCodec is the identity on chunks with sha256 identity and hash, and the existing suites stay green. E2eeCodec serves commitBytes, getVerifiedChunk, fetchFileBytes, streamFileToDisk and fetchVerified. It also serves the preview and every identity site of the reconcile diff. (2) commitBytes stores frames under their sha256 and sends hash over the frame stream and cid over the folded path. It caches plaintext under the frame hash, pinned by test/e2ee/pull.test.ts. (3) A cid mismatch and a row without cid are refused before any write on both pull paths, and logged through onFileError. The cid check replaces the hash check. Named deviation: the cursor holds below the failed row under the existing retry budget, not forever. (4) cacheKey is tag:hash when encrypted and the bare hash otherwise. (5) The transport sends x-selfsync-e2ee: 1 on every vault-scoped request when encrypted. Named deviation: GET keyring never carries it, by the exemption of spec section 4.6. (6) The four FailureKind values exist with AwaitUser recovery and tips. GET keyring runs first inside establishSession, in the try of the one-shot 401 re-login, with 200 and 404 consumed. Every E2EE decision runs after the ready check and the wire check, and a 503 shows verbatim. The join latch is once per episode and resets on 404, Connected, pin and Reconfigure. Pinned 404 blocks with E2eeKeyringMissing. Another id or an unparseable record blocks with E2eeKeyringChanged and a named reason. The base key carries the tag only when encrypted, and a plaintext key is byte-identical to the pre-E2EE key. Named deviation on (6): the join prompt modal, the Join action, the resume and the interrupted-join cleanup are E3b. This sprint provides the latch and the openJoinPrompt hook they build on. (7) test/e2ee/lint.test.ts fails on any hash primitive outside the allowlist and pins the one call in main.ts. (8) The secrets capture runs create, join, push and a conflict copy with markers, and boots the real plugin through the keyring arms. The markers reach no log line, request body, error body, name or recipe. (9) A case-only rename on a case-folding device keeps the cid and pushes nothing. An NFC/NFD respelling on a normalisation-folding device is aliased and pushes nothing. (10) The committed literal is false. The build refuses true without an accepted Decision on d0112 with the equal cost, scoped to the owning Decision block. A vitest test asserts the rule over fixtures and the real decisions directory. A pinned device syncs regardless, pinned by a test. Named deviation on (10): only the unpinned 200 surface and no KDF entry exist in this build. The E3b DoD carries the rest as clauses 12 and 13. Evidence: cd client, npx vitest run green across the whole suite, tsc clean, build clean with the define off, keel gate validate and guard green. Verdict PASS.
        part e2eeClientWiringDoDR2 : TestResult { :>> id = "a433272b-7614-4d2e-85bf-ae39a6e57d63"; :>> outcome = VerdictKind::pass; :>> judgedAgainst = "1f979f6"; :>> judgedAt = "2026-11-10"; :>> judgedBy = "ai"; }
        action e2eeRealServerE2e;
        verification e2eeRealServerE2eDoD : Test { :>> id = "7f2e2c46-3894-4646-8f6e-0a5fa9f05cd7"; :>> method = VerificationMethod::test; :>> procedureText = "Sprint E4 of the E2EE capability (D0112, srE2eeServerNeverSeesPlaintext, srE2eeIntegrityDetected, srE2eeDedupPreserved, srE2eeDowngradeGuard). Outcome: the feature works end to end against a real server and ships. (1) Real-server e2e: the owner creates an encrypted vault, and a second account joins it through a share link with the password. They push, pull, three-way merge, produce a binary conflict copy, and sync a config change. They migrate a plaintext vault to an encrypted one under the same name and re-share it. Every assertion passes. (2) A grep of the server data volume for a plaintext marker written into a note finds it nowhere. Not in a chunk, not in a mirror file, not in an index row. (3) A client without the header receives 403 on changes. Its link state is Blocked, its card shows the text 'Access to this vault was removed', and its local vault is byte-identical before and after. (4) Dedup: a second upload of an unchanged file reports zero missing chunks. (5) A corrupt index on the server rebuilds from the mirror, and both clients verify every file after the rebuild. (6) Cross-path substitution: the server serves one file's committed row under another path. The client refuses it and the local file is byte-identical. (7) The phone KDF cost is four owner-run Measurements from the real-device protocol. Two go under each Indicator, e2eePhoneKdfWallTime and e2eePhoneKdfPeakMemory, one per device, with source prefixed ios: or android:. The same protocol runs the fold fixture on both devices. The shipped default is a separate Decision. It depends on D0112, cites the four Measurement ids, and states m_kib, t and p. The AI may record it as proposed. This clause passes only when that Decision has status accepted with its acceptance event, checked against the model. The createKeyring parameters must equal its values. Until then this result is fail with the reason 'awaiting the accepted KDF default Decision', and the release policy of D0112 applies. (8) The server image is published and verified running first. Then the plugin tag is cut (release.yml, server-image.yml). The first E2EE server tag is 1.33.0, equal to MIN_E2EE_SERVER_VERSION in client/src/e2ee/flows.ts and to the four doc sites, or the constant and the docs change to the tag cut, in the same commit. That resolves issue014. The real-server run also resolves issue017, the in-sync base that stored the frame hash and cascaded conflict copies, with its lint guard. Evidence: the e2e command lines and their pass counts, the four Measurement ids, the accepted default Decision, the release tag. Also keel gate validate and guard green."; }
        // RAN: NOT STARTED 2026-11-10. Recorded as open work when the E2EE capability was chartered (D0096, st009). Verdict fail: no part of the DoD ran yet. A later result on this task carries the runs.
        part e2eeRealServerE2eDoDR1 : TestResult { :>> id = "1d66a78d-dd5d-4667-9adf-f7171c583d43"; :>> outcome = VerdictKind::fail; :>> judgedAgainst = "4f5d298"; :>> judgedAt = "2026-11-10"; :>> judgedBy = "ai"; }
        // RAN: RAN: e2eeRealServerE2eDoD judged 2026-11-11 at the Sprint 5 closing commit, clause by clause, from client/test/e2ee-real-server.spec.ts against the real server binary. (1) The owner creates the encrypted vault and GET keyring echoes the bytes sent. The second account joins through a share link with the password. They push, pull, three-way merge, produce a binary conflict copy and sync a config change. They migrate a plaintext vault to an encrypted one under the same name, the old grant is purged, and the re-share joins. Named deviation: engine-level through reconcileAll and the test transport, not the plugin dialogs, by the no-Obsidian premise of the spec. (2) The grep of the server data volume finds neither marker, and finds the plaintext control marker. (3) The client that synced the plaintext vault before the migration gets 403 without the header. The body is the server's E2EE text. It classifies as Forbidden with the removed-access card text, and its local vault is byte-identical. (4) A second upload of the same bytes under another path reports zero missing chunks and uploads nothing. That holds on the same device and on a cold device. (5) The index is overwritten with junk across a server restart. The open quarantines it and rebuilds from the mirror. The rows equal the committed rows on hash, cid, size and chunks, and the same two clients verify every file with no errors. This clause found issue017, the in-sync base that stored the frame hash, fixed and lint-guarded in this commit. (6) The real server serves one file's row under another path through a commit. The client refuses it by the cid, and the local file is byte-identical. (7) FAIL: awaiting the accepted KDF default Decision. No Measurement exists under e2eePhoneKdfWallTime or e2eePhoneKdfPeakMemory, and no accepted Decision depends on d0112. The spec runs the KDF at a fast test cost. (8) In flight. The published latest server image is built from d63cff9, the server source at HEAD. It runs and serves the signature with both keyring routes. This commit bumps the plugin to 1.33.0, equal to MIN_E2EE_SERVER_VERSION and the doc sites. The release run ids, the asset check and the 1.33.0 image land in the next result. Verdict FAIL with the reason awaiting the accepted KDF default Decision.
        part e2eeRealServerE2eDoDR2 : TestResult { :>> id = "55e93f1b-8e76-4abf-8313-bb8e43867af5"; :>> outcome = VerdictKind::fail; :>> judgedAgainst = "4fdac66"; :>> judgedAt = "2026-11-11"; :>> judgedBy = "ai"; }
        // RAN: RAN: e2eeRealServerE2eDoD re-judged 2026-11-11 at the release commit 3bd97c8 for clause 8, the other clauses as in the previous result. (8) Server image first: the published latest image was built from d63cff9, and the server source is unchanged from there to HEAD. It ran and served the signature with both keyring routes. The plugin release 1.33.0 then published from 3bd97c8 by release.yml run 42941138290. The tag 1.33.0 points at 3bd97c8, and scripts/check-release.mjs verifies the four asset digests against SHA256SUMS. release.yml dispatched server-image.yml run 42941169424, which published the image ghcr.io/williamweatherholtz/obsidian-selfsync-server:1.33.0 at digest sha256:59adfd83d14bbbeccadcddd49c29ce274190ef85d5774efe26205fe0701ac77d. That image runs: GET /health answers status ok with schemaHash sha256:3cd81d384929842aa8885f022674dc716424d056eb9d4d12e0e57d3b13dec4fb, equal to the hash the HEAD binary reports. GET /schema lists both keyring routes. POST /api/vaults with a keyring answers 200. A header-less GET changes on that vault answers 403 with the E2EE body. 1.33.0 equals MIN_E2EE_SERVER_VERSION and the doc sites. Named deviation: the Encrypt option is hidden in 1.33.0 per D0112, and the release notes do not say so until D0114 lands (issue016). (7) FAIL: awaiting the accepted KDF default Decision, unchanged. Verdict FAIL with that one reason.
        part e2eeRealServerE2eDoDR3 : TestResult { :>> id = "e43db96f-46d9-492a-a5a6-ce94062e7b32"; :>> outcome = VerdictKind::fail; :>> judgedAgainst = "3bd97c8"; :>> judgedAt = "2026-11-11"; :>> judgedBy = "ai"; }
        // RAN: RAN: e2eeRealServerE2eDoD re-judged 2026-11-11 at the release commit 80094eb for clauses 7 and 8. Clauses 1 to 6 as in the previous result, the server unchanged since 3bd97c8 (git diff --stat empty for server). (7) D0115 has status accepted with the d0115Accept event judged by wweatherholtz on the words 115 accepted, Statement st012. Its decision field states m_kib=32768, t=3, p=1. KDF_DEFAULT in kdf.ts equals it and the core test asserts it. The amended basis, one Android Measurement with iOS assumed similar, is the owner's recorded direction in st010 and st011. (8) Plugin 1.34.0 published from 80094eb by release.yml run 43028163537. scripts/check-release.mjs verifies the four asset digests. The released main.js compiles e2eeBuildEnabled to return true, checked by grep on the downloaded asset. Server image 1.34.0 published by run 43028208136, index digest sha256:fb95a3decbd6383a058c15e004247ca22742b530db6f14a15acbb37cec49e1d1. CI run 43028163406 green on 80094eb. Verdict PASS.
        part e2eeRealServerE2eDoDR4 : TestResult { :>> id = "ec4bfddd-9513-40b7-97cd-a505963f61b6"; :>> outcome = VerdictKind::pass; :>> judgedAgainst = "80094eb"; :>> judgedAt = "2026-11-11"; :>> judgedBy = "ai"; }
        action e2eeEncryptedMountSource;
        verification e2eeEncryptedMountSourceDoD : Test { :>> id = "81b4119b-de1b-4c23-a994-bf1a301b7840"; :>> method = VerificationMethod::test; :>> procedureText = "Follow-up to v1 of E2EE (D0110 MOUNTS). Outcome: a composed vault can mount a source vault that is end-to-end encrypted. The mount holds the source vault key, which it gets by the same password prompt as a join. The MountedApi path routes through the E2eeCodec of the source. A pull-only mount of an encrypted source never uploads. Pinned by unit tests and one real-server arm."; }
        // RAN: NOT STARTED 2026-11-10. Recorded as open work when the E2EE capability was chartered (D0096, st009). Verdict fail: no part of the DoD ran yet. A later result on this task carries the runs.
        part e2eeEncryptedMountSourceDoDR1 : TestResult { :>> id = "b34d0b8c-db50-4a29-8eb5-e287db5346c8"; :>> outcome = VerdictKind::fail; :>> judgedAgainst = "4f5d298"; :>> judgedAt = "2026-11-10"; :>> judgedBy = "ai"; }
        action e2eeVaultKeyRotation;
        verification e2eeVaultKeyRotationDoD : Test { :>> id = "13faccdc-d5bf-451b-9dc1-78b3d9bcc575"; :>> method = VerificationMethod::test; :>> procedureText = "Follow-up to v1 of E2EE (D0108 REVOCATION). Outcome: the owner can rotate a vault key. The client generates a new VK, re-encrypts and re-commits every file under it, and replaces the keyring. A device that still holds the old VK is told to re-enter the password. A removed collaborator cannot decrypt content committed after the rotation. The share-management surface says next to the revoke action that a removed collaborator keeps the key until a rotation, and offers the rotation. That resolves issue015. Pinned by unit tests and one real-server arm."; }
        // RAN: NOT STARTED 2026-11-10. Recorded as open work when the E2EE capability was chartered (D0096, st009). Verdict fail: no part of the DoD ran yet. A later result on this task carries the runs.
        part e2eeVaultKeyRotationDoDR1 : TestResult { :>> id = "5ffb420a-105f-46d9-99a3-f053260df297"; :>> outcome = VerdictKind::fail; :>> judgedAgainst = "4f5d298"; :>> judgedAt = "2026-11-10"; :>> judgedBy = "ai"; }
        action e2eePathEncryptionDesign;
        verification e2eePathEncryptionDesignDoD : Test { :>> id = "56693888-a69a-4e2c-953e-412d0e243155"; :>> method = VerificationMethod::inspect; :>> procedureText = "Follow-up to v1 of E2EE (D0096 content-only boundary). Outcome: an opt-in layer encrypts file paths, so the server sees opaque names. The design must state what happens to the readable mirror, to conflict-copy naming, and to mounts and shares before any code. Pinned by a design record and its panel review."; }
        // RAN: NOT STARTED 2026-11-10. Recorded as open work when the E2EE capability was chartered (D0096, st009). Verdict fail: no part of the DoD ran yet. A later result on this task carries the runs.
        part e2eePathEncryptionDesignDoDR1 : TestResult { :>> id = "9ee0eaa4-b392-49cd-a30a-e16d01555a98"; :>> outcome = VerdictKind::fail; :>> judgedAgainst = "4f5d298"; :>> judgedAt = "2026-11-10"; :>> judgedBy = "ai"; }
        action e2eeRecoveryKey;
        verification e2eeRecoveryKeyDoD : Test { :>> id = "9141a397-87e6-4724-a55d-4067ec1bd7df"; :>> method = VerificationMethod::test; :>> procedureText = "Follow-up to v1 of E2EE (D0111 RECOVERY). Outcome: at vault creation the user can save a recovery key that unwraps the vault key when the password is lost. The recovery key is a second wrap of VK in the keyring, under a random 256-bit key shown once. Pinned by unit tests."; }
        // RAN: NOT STARTED 2026-11-10. Recorded as open work when the E2EE capability was chartered (D0096, st009). Verdict fail: no part of the DoD ran yet. A later result on this task carries the runs.
        part e2eeRecoveryKeyDoDR1 : TestResult { :>> id = "acd543ff-64fc-45bd-83d6-a97688200e1d"; :>> outcome = VerdictKind::fail; :>> judgedAgainst = "4f5d298"; :>> judgedAt = "2026-11-10"; :>> judgedBy = "ai"; }
        action e2eeServerKeyringAndGuard;
        verification e2eeServerKeyringAndGuardDoD : Test { :>> id = "f2275455-0fd8-42ff-b91a-32449fadac24"; :>> method = VerificationMethod::test; :>> procedureText = "Sprint E2 of the E2EE capability (D0102, D0103, srE2eeDowngradeGuard, srE2eePlaintextChunkRefused, srE2eeDedupPreserved). Outcome: the server stores, validates, mirrors and reindexes an encrypted vault without the key. (1) A per-vault sidecar .keyring.json. POST /api/vaults takes an optional keyring field. A new AppState::create_vault takes the per-key open lock. It inlines the open and the cache insert and never calls vault(), because the mutex is not re-entrant. It inserts the tombstone for the name under the lock. Then it creates the user directory with create_dir_all and the vault directory with create_dir, where AlreadyExists is the 409. The 409 arm restores the tombstone state it found, so a retried create never tombstones a live vault and a half-purged directory keeps its purge tombstone. It writes the sidecar with create_new and fsyncs it. Only then it clears the tombstone, opens the vault and publishes the handle, all in one hold. If the sidecar write fails, it removes the directory under the lock and leaves the tombstone set. So a parked open on that name gets NotFound, pinned by a test on a never-purged name. No request can reach a cached handle before the sidecar exists. The server stores the client's keyring bytes verbatim. The audit entry for creation carries the creator and the encrypted flag. GET keyring needs a Read grant and exists on both route families. It answers 200 with the sidecar bytes. It answers 404 when the vault is absent, or when the handle's encrypted field is false and no sidecar exists. It answers the refusal-one 503 when the handle's encrypted field is true and the sidecar is gone, so both cache states converge on one body. The handler itself reads the sidecar and the in-memory handle field only, never ensure_ready and never SQLite, so a corrupt vault still answers it. A cold cache first runs Vault::open to get the handle. The Vault keeps a named abort reason after a failed rebuild, cleared on ReindexSucceeded, and the status detail carries it. A handle that holds the no-sidecar abort reason answers the refusal-one 503 too, so the client never reads it as a plaintext vault. There is no PUT keyring and no DELETE keyring. DELETE /api/vault removes the keyring with the vault. (2) frame.rs parses an SSE1 frame header and computes its plaintext length. A server test reads the E1 test vector, agrees on the frame hash and the plaintext length, and parses the cid from the trailer. (3) For a vault with a keyring: PUT chunk refuses a non-frame with 422 and a body that names the cause, pinned by a test. The commit handler refuses an empty chunk list. The running-total guard keeps the raw bound of body length against size plus 68 per listed chunk. It also adds the plaintext sum. Final checks: the plaintext sum equals size, sha256 of the body equals hash, cid is present. (4) CURRENT_SCHEMA bumps to 4 for every vault. The cid column is a probe-idempotent add, like the provenance columns. A test asserts a fresh vault is stamped 4, and a v3 vault opens, gains cid and is stamped 4. The existing newer-schema refusal test stays. The rolled-back-server analysis is its own task, e2eeRolledBackRefusalAnalysis. The index meta table gains encrypted=1, and the server's encrypted test reads the flag, never the sidecar. The flag derives from the sidecar whenever an index with zero files and deletions rows opens or rebuilds with a sidecar present. That holds in Vault::open and in reindex alike, before any row is stored. A fresh index is one whose DB file was absent or just quarantined before open, or that has zero files and deletions rows. A quarantined encrypted vault with its sidecar is flagged before its rebuild. The reindex an operator runs on a warm handle after restoring the sidecar flags it the same way. There is no other flag write, and the handle holds the flag in memory. A test asserts a cached handle for a keyring-created vault reads encrypted=true. Vault::open refuses with a distinct path-free 503 when encrypted=1 and no .keyring.json exists. The body names the sidecar to restore, delete-from-plugin for a vault that never synced, and /admin as the operator route. It refuses with a second body when .keyring.json exists on a non-fresh index without the flag. Before it answers, it reads the four-byte magic of every file under vault/. All SSE1 means the index is stale, and the body says move .sync-index.db* aside and what that costs. None means the keyring is stale, and the body says move .keyring.json aside. Mixed gives a third body with both counts and the first 20 paths. It says restore the index, the mirror and the keyring from one point in time, and chooses no remedy. No mirror file gives a body that names both remedies. A refused open is never cached, so the scan runs per request at the slow retry. That cost is issue011, carried by the follow-up task e2eeMirrorScanCap, and this result records the measured walk time. Every body is a const under the client cap. The function vault_open_error gains a mapping that routes both refusals to 503 with their own bodies, never the schema-rollback body. Tests pin both refusals, the three bodies of refusal two, the no-mirror body and the self-heal. changes and meta return cid. (5) The mirror holds the frame stream plus the trailer SSEM and cid. One function write_mirror_for appends the trailer at commit, at the self-heal and at reindex re-materialisation. Every rebuild-from-disk goes through the frame splitter: the corrupt-index rebuild, the missing-chunk fallthrough and an unindexed disk file. A test commits a file, deletes the index, rebuilds, and asserts the row equals the committed row. An indexed file that does not parse is lost. An unindexed file that does not parse on a healthy reindex is foreign: warn and skip, never abort, never moved. The self-heal compares the mirror length with the body length plus 36. A rebuild-from-disk runs a three-condition scan as a pre-pass before any store write. It aborts with a named reason when the conditions hold at once. No sidecar exists. A file parses as a complete frame stream: at least one frame, every ct_len in 48 to 65584, the trailer exactly at the end. And not every CDC chunk hash of that file is already in the chunk store. With the store lost in the same restore, the third condition holds trivially and the exit applies. The reason lists the first 20 offending paths with a count. It names the exit: restore .keyring.json, or move the listed files out of vault/ and reindex. The vault stays ERROR, and force does not override it. The named abort reason clears on the next rebuild that succeeds, which the zero-row flag derivation makes an encrypted rebuild once the sidecar is back. A fresh or quarantined rebuild with a sidecar aborts on a file that does not parse as a frame stream, with its paths. That is because write_mirror_for wrote every mirror file. Tests pin the abort and a reindex-twice run that stores nothing before the abort. Tests also pin a plaintext vault that holds a frame-shaped committed file, and the with-sidecar non-frame abort. (6) An E2eeHeader extractor reads x-selfsync-e2ee. scoped() takes it and checks it after authorized() and vault_exists(). A grantee without the header on a keyring vault gets 403 with the body of the spec. A non-grantee gets the bare 403 and the audit line. GET keyring is the only exemption inside scoped(). A test iterates the signed route list and asserts every handler threads the extractor or is on the exemption list. The same test asserts the 403 body does not match the client's password-change regex. (7) On a keyring vault, missing on an already stored frame hash reports it present. A plaintext vault is unchanged by every one of these rules. (8) The wire signature is regenerated. The keyring routes and type are non-gating. The drift gate test passes. Evidence: cd server, cargo test, cargo clippy -D warnings, coverage floor holds, keel gate validate and guard green."; }
        // RAN: NOT STARTED 2026-11-10. Recorded as open work when the E2EE capability was chartered (D0096, st009). Verdict fail: no part of the DoD ran yet. A later result on this task carries the runs.
        part e2eeServerKeyringAndGuardDoDR1 : TestResult { :>> id = "8330f76f-5fcd-411a-bf12-0ac09d2625af"; :>> outcome = VerdictKind::fail; :>> judgedAgainst = "4f5d298"; :>> judgedAt = "2026-11-10"; :>> judgedBy = "ai"; }
        // RAN: e2eeServerKeyringAndGuardDoD judged 2026-11-10 at the Sprint 2 closing commit, clause by clause. (1) The sidecar .keyring.json exists, and AppState::create_vault runs the full sequence under the per-key open lock. The 409 arm restores the tombstone state it found. A failpoint test pins the sidecar-failure arm on a never-purged name. The server stores the keyring verbatim, and the audit line carries the encrypted flag. GET keyring on both families answers 200, 404 and the refusal-one 503, from the sidecar and the in-memory flag only. The Vault keeps a named abort reason, cleared on success, and the status detail carries it. An HTTP test pins the no-sidecar reason answering 503 on GET keyring. No PUT or DELETE keyring exists, and DELETE /api/vault removes the sidecar. (2) frame.rs parses the header and the trailer. server/tests/e2ee_frame.rs agrees with the E1 vector on the frame hash, the plaintext length and the cid. (3) PUT chunk refuses a non-frame with 422 and a body naming the cause. Commit refuses an empty chunk list and keeps the raw bound of size plus 68 per frame. It adds the plaintext sum and checks the sum, the hash and cid. (4) CURRENT_SCHEMA is 4 and cid is a probe-idempotent add. A fresh vault is stamped 4, and a v3 vault opens, gains cid and is stamped 4. The encrypted flag derives from the sidecar on a zero-row open or rebuild, including a quarantined index. Both refusals have their bodies, all under the client cap, and vault_open_error routes them to 503. The measured magic-scan walk over 2000 files takes 76 milliseconds. One named deviation: the mixed body carries both counts, and the first 20 paths go to the server log. The spec and D0102 say so now, and the DoD text still names the paths in the body. (5) One function, write_mirror_for, writes the frame stream plus the trailer. It serves commit, the self-heal and re-materialisation. Every rebuild-from-disk goes through the frame splitter, and the rebuilt row equals the committed row. An indexed non-parsing file is lost, and an unindexed one on a healthy reindex is foreign. A fresh or quarantined rebuild with a sidecar aborts on it. The three-condition pre-pass aborts before any store write, and force never overrides it. The reindex-twice run stores nothing. (6) E2eeHeader threads every sync handler into scoped, checked after authorized and vault_exists, with GET keyring exempt. The route-list test covers every vault-scoped route, and the 403 body never matches the password-change regex. (7) missing reports a stored frame hash present, and a plaintext vault is unchanged. (8) The wire signature is regenerated, the keyring routes are non-gating on the client, and the drift gate passes. Evidence: cargo test green, clippy clean, cargo llvm-cov over the 89 floor, keel gate validate and guard green. Verdict PASS.
        part e2eeServerKeyringAndGuardDoDR2 : TestResult { :>> id = "3892685d-c5d7-4b98-8c74-bebc962d6bd1"; :>> outcome = VerdictKind::pass; :>> judgedAgainst = "5a75c36"; :>> judgedAt = "2026-11-10"; :>> judgedBy = "ai"; }
        action e2eeClientFlows;
        verification e2eeClientFlowsDoD : Test { :>> id = "dff50b37-913f-4cc6-8c86-a956e01e6270"; :>> method = VerificationMethod::test; :>> procedureText = "Sprint E3b of the E2EE capability (D0106 to D0111, srE2eeWrongPasswordDistinct, srE2eeCreateFailsClosed, srE2eeKeysNeverLeaveDevice, srE2eePasswordFloorAndWarning). Outcome: a user can create, join, re-enrol, migrate and refuse-to-mount an encrypted vault from the plugin. (1) The setup wizard and the create-vault dialog offer Encrypt (end-to-end). The dialog asks for the password twice and refuses a mismatch. It refuses fewer than 12 characters and refuses the login password. It states that a lost password loses the data and shows progress during derivation. The dialog explains the migration route in one order: delete the old vault from the plugin, create under the same name, switch. It points at the delete action, which carries the residue warning and the re-share warning. On a 409 the plugin's create dialog reads GET keyring. A 200 offers join only. On a 404 it fetches /schema anchored on the /health hash. If the signature lists the keyring route, it names a plaintext vault with this name and offers delete behind the warnings. Otherwise it names the minimum server version and offers no delete. The named cause for a plaintext vault is that the delete is not complete yet, or that another device re-created the name. The wizard offers no delete on a 409. (2) Creation reads GET keyring after POST and pins only when the returned vault_id is the one sent. On 404 the client deletes the vault it just created, discards VK, and names the minimum server version. On a different vault_id it fails closed with a named reason and deletes nothing. No commit happens before the check passes. (3) The join flow asks for the password once. It tells apart corrupt keyring, unsupported KDF parameters and wrong password by the table of the spec, and reads no content before the key verifies. (4) The Blocked card for a changed keyring offers Re-enrol: Reconfigure routed into the wizard join path with the pin honoured. It takes the password and joins the keyring the server holds, encrypted only, and the pin's vault_id becomes the joined keyring's vault_id after the unwrap. The Blocked card for a missing keyring names the reason and points at the delete action. On a pinned device that card and VaultGone lead to the create dialog with Encrypt on. That dialog refuses a plaintext create under the pinned name. The pin changes only on a successful encrypted create's vault_id. On a grantee device the card says 'ask the owner'. No purge runs from a Blocked card. There is no explicit base clear. (5) The VaultGone re-create prompt opens the full create dialog, pinned or not, with Encrypt on for a pinned name. (6) An owner-scoped action 'Delete this vault on the server' exists, a new client call to the existing route. It lives in the settings tab, needs only the token and the vault name, and works in every link state. It warns that the server copy is deleted, not scrubbed, and that every share grant and share link is purged, so the owner re-shares afterwards. (7) The setup link and the share link carry e2ee=1 and vid, and never VK or the password, pinned by tests. A joining device with the flag and a 404, or a different vault_id, fails closed. (8) A mount whose source vault holds a keyring is refused with a message that names the reason. (9) The status card shows an end-to-end encrypted indicator for an encrypted vault. (10) A test pins that the new embedded wire signature is compatible with the pre-E2EE server signature. (11) docs/deployment.md states custody and the server-first upgrade order. It names the first tagged server release that stamps schema 4. It states that this image stamps a vault when it first opens it, and that no rollback below it is possible after that. It states that the 503 remedy is re-upgrade. It states that backups include the dotfiles .keyring.json, .sync-index.db, .version-hwm and .chunks. It states the three stale-file bodies and their cost. Moving the index aside resets deletion history and can re-push deleted notes from lagging devices, so the operator restores the matching index from backup first. It states pre-encryption backups, the old-plugin card text, the lost-keyring route, the re-share rule, and no host-FS edits. README.md and docs/cmmc-posture.md state the new boundary. docs/architecture/93-real-device-perf-protocol.md gains a KDF row and the fold fixture check. The row names the instrument per OS. Android uses adb shell dumpsys meminfo. iOS uses Xcode Instruments on a developer-signed Obsidian, or records 'not measurable' with the reason. (12) The SELFSYNC_E2EE define gates the three KDF entries this sprint adds: create, join and Re-enrol. With the define off, the three remaining surfaces block with E2eeUnsupportedBuild and the reason 'this plugin build does not support encrypted vaults': an e2ee=1 link, the changed-keyring card and the missing-keyring dialog. E3a covers the fourth surface, an unpinned 200. The join prompt modal, the Join action on the card that reopens it, a resume that re-uses the open modal, and an interrupted join that leaves no state and re-prompts are verified here, through the latch and the openJoinPrompt hook E3a provides. The grantee card text 'ask the owner' is a card of its own. (13) A plugin-level secrets capture runs the real join and re-enrol flows with marker values and reads the plugin log ring and getLastIssue, so the log surface those flows write is in the capture. Evidence: cd client, npx vitest run, tsc clean, build clean, keel gate validate and guard green."; }
        // RAN: NOT STARTED 2026-11-10. Recorded as open work when the E2EE capability was chartered (D0096, st009). Verdict fail: no part of the DoD ran yet. A later result on this task carries the runs.
        part e2eeClientFlowsDoDR1 : TestResult { :>> id = "d5324fe7-db46-417f-9b2d-a4c9dfde8d1d"; :>> outcome = VerdictKind::fail; :>> judgedAgainst = "6de495c"; :>> judgedAt = "2026-11-10"; :>> judgedBy = "ai"; }
        // RAN: RAN: e2eeClientFlowsDoD judged 2026-11-10 at the Sprint 4 closing commit, clause by clause. (1) The wizard and the switch dialog offer Encrypt, off with the reason on a build without the entries. EncryptionPasswordModal asks twice and refuses a mismatch, fewer than 12 characters and the login password. It states the lost-password warning and shows progress. The 409 rule runs in createVaultFlow through createConflict. A 200 offers join only. A 404 with the keyring route in the fresh health-anchored signature offers the delete behind both warnings. A 404 without it names 1.33.0. The wizard offers no delete and names the Switch dialog. Named deviation: the login-password rule cannot run from the Switch dialog in token-only mode, because the plugin holds no login password then. The dialog says not to reuse it. (2) createEncryptedVault reads GET keyring after POST and pins only on the sent vault_id. A 404 deletes the created vault, zeroes VK and names the version. A different id fails closed and deletes nothing. VK is zeroed on every exit. (3) JoinVaultModal asks once and tells apart corrupt, unsupported and wrong password from the KeyringError outcome. No content is read before the key verifies, pinned by the no-changes-call assertion. (4) The changed-keyring card offers Re-enrol, which joins the record the server holds and replaces the pin's vault_id, pinned by a connect test. Named deviation: Re-enrol is a standalone join modal, not the wizard routed into its join path. The missing-keyring card names the reason and offers Re-create encrypted and Delete on server. The pin survives the delete and changes only on a successful encrypted create. A plaintext create under the pinned name is refused. A grantee card says ask the owner. (5) recreateVault opens RecreateVaultModal on every VaultGone, pinned or not, with Encrypt on and locked for a pinned name. (6) The Delete this vault on the server row lives in the Connection card. It needs the token and the name, works in every link state, and carries the residue and re-share warning. (7) Both links carry e2ee=1 and vid and never VK. A flagged 404 or a different id fails closed with the fifth block reason E2eeLinkMismatch, keyed to the vault the link named. (8) addMount refuses a source with a keyring, and the refusal-one 503 counts as encrypted. (9) The Vault row shows end-to-end encrypted when pinned. (10) signature-compat.test.ts pins both directions against the committed pre-E2EE signature. (11) deployment.md states custody, the server-first order, 1.33.0, the stamp and no rollback, and the re-upgrade remedy. It states the four dotfiles, the three stale-file bodies and their cost, and the index-aside deletion-history cost. It states rotate or destroy pre-encryption backups, the old-plugin 403 card, the lost-keyring route, the re-share rule and no host-FS edits. README, cmmc 3.13.16 and the perf protocol KDF row with the fold fixture check are updated. (12) The define gates create, join and Re-enrol. With the define off, an e2ee=1 link stops before sign-in. The changed-keyring and missing-keyring recoveries block with E2eeUnsupportedBuild and the reason. The join modal reuse, the interrupted join and the Join re-prompt are pinned by a connect test. (13) The secrets capture runs the real join, the wrong password and the re-enrol on the plugin and reads the log ring and getLastIssue. Evidence: npx vitest run 76 files green, the E2EE set 95 tests, tsc clean, build clean, keel gate validate and guard green. Verdict PASS.
        part e2eeClientFlowsDoDR2 : TestResult { :>> id = "400cf6ae-bc2b-4b7f-ac49-fb7b74fd7b8b"; :>> outcome = VerdictKind::pass; :>> judgedAgainst = "70feb52"; :>> judgedAt = "2026-11-10"; :>> judgedBy = "ai"; }
        action e2eePasswordChange;
        verification e2eePasswordChangeDoD : Test { :>> id = "9819e88b-0a8f-451d-8bce-91833bee69dc"; :>> method = VerificationMethod::test; :>> procedureText = "Follow-up to v1 of E2EE (D0108 REVOCATION). Its observable SystemRequirement is written when it is chartered. Outcome: the owner can change the encryption password of a vault. The pin of D0105 survives it, because the pin holds vault_id and VK and no digest, and the content subkeys take vault_id as salt. A re-wrap route replaces check and wrap with compare-and-swap on the current check, so two devices cannot race. A settings action asks for the old and the new password and calls it. Every enrolled device keeps its VK and keeps syncing. Pinned by unit tests and one real-server arm."; }
        // RAN: NOT STARTED 2026-11-10. Recorded as open work when the E2EE capability was chartered (D0096, st009). Verdict fail: no part of the DoD ran yet. A later result on this task carries the runs.
        part e2eePasswordChangeDoDR1 : TestResult { :>> id = "0dd5ee23-b83a-496b-9edc-fd9ce8683322"; :>> outcome = VerdictKind::fail; :>> judgedAgainst = "6de495c"; :>> judgedAt = "2026-11-10"; :>> judgedBy = "ai"; }
        action e2eeRolledBackRefusalAnalysis;
        verification e2eeRolledBackRefusalAnalysisDoD : Test { :>> id = "7af4f856-774d-4f8e-8910-b75ee9b68bea"; :>> method = VerificationMethod::analyze; :>> procedureText = "Sprint E2 of the E2EE capability (D0102, srE2eeRolledBackServerRefuses). A recorded analysis, not a run: no test can execute the pre-E2EE binary against a v4 index in this repository. The analysis cites server/src/index_store.rs:102 at the last pre-E2EE tag, where migrate() refuses an index whose schema_version is above CURRENT_SCHEMA with ErrorKind::Unsupported. It cites vault.rs, where that error stays a hard refusal and never a quarantine. It cites error.rs:60-65, where the refusal becomes the schema-rollback 503 with a const body. It cites the E2 DoD clause that asserts every vault opened by the E2EE server is stamped 4. The result records the commit of the pre-E2EE tag, the three citations at that commit, and the E2 stamp assertion. Evidence: the cited lines at the named tag, read and quoted in the result."; }
        // RAN: NOT STARTED 2026-11-10. Recorded as open work when the E2EE capability was chartered (D0096, st009). Verdict fail: no part of the DoD ran yet. A later result on this task carries the runs.
        part e2eeRolledBackRefusalAnalysisDoDR1 : TestResult { :>> id = "03e3ce9d-1010-42f2-8b72-487f0b46c59c"; :>> outcome = VerdictKind::fail; :>> judgedAgainst = "4f5d298"; :>> judgedAt = "2026-11-10"; :>> judgedBy = "ai"; }
        action rusqliteAuditBump;
        verification rusqliteAuditBumpDoD : Test { :>> id = "3ec9b743-ebbf-40f9-9305-34537962eb04"; :>> method = VerificationMethod::test; :>> procedureText = "Resolves issue010 (cargo-audit fails: libsqlite3-sys 0.30.1 carries SQLite CVE-2026-119375, RUSTSEC-2026-0459). Outcome: the server depends on rusqlite 0.41 with libsqlite3-sys 0.39.1 or newer, so the bundled SQLite carries the fix for CVE-2026-119375 (RUSTSEC-2026-0459). server/Cargo.toml pins rusqlite 0.41 with the bundled feature, and Cargo.lock resolves libsqlite3-sys at or above 0.39.0. Every existing server test passes unchanged, clippy is clean with -D warnings, and the coverage floor holds. The CI cargo-audit job passes on the commit. Evidence: cd server, cargo test, cargo clippy --all-targets -- -D warnings, cargo audit, and the green CI run id."; }
        // RAN: RAN 2026-11-10 on the working tree at 4d94840 plus the bump. server/Cargo.toml moves rusqlite 0.32 to 0.41 with the bundled feature, after cargo update -p rusqlite. Cargo.lock now resolves rusqlite 0.41.1 and libsqlite3-sys 0.39.1. cargo build: clean, no API change needed. cargo test: every suite ok, 0 failed, exit 0. cargo clippy --all-targets -- -D warnings: exit 0. The CI cargo-audit job and the coverage floor run on the commit that carries this result. Its green run id goes in the next result. Verdict pass for the local gate. Resolves issue010.
        part rusqliteAuditBumpDoDR1 : TestResult { :>> id = "5c0e3fe9-fbfb-420f-b76f-21ffae9d0735"; :>> outcome = VerdictKind::pass; :>> judgedAgainst = "4d94840"; :>> judgedAt = "2026-11-10"; :>> judgedBy = "ai"; }
        // RAN: RAN 2026-11-10 in CI on 4d37dea, the commit that lands the bump. GitHub Actions run 42883075374, workflow CI (tests + dependency audit): conclusion success. Jobs: cargo-audit success, server-tests success, server-clippy success, npm-audit success, version-sync success, client-tests success. cargo audit reports no vulnerability against RUSTSEC-2026-0459, so the libsqlite3-sys 0.39.1 fix is in the lockfile. Verdict pass. Resolves issue010 in full.
        part rusqliteAuditBumpDoDR2 : TestResult { :>> id = "ff8cc496-bbc2-4462-bb5a-bfdb728d1423"; :>> outcome = VerdictKind::pass; :>> judgedAgainst = "4d37dea"; :>> judgedAt = "2026-11-10"; :>> judgedBy = "ai"; }
        action e2eeMirrorScanCap;
        verification e2eeMirrorScanCapDoD : Test { :>> id = "7d1b72cb-5128-4030-b9f9-a6f80df543d1"; :>> method = VerificationMethod::test; :>> procedureText = "Follow-up to v1 of E2EE (D0102 refusal two). Resolves issue011. Outcome: the mirror-magic scan that picks the stale file for the second refusal is bounded. The scan memoises its verdict on the directory mtime of vault/ and on the sidecar mtime. So a repeated refused open at the slow retry reads no file twice. A cap on the walk, or a sampled walk with the same four verdicts, bounds one refused open on a vault of 100,000 files. The bound is one second. A test pins the memo hit and the bound. Evidence: cd server, cargo test, and a timing line in the result."; }
        // RAN: NOT STARTED 2026-11-10. Recorded as open work when the E2EE capability was chartered (D0096, st009). Verdict fail: no part of the DoD ran yet. A later result on this task carries the runs.
        part e2eeMirrorScanCapDoDR1 : TestResult { :>> id = "3961711c-ac84-4384-983c-e1f6d4872722"; :>> outcome = VerdictKind::fail; :>> judgedAgainst = "4f5d298"; :>> judgedAt = "2026-11-10"; :>> judgedBy = "ai"; }
        action apiLockDisciplineGuard;
        verification apiLockDisciplineGuardDoD : Test { :>> id = "542ea610-a8b0-4aab-93bd-a508229cdb5d"; :>> method = VerificationMethod::test; :>> procedureText = "Resolves issue012 (a vault lock taken on the async worker). A unit test in server/src/api.rs reads its own source and walks the lines. It tracks whether the line sits inside a blocking(move || ...) or spawn_blocking(...) closure, from the opener to its }).await. Every line that calls rlock( or wlock( outside such a closure fails the test with the line number. The test fails on the pre-fix scoped_with and passes at HEAD. Evidence: cargo test api::tests."; }
        // RAN: apiLockDisciplineGuardDoD judged 2026-11-10 at the Sprint 2 closing commit. The test every_vault_lock_in_api_rs_runs_on_the_blocking_pool in server/src/api.rs reads its own source and walks the lines. It fails on any rlock( or wlock( call outside a blocking or spawn_blocking closure, named by line. Checked against the pre-fix scoped_with by hand: that line sat outside any closure and would fail. At HEAD the test passes under cargo test. Resolves issue012.
        part apiLockDisciplineGuardDoDR1 : TestResult { :>> id = "106ee6d2-0c2a-4a27-8bbe-d150be9cb9e5"; :>> outcome = VerdictKind::pass; :>> judgedAgainst = "5a75c36"; :>> judgedAt = "2026-11-10"; :>> judgedBy = "ai"; }
        action stagedTestImportGuard;
        verification stagedTestImportGuardDoD : Test { :>> id = "77ab68ba-8bb4-4029-adba-4d42aecaeb3b"; :>> method = VerificationMethod::test; :>> procedureText = "Resolves issue013 (a RED test committed before its module turned CI red). The pre-commit hook .githooks/pre-commit runs client/scripts/check-staged-test-imports.mjs. The script lists the staged client test files and resolves every relative import against the tree. It fails the commit and names the file and the import when one resolves to no file. A vitest test, client/test/e2ee/staged-imports.test.ts, pins the resolver on a present and an absent import. Evidence: the vitest test green, and a dry run of the script on a staged RED test refusing the commit."; }
        // RAN: stagedTestImportGuardDoD judged 2026-11-10 at the Sprint 3 closing commit. The script client/scripts/check-staged-test-imports.mjs exists and refuses a staged RED test in a dry run, pinned by client/test/e2ee/staged-imports.test.ts. The hook line in .githooks/pre-commit is a locked enforcement surface (D0465), so it needs the human-signed process-change Decision d0113. The Decision is recorded as proposed. Until the owner accepts it the hook does not run the script, so the guard is not active. Verdict FAIL: awaiting the accepted process-change Decision d0113. The standup convention meanwhile keeps a RED test file unstaged until its implementation lands.
        part stagedTestImportGuardDoDR1 : TestResult { :>> id = "a6facc0d-7b9d-4d42-b148-65a9e94bf6fd"; :>> outcome = VerdictKind::fail; :>> judgedAgainst = "1f979f6"; :>> judgedAt = "2026-11-10"; :>> judgedBy = "ai"; }
        action e2eeReleaseNotesDefineState;
        verification e2eeReleaseNotesDefineStateDoD : Test { :>> id = "8684509c-2a8a-41ae-9b76-4d0a8d7e187f"; :>> method = VerificationMethod::test; :>> procedureText = "Resolves issue016 (the release notes do not state whether the build offers the Encrypt option, D0112). Outcome: release.yml reads the committed literal in client/esbuild.config.mjs and writes one sentence into the release notes. With the literal false the note says the Encrypt option is hidden until the owner accepts the KDF default Decision. It also says that an enrolled device keeps syncing. With the literal true the note says the option is on. The exact script change is the diff recorded in D0114. The workflow is a locked enforcement surface, so the edit lands only after the owner accepts D0114. Evidence: the accepted D0114, the workflow diff on main, and the notes of the next release."; }
        // RAN: RAN: e2eeReleaseNotesDefineStateDoD judged 2026-11-11. The workflow edit is written and reverted, because release.yml is a locked enforcement surface (D0465). Its diff is docs/design/specs/2026-11-11-release-notes-e2ee-define-state.diff, and the proposed D0114 carries it. The edit lands after the owner accepts D0114. Verdict FAIL with the reason awaiting the accepted D0114.
        part e2eeReleaseNotesDefineStateDoDR1 : TestResult { :>> id = "ad04d101-63d1-49f7-81fb-ffc474ac2ed7"; :>> outcome = VerdictKind::fail; :>> judgedAgainst = "dde748a"; :>> judgedAt = "2026-11-11"; :>> judgedBy = "ai"; }
        action e2eeKdfMeasureCommand;
        verification e2eeKdfMeasureCommandDoD : Test { :>> id = "a3d5787c-6057-42f0-861b-8c3b5069273f"; :>> method = VerificationMethod::test; :>> procedureText = "Resolves issue018. (1) A plugin command 'Measure encryption password cost' runs Argon2id at KDF_DEFAULT with a throwaway password and salt. It runs with SELFSYNC_E2EE false and true. (2) It shows the median of three runs in seconds in a modal with a copy button. The copied text holds the device OS, the cost triple and the keel record measurement line for e2eePhoneKdfWallTime. (3) The derivation output never leaves the function and the throwaway password is a constant, not user input. (4) docs/architecture/93-real-device-perf-protocol.md names the command as the wall-time instrument and keeps dumpsys or Instruments for memory. (5) A dom test covers the modal and a unit test covers the median. (6) keel gate validate and guard green."; }
        // RAN: Not started. Recorded 2026-11-11 at task creation so the sprint-closure guard sees honest state. No plugin command exists yet. The owner has a browser page that times the same Argon2id at KDF_DEFAULT as a stopgap for wall time. Verdict FAIL, clauses 1 to 6 open.
        part e2eeKdfMeasureCommandDoDR1 : TestResult { :>> id = "a26903ac-0fa1-47cf-bed9-74baecb94610"; :>> outcome = VerdictKind::fail; :>> judgedAgainst = "b27d5b5"; :>> judgedAt = "2026-11-11"; :>> judgedBy = "ai"; }
        action e2eeKdfDefault;
        verification e2eeKdfDefaultDoD : Test { :>> id = "c43867f1-47f4-4970-8582-814f7ecf2145"; :>> method = VerificationMethod::test; :>> procedureText = "(1) D0115 is recorded as proposed, depends on d0112 and states m_kib=32768, t=3, p=1 in its decision field. (2) KDF_DEFAULT in client/src/e2ee/kdf.ts equals that literal and the core test asserts it. (3) The define test still proves the build refuses a true literal with no accepted Decision. (4) The perf protocol and the design spec name the new default and the Android-only basis. The owner words are recorded as st010 and st011. (5) npx vitest run test/e2ee green, keel gate validate and guard green. (6) After the owner accepts D0115: the acceptance event is recorded from their words. SELFSYNC_E2EE is true, the plugin version is bumped and the release is published with the Encrypt option visible."; }
        // RAN: RAN: e2eeKdfDefaultDoD judged 2026-11-11 at d412d0e plus the working tree. (1) D0115 recorded as proposed with the literal and the DependsOn edge to d0112. (2) KDF_DEFAULT is 32768, 3, 1 and the core test asserts it. (3) The define test proves the build refuses a true literal with no accepted Decision. (4) The perf protocol and the design spec name the new default and the Android-only basis. st010 and st011 hold the owner words. (5) npx vitest run test/e2ee: 101 passed, 1 skipped. keel gate validate and guard green. (6) FAIL: awaiting the owner acceptance of D0115. The define, the version and the release wait on it. Verdict FAIL with that one reason.
        part e2eeKdfDefaultDoDR1 : TestResult { :>> id = "18029f94-e7c1-487b-afe4-409c0cab374f"; :>> outcome = VerdictKind::fail; :>> judgedAgainst = "d412d0e"; :>> judgedAt = "2026-11-11"; :>> judgedBy = "ai"; }
        // RAN: RAN: e2eeKdfDefaultDoD re-judged 2026-11-11 at the release commit 80094eb. Clauses 1 to 5 as in R1. (6) The owner accepted D0115 with the words 115 accepted, recorded as st012 and the d0115Accept event judged by wweatherholtz. SELFSYNC_E2EE is true in client/esbuild.config.mjs and the build check passes on the accepted Decision. The define test now asserts that pass and that a drifted KDF_DEFAULT still fails. The version is 1.34.0. release.yml run 43028163537 published the plugin and check-release verifies the assets. The released main.js compiles the build flag to true. Verdict PASS.
        part e2eeKdfDefaultDoDR2 : TestResult { :>> id = "1d889be9-3db9-453a-a594-be16adc3faaa"; :>> outcome = VerdictKind::pass; :>> judgedAgainst = "80094eb"; :>> judgedAt = "2026-11-11"; :>> judgedBy = "ai"; }
        action e2eeRealObsidianE2e;
        verification e2eeRealObsidianE2eDoD : Test { :>> id = "c4ddf5a8-a533-49d9-b8b5-9d42b96b770d"; :>> method = VerificationMethod::test; :>> procedureText = "Sprint 7 of the E2EE capability (D0112, srE2eeServerNeverSeesPlaintext, srE2eeDedupPreserved). Outcome: the shipped Encrypt feature works through the real plugin in real Obsidian, on a throwaway vault, measured. The spec is client/e2e-obsidian/e2ee.pwspec.ts, run by npm run test:obsidian-e2e. (1) Device A starts on a plaintext seed vault and pushes a control note. (2) Device A creates the encrypted vault through the plugin's own Encryption password dialog, driven by the two fields and the CTA button. A mismatched confirmation is refused inline first. The device holds a pin with a 64-hex vk and reaches a healthy status. (3) Device B is staged on the encrypted vault with no pin, and the plugin's own Join dialog opens by itself. A wrong password shows the Wrong password text and pins nothing. The right password pins the same vault id and the same vk as device A. (4) A note made on A before B joined arrives on B with the same bytes. A change on B flows back to A. A second note made on A after both are pinned arrives on B. (5) Loopback mode: a grep of the server data volume finds the plaintext control marker. It finds the encrypted marker nowhere and the encryption password nowhere. Neither device's data.json holds the password. (6) The spec records desktop Measurements: the KDF wall time at the shipped default on create and on join. Also the push time of one note plaintext and encrypted, and the encrypted A to B convergence time. Each is recorded under an Indicator with the spec as its source. (7) Real-server mode exists: SELFSYNC_E2E_SERVER_URL with a username and password runs the same flow against a server the owner operates. The vaults are named for the run and the spec deletes them at the end. The grep clause prints the host command instead. (8) docs/testing.md names the spec and both modes. (9) Resolves issue019, found by the first run of this spec: an unpinned device could not join an encrypted vault because its status probe met the server downgrade guard. The connect probe sends the header once GET keyring finds a record on a build with support, the connect.test.ts fake mirrors the guard, and the spec joins through the dialog. Evidence: the Playwright pass line, the E2EE-MEASURE JSON line, the Measurement ids, keel gate validate and guard green."; }
        // RAN: e2eeRealObsidianE2eDoD judged 2026-11-11 at d79c772 plus the working tree, clause by clause. Source: client/e2e-obsidian/e2ee.pwspec.ts run mwcboq98 against the HEAD server binary through two real Obsidian instances. The Playwright line: 1 passed (36.2s). (1) Device A pushed the control note to the plaintext seed vault in 0.47 seconds. (2) The Encryption password dialog opened from createVaultFlow. The mismatched confirmation showed 'The two entries do not match.' and the dialog stayed. The right pair closed it in 2.22 seconds, device A holds a 64-hex vk pin, status healthy. (3) Named deviation. The Join dialog did not open by itself within 10 seconds. The harness first-open ceremony presses Escape on every modal it meets and spent the latch. The card's Join action opened it, status before was blocked. A wrong password showed 'Wrong password.' and pinned nothing. The right password closed the dialog in 2.12 seconds and pinned the same vault id and vk as A. (4) secret.md arrived on B in 1.02 seconds with the same bytes. The B edit flowed back to A. second.md arrived on B in 0.58 seconds. (5) The grep of the server data volume found the control marker in two files, the encrypted marker in none, the password in none. Neither device data file holds the password. (6) Six Measurements recorded. e2eeDesktopKdfWallTimeM1 2.22 and M2 2.12. e2eeSyncWallTimeM1 0.47, M2 0.46, M3 1.02, M4 0.58. (7) Real-server mode exists in the spec through SELFSYNC_E2E_SERVER_URL and the two credential variables. It uses run-named vaults and deletes them at the end. It did not run in this sprint, no server credentials were given. (8) docs/testing.md names the spec and both modes. (9) issue019 found by the first run, fixed in main.ts probe, guarded by the connect.test.ts fake and this spec. The suite: 77 files, 1152 tests passed, 3 skipped. smoke and convergence specs still pass with the helper change. Verdict PASS.
        part e2eeRealObsidianE2eDoDR1 : TestResult { :>> id = "9fd9172a-37f9-44d1-a08a-565eb6bb814b"; :>> outcome = VerdictKind::pass; :>> judgedAgainst = "d79c772"; :>> judgedAt = "2026-11-11"; :>> judgedBy = "ai"; }
        // RAN: e2eeRealObsidianE2eDoD re-judged 2026-11-11 at 8708928 for clause 7, the other clauses as in R1. Real-server mode ran against https://notes2.willweatherholtz.com, the owner's containerized server behind a TLS proxy, with the test account the owner made. The account had must_change_password set, so the password changed through POST /api/password first. The staged plugin path does not handle a forced change outside the setup wizard. Run mwceeanp: 1 passed (1.6m). Both dialogs drove the real flows over the internet. The grep clause printed the host command for marker SELFSYNC-E2EE-MARKER-39ba4fb3-dbd9-4a84-b81c-8574a3f32c63. The run vaults e2e-seed-mwceeanp and e2e-enc-mwceeanp are gone: GET /api/vaults for the account answers an empty list. Measurements recorded as e2eeDesktopKdfWallTimeM3 1.68 and M4 1.25, e2eeSyncWallTimeM5 0.67, M6 1.35, M7 1.02, M8 62.47. The live change latency of 62.47 seconds against 0.58 on loopback is tracked as issue020 with the resolver e2eeRemoteLiveLatency. A WebSocket upgrade through the proxy answers 101, so the socket is not refused. The cause is not established. Verdict PASS.
        part e2eeRealObsidianE2eDoDR2 : TestResult { :>> id = "54590d39-0f64-4eec-95b2-5c4693fd8339"; :>> outcome = VerdictKind::pass; :>> judgedAgainst = "8708928"; :>> judgedAt = "2026-11-11"; :>> judgedBy = "ai"; }
        action e2eeRemoteLiveLatency;
        verification e2eeRemoteLiveLatencyDoD : Test { :>> id = "ab714e3d-0495-4a0d-b212-ba04f96e6c00"; :>> method = VerificationMethod::test; :>> procedureText = "Resolves issue020. Outcome: the cause of the 62 second live change latency against the owner's server is named from evidence, and fixed or documented. (1) The spec runs in real-server mode with the plugin log of both devices captured. The log shows for device B whether the WebSocket opened, stayed open, and received a changed message for the live note. (2) The cause is one of three. The proxy drops or buffers the socket. The client socket dropped and the poll fallback carried the change. The server did not publish. The result names it with the log lines. (3) A proxy cause gets a documented setting in docs/deployment.md and a rerun that converges under 5 seconds. A client or server cause gets a code fix with a test and the same rerun. Evidence: the rerun E2EE-MEASURE line, the log excerpt, keel gate validate and guard green."; }
        // RAN: Not started. Recorded 2026-11-11 so the task is not served as ready forever without a result. issue020 is tracked with this task as its resolver. The rerun with captured plugin logs has not run. Verdict FAIL.
        part e2eeRemoteLiveLatencyDoDR1 : TestResult { :>> id = "bb172f4d-8a9d-4809-b27d-685f3bbad070"; :>> outcome = VerdictKind::fail; :>> judgedAgainst = "8708928"; :>> judgedAt = "2026-11-11"; :>> judgedBy = "ai"; }
        // RAN: e2eeRemoteLiveLatencyDoD judged 2026-11-11 at f764122 after the owner redid the server (st017). Clause 1: 36 reruns of e2ee.pwspec.ts against https://notes2.willweatherholtz.com with both plugin logs kept. Every live note converged in 0.53 to 1.57 seconds. The 62 seconds of run mwceeanp, started 17:33:40 UTC, did not reproduce, and that run has no kept log. A 200 second WebSocket probe through Cloudflare and Caddy shows a heartbeat every 30 seconds and no close. Clause 2: the cause is not named. Two code paths give 60 seconds. SLOW_RETRY_SECS after a 503 or a 429 in connstate.ts, and the idle poll after a lost poke in main.ts. Neither is shown by a log line. The server log of that window, or the owner's word on a restart at that time, is the missing evidence. Clause 3: no fix applied, nothing to document yet. The full suites pass on the redone server: 5 remote runs, 12 Obsidian specs on loopback, client 1152 tests, server cargo test green. Verdict FAIL, reason: the cause is not named from evidence.
        part e2eeRemoteLiveLatencyDoDR2 : TestResult { :>> id = "7e14dda4-ea7b-49f3-885f-6e1da67eb059"; :>> outcome = VerdictKind::fail; :>> judgedAgainst = "f764122"; :>> judgedAt = "2026-11-11"; :>> judgedBy = "ai"; }
        // RAN: e2eeRemoteLiveLatencyDoD judged 2026-11-11 at be3f5ae. Clause 1: the owner confirmed a server restart in the window of run mwceeanp (st018). The spec gained SELFSYNC_E2E_RESTART_AT_LIVE, a loopback reproduction. It kills the server at the live note and restarts it on the same address after a set number of seconds. Two runs kept both plugin logs: mwcm9clw with a 10 second outage, mwcmbk4j with a 35 second outage. Clause 2: the cause is the client reconnect backoff after a server restart. Device A log of mwcmbk4j shows connect FAILED net::ERR_CONNECTION_REFUSED at 21:16:13, 21:16:19 and 21:16:31. The next lines say retrying in 3s, 4s, 9s and 22s, then connected @ v4 at 21:16:53. The server was back at 21:16:41.96. The note waited 11 seconds in the last backoff interval. Device B shows the same ladder with 6s, 8s and 17s. The path is recoveryFor Transient in connstate.ts line 138 and scheduleRecovery in main.ts line 3238. The base is 3 seconds, doubled per failure, capped at 30 seconds. A refused connect costs 2 seconds more. The 62 seconds of mwceeanp fits an outage of about 40 seconds, an image pull and start, plus one backoff interval. Of the three DoD candidates this is the second in substance: the client lost the socket. Recovery ran through the reconnect backoff, not the poll. The two other candidates are excluded. The proxy passed a 200 second WebSocket probe. The server published every change in all 36 remote runs. The slow retry after a 503 and the idle poll are in no log. Clause 3: documented, not changed. The owner accepted the latency as a risk (st019). The docs/deployment.md section After a server restart gives the backoff ladder, the worst case and the measured points. The docs/testing.md e2ee bullet documents both knobs. Measurements e2eeSyncWallTimeM9 13.51 and M10 47.26 record the reproduction. The rerun under 5 seconds holds: 36 remote runs without an outage converged in 0.53 to 1.57 seconds. Client suite 1152 green, tsc clean. Verdict PASS.
        part e2eeRemoteLiveLatencyDoDR3 : TestResult { :>> id = "d34561e5-bc77-4705-8935-4572c6bd7b8d"; :>> outcome = VerdictKind::pass; :>> judgedAgainst = "be3f5ae"; :>> judgedAt = "2026-11-11"; :>> judgedBy = "ai"; }
    }

    // statusLightFlickerFsmDoD (2026-07-28, pass @ 18f9cc2) asserted the OPPOSITE display rule: "entering the
    // visible 'syncing' display is DEBOUNCED and gated on syncPending>0 ... a 0-pending or sub-second reconcile
    // never paints". It was true when judged, and its result stands in history; it is no longer the governing
    // invariant. The DELAY is gone (a real one-file save finishes inside it, so it hid the very work the user
    // asked to see) and the flicker property it protected now lives on the pending gate plus the re-arming
    // quiet window, re-pinned by the restored guard test in client/test/statuslight.test.ts. Typed edge, not a
    // rewrite of the old text (critique F5, UX-honesty lens).
    #Supersede dependency from localEditVisibleInIndicatorDoD to statusLightFlickerFsmDoD;

    // The config-sync capability (0.10.4), marked #Capability + rooted to its Need so
    // `keel guard requirement-rootedness` actively enforces its traceability (engine D0099). This is the
    // first declared capability — the guard was vacuous until now; the escape is why we declare it.
    #Capability part configSyncCapability : Story {
        :>> id = "c0f1a5cc-7001-4a10-9b20-a1b2c3d40061";
        :>> title = "Safe cross-device config/plugin sync";
        :>> createdAt = "2026-07-05"; :>> createdBy = "wweatherholtz";
        :>> kind = WorkKind::code; :>> priority = WorkPriority::p0; :>> owner = "wweatherholtz";
    }
    #DerivedFrom dependency from configSyncCapability to nConfigSync; // hard rootedness gate (engine D0099)
    #CharteredBy dependency from configSyncCapability to nConfigSync; // charter lineage (rootedness burndown)

    // The embedded-timestamp + volatile-field-aware-sync capability (2026-07-29), rooted to its Need so
    // requirement-rootedness enforces the traceability (engine D0099). Spec: docs/design/specs/2026-07-29-embedded-timestamp-metadata.md.
    #Capability part embeddedTimestampCapability : Story {
        :>> id = "d7c17001-0000-4a10-9b20-a1b2c3d40071";
        :>> title = "Embedded timestamps + volatile-field-aware sync";
        :>> createdAt = "2026-07-29"; :>> createdBy = "wweatherholtz";
        :>> kind = WorkKind::code; :>> priority = WorkPriority::p1; :>> owner = "wweatherholtz";
    }
    #DerivedFrom dependency from embeddedTimestampCapability to nTimestampFidelity; // hard rootedness gate (engine D0099)
    #CharteredBy dependency from embeddedTimestampCapability to nTimestampFidelity; // charter lineage

    // The end-to-end encryption capability (2026-11-10, st009/us012-us014), rooted to its Need so
    // requirement-rootedness enforces the traceability (engine D0099). Spec: docs/design/specs/2026-11-10-e2ee-design.md.
    // Chartered by D0096 (direction), built under the D0099-D0104 set (construction) and the D0105-D0112 set (custody).
    #Capability part e2eeCapability : Story {
        :>> id = "b0260304-c4b0-475d-8b7d-9c09534f5356";
        :>> title = "Optional end-to-end encryption of vault content";
        :>> createdAt = "2026-11-10"; :>> createdBy = "ai";
        :>> kind = WorkKind::code; :>> priority = WorkPriority::p1; :>> owner = "ai";
        :>> estimatedPoints = 21;
    }
    #DerivedFrom dependency from e2eeCapability to nE2eeContentPrivacy; // hard rootedness gate (engine D0099)
    #CharteredBy dependency from e2eeCapability to d0096; // charter lineage


    // ---- #Covers edges (per-sitting review -> the sprint tasks it covers, D0049/issue040) ----
    // HOISTED to package level 2026-09-07: these 74 edges used to sit INSIDE `action def SelfSyncDelivery`,
    // and keel-parser records a `dependency` statement nested in an action body as SKIPPED - every one was
    // invisible to sitting-coverage (0 covered) while the text read as if the sittings were reviewed
    // (issueNestedCoversEdgesSkipped). Package-level dependency statements are parsed; the #Verify edges in
    // acceptance.sysml were counted for exactly that reason. Same edges, same order, nothing re-judged.
    #Covers dependency from sittingReview20260728 to statusLightFlickerFsm;
    #Covers dependency from sittingReview20260729 to embeddedTimestampMetadata;
    #Covers dependency from sittingReview20260729 to embeddedTimestampCapability;
    #Covers dependency from sittingReview20260729 to frontmatterParserSafety;
    #Covers dependency from sittingReview20260729 to timestampBackfill;
    #Covers dependency from sittingReview20260729 to statusHangsOnSyncing;
    #Covers dependency from sittingReview20260730 to timestampIgnoreRedesign;
    #Covers dependency from sittingReview20260731 to pluginSyncRemovalPropagation;
    #Covers dependency from sittingReview20260731 to pluginSyncDisplayName;
    #Covers dependency from sittingReview20260731 to vaultChangeTransitionGuard;
    #Covers dependency from sittingReview20260731 to sessionIdleReloginEase;
    #Covers dependency from sittingReview20260730 to connectionFsmTypedFailure;
    #Covers dependency from sittingReview20260731 to hotLoadSyncedPlugins;
    #Covers dependency from sittingReview20260801 to hotLoadPrivacyGateFreshCheck;
    #Covers dependency from sittingReview20260801 to reconcilePathReloginOnce;
    #Covers dependency from sittingReview20260801 to vaultKeyServerQualified;
    #Covers dependency from sittingReview20260802 to critiqueBacklogFsm;
    #Covers dependency from sittingReview20260802 to critiqueBacklogTimestamp;
    #Covers dependency from sittingReview20260802 to critiqueBacklogVault;
    #Covers dependency from sittingReview20260802 to critiqueBacklogSecurity;
    #Covers dependency from sittingReview20260802 to statusDisplayPureProjection;
    #Covers dependency from sittingReview20260802 to switchAbortOnOutage;
    #Covers dependency from sittingReview20260802 to connectPhaseNoOptimisticFlip;
    #Covers dependency from sittingReview20260802 to switchReportsProgress;
    #Covers dependency from sittingReview20260802 to resumeReattemptsConnection;
    #Covers dependency from sittingReview20260802 to switchUploadProbeGuard;
    #Covers dependency from sittingReview20260802 to cssTrustGate;
    #Covers dependency from sittingReview20260802b to deleteRemoteCasGuard;
    #Covers dependency from sittingReview20260802b to removeDiagnoseButton;
    #Covers dependency from sittingReview20260802c to connectPhaseVisibility;
    #Covers dependency from sittingReview20260802d to streamedPullRacingEditGuard;
    #Covers dependency from sittingReview20260802e to persistScanSkipHint;
    #Covers dependency from sittingReview20260802f to tokenIdleDefaultOff;
    #Covers dependency from sittingReview20260802f to configWalkParallel;
    #Covers dependency from sittingReview20260802g to reconcileExamProgress;
    #Covers dependency from sittingReview20260802g to removePluginServerButton;
    #Covers dependency from sittingReview20260802g to wsSupersededGuard;
    #Covers dependency from sittingReview20260803a to timestampSettingsUx;
    #Covers dependency from sittingReview20260803a to settingsUxPolish;
    #Covers dependency from sittingReview20260803a to collapseHeaderFix;
    #Covers dependency from sittingReview20260803a to collapseHeaderGroupFix;
    #Covers dependency from sittingReview20260803a to shareLinksCanonical;
    #Covers dependency from sittingReview20260803a to shareLinkOnboarding;
    #Covers dependency from sittingReview20260803a to accountCreationLink;
    #Covers dependency from sittingReview20260803a to pluginWiringTimerLeakFix;
    #Covers dependency from sittingReview20260803a to collapseChevronFix;
    #Covers dependency from sittingReview20260803a to settingsRevamp;
    #Covers dependency from sittingReview20260803a to connectionRowOverflowFix;
    #Covers dependency from sittingReview20260803a to pluginPushPull;
    #Covers dependency from sittingReview20260803a to mfaDeprecation;
    #Covers dependency from sittingReview20260803a to changeProvenanceNotify;
    #Covers dependency from sittingReview20260805a to pushPullPreview;
    #Covers dependency from sittingReview20260805a to pushPullGreyout;
    #Covers dependency from sittingReview20260805a to pushPullProvenance;
    #Covers dependency from sittingReview20260805a to settingsScrollPreserve;
    #Covers dependency from sittingReview20260805a to pushPullDisableInactionable;
    #Covers dependency from sittingReview20260805a to pushPullDisableInert;
    #Covers dependency from sittingReview20260807a to pluginSyncAutopilot;
    #Covers dependency from sittingReview20260807a to mountsFoundation;
    #Covers dependency from sittingReview20260807b to mountIoAdapters;
    #Covers dependency from sittingReview20260807b to mountEngineCore;
    #Covers dependency from sittingReview20260807b to mountEngine;
    #Covers dependency from sittingReview20260807b to mountUx;
    #Covers dependency from sittingReview20260807b to mountHardeningR1;
    #Covers dependency from sittingReview20260807b to mountHardeningR2;
    #Covers dependency from sittingReview20260807b to mountHardeningR3;
    #Covers dependency from sittingReview20260807b to mountHardeningR4;
    #Covers dependency from sittingReview20260807b to mountHardeningR5;
    #Covers dependency from sittingReview20260807b to mountHardeningR6;
    #Covers dependency from sittingReview20260807b to mountHardeningR7;
    #Covers dependency from sittingReview20260807b to mountHardeningR8;
    #Covers dependency from sittingReview20260807b to mountHardeningR9;
    #Covers dependency from sittingReview20260807b to mountHardeningR10;
    #Covers dependency from sittingReview20260807b to bulkDeleteConfirm;

    // decisionClauseSplitDoD: judged from the set by wweatherholtz (D0443; D0312 B - one item, one record, one quote)
    part decisionClauseSplitDoDR2 : TestResult { :>> id = "0086c6ca-8b01-41c7-933a-8ca210522dd6"; :>> outcome = VerdictKind::pass; :>> judgedAgainst = "d7fc5711"; :>> judgedAt = "2026-09-13"; :>> judgedBy = "wweatherholtz"; :>> createdBy = "wweatherholtz"; }
    verification decisionClauseSplitDoDAttest1 : Test { :>> id = "75e125cc-1bdf-4dc7-8737-1738dbe4d205"; :>> title = "Quote receipt for decisionClauseSplitDoDR2 (D0198)"; :>> createdAt = "2026-09-13"; :>> createdBy = "wweatherholtz"; :>> method = VerificationMethod::confirmation; :>> procedureText = "Quote receipt for decisionClauseSplitDoDR2 (D0198/D0443): wweatherholtz judged the proposed result decisionClauseSplitDoDR1 pass from the sampled set of delivery.sysml; recorded from chat - their words, verbatim: “[x] Accept all 34 clause records”"; }
    part decisionClauseSplitDoDAttest1R1 : TestResult { :>> id = "6fbb58ba-b71a-4298-ba3d-39a3a4f0f6bc"; :>> outcome = VerdictKind::pass; :>> judgedAgainst = "d7fc5711"; :>> judgedAt = "2026-09-13"; :>> judgedBy = "wweatherholtz"; :>> createdBy = "wweatherholtz"; }

    // engineVintageResyncDoD: judged from the set by wweatherholtz (D0443; D0312 B - one item, one record, one quote)
    part engineVintageResyncDoDR2 : TestResult { :>> id = "6e67ab51-53bf-47c8-a7c0-04a76b23b8dc"; :>> outcome = VerdictKind::pass; :>> judgedAgainst = "7ac3632d"; :>> judgedAt = "2026-09-13"; :>> judgedBy = "wweatherholtz"; :>> createdBy = "wweatherholtz"; }
    verification engineVintageResyncDoDAttest1 : Test { :>> id = "bd75b22e-5f35-4bfe-9f87-c9b93f384f13"; :>> title = "Quote receipt for engineVintageResyncDoDR2 (D0198)"; :>> createdAt = "2026-09-13"; :>> createdBy = "wweatherholtz"; :>> method = VerificationMethod::confirmation; :>> procedureText = "Quote receipt for engineVintageResyncDoDR2 (D0198/D0443): wweatherholtz judged the proposed result engineVintageResyncDoDR1 pass from the sampled set of delivery.sysml; recorded from chat - their words, verbatim: “Accept decisions - I can revert/supersede later as needed”"; }
    part engineVintageResyncDoDAttest1R1 : TestResult { :>> id = "d324451e-749a-4ee9-ba7f-3786e4b79293"; :>> outcome = VerdictKind::pass; :>> judgedAgainst = "7ac3632d"; :>> judgedAt = "2026-09-13"; :>> judgedBy = "wweatherholtz"; :>> createdBy = "wweatherholtz"; }

    // lockfilePolicyDoD: judged from the set by wweatherholtz (D0443; D0312 B - one item, one record, one quote)
    part lockfilePolicyDoDR2 : TestResult { :>> id = "44c9bedf-5944-4c66-9402-a222d9e7986e"; :>> outcome = VerdictKind::pass; :>> judgedAgainst = "7ac3632d"; :>> judgedAt = "2026-09-13"; :>> judgedBy = "wweatherholtz"; :>> createdBy = "wweatherholtz"; }
    verification lockfilePolicyDoDAttest1 : Test { :>> id = "bc4e2cb5-d9e4-4340-ae81-0a03156902b4"; :>> title = "Quote receipt for lockfilePolicyDoDR2 (D0198)"; :>> createdAt = "2026-09-13"; :>> createdBy = "wweatherholtz"; :>> method = VerificationMethod::confirmation; :>> procedureText = "Quote receipt for lockfilePolicyDoDR2 (D0198/D0443): wweatherholtz judged the proposed result lockfilePolicyDoDR1 pass from the sampled set of delivery.sysml; recorded from chat - their words, verbatim: “Accept decisions - I can revert/supersede later as needed”"; }
    part lockfilePolicyDoDAttest1R1 : TestResult { :>> id = "b6462735-8d6a-4fa0-8f37-fae4ae500840"; :>> outcome = VerdictKind::pass; :>> judgedAgainst = "7ac3632d"; :>> judgedAt = "2026-09-13"; :>> judgedBy = "wweatherholtz"; :>> createdBy = "wweatherholtz"; }
}
