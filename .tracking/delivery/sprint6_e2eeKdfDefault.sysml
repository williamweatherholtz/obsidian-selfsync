// ProjectDeliveryS6 — Sprint 6: the E2EE KDF default D0115 on the owner's Android Measurement, KDF_DEFAULT set to it, the define flip and the release gated on acceptance (D0112). EXECUTE. 2 pts.
package ProjectDeliveryS6 {
    private import EngineElement::*;
    private import EngineWork::*;
    private import EngineVerification::*;
    private import EngineRelationships::*;

    #CharteredBy dependency from e2eeKdfDefaultStory to d0112;

    part e2eeKdfDefaultStory : Story {
        :>> id = "ec76cdd8-9547-4810-bd26-bf091c056d83";
        :>> title = "Sprint 6: the KDF default Decision D0115 recorded and the code, tests and docs set to m_kib=32768, t=3, p=1, with the define flip and release waiting on the owner acceptance (2 pts)";
        :>> createdAt = "2026-11-11"; :>> createdBy = "ai"; :>> kind = WorkKind::code; :>> priority = WorkPriority::p0; :>> owner = "ai"; :>> estimatedPoints = 2;
    }

    action def DeliveryRunS6 {
        action storyE2eeKdfDefault;
        verification storyE2eeKdfDefaultDoD : Test { :>> id = "5c0cc344-982b-4bde-a6a0-3605fe39025c"; :>> method = VerificationMethod::test; :>> procedureText = "DELIVERED BACKLOG ITEMS: e2eeKdfDefault. Done means D0115 is recorded as proposed with the literal m_kib=32768, t=3, p=1 and its DependsOn edge to d0112, KDF_DEFAULT equals it, the core and define tests pass, the perf protocol and the design spec name the new default and the Android-only basis, and the owner direction is recorded verbatim as st010 and st011 with the story us015. Verified by cd client, npx vitest run test/e2ee, keel gate validate and guard green, and a result on e2eeKdfDefault at the sprint commit. The define flip, the version bump and the release happen in this sprint only after the owner accepts D0115, and the E4 clause 7 result re-judges then."; }
        // RAN: Story DoD for Sprint 6 judged 2026-11-11 at 80094eb. The delivered item e2eeKdfDefault carries result R2 with all six clauses green. D0115 is accepted on the owner's words, the define is on, 1.34.0 is published and verified. Evidence: the client suite 1152 passed, keel gate validate and guard green, the release and image run ids. Verdict PASS.
        part storyE2eeKdfDefaultDoDR1 : TestResult { :>> id = "acf913c2-6edb-4720-85f7-8b5da45fd758"; :>> outcome = VerdictKind::pass; :>> judgedAgainst = "80094eb"; :>> judgedAt = "2026-11-11"; :>> judgedBy = "ai"; }
    }

    verification e2eeKdfDefaultRefineGate : Test { :>> id = "19a41dc9-a254-47e1-8bd0-aa5dd462cc02"; :>> title = "Sprint 6 refine gate (DoR)"; :>> createdAt = "2026-11-11"; :>> createdBy = "ai"; :>> method = VerificationMethod::inspect; :>> procedureText = "DoR for Sprint 6. estimatedPoints 2 is set (one Decision, one constant, two tests, two docs, the intake records, then after acceptance the define flip and a release). The Story carries CharteredBy d0112. Scope is the e2eeKdfDefault task. Dependencies: Measurement e2eePhoneKdfWallTimeM1 at d412d0e and the owner statements st010 and st011. The acceptance of D0115 is the owner's and is named, not assumed. Verdict PASS when all four hold."; }
    // RAN: DoR for Sprint 6 judged 2026-11-11. estimatedPoints 2 is set: one Decision, one constant, two tests, two docs, the intake records, then the define flip and a release after acceptance. The Story carries CharteredBy d0112. Scope is the e2eeKdfDefault task alone. Dependencies: Measurement e2eePhoneKdfWallTimeM1 at d412d0e, and the owner statements st010 and st011. The acceptance of D0115 is the owner's, named as the one blocker. Verdict PASS.
    part e2eeKdfDefaultRefineGateR1 : TestResult { :>> id = "1c13d52e-0229-43cf-a3b1-80a81417367a"; :>> outcome = VerdictKind::proposed; :>> judgedAgainst = "d412d0e"; :>> judgedAt = "2026-11-11"; :>> judgedBy = "ai"; }
    verification e2eeKdfDefaultStandupGate : Test { :>> id = "355f18d4-e014-47e3-887d-5f36b758a4fc"; :>> title = "Sprint 6 standup gate"; :>> createdAt = "2026-11-11"; :>> createdBy = "ai"; :>> method = VerificationMethod::inspect; :>> procedureText = "Standup for Sprint 6. Plan in order: record st010, st011, us015 and D0115 with its edges, set KDF_DEFAULT and the core test, update the perf protocol and the design spec, record the task with its DoD and result, commit. Then present D0115 to the owner. After acceptance: record the acceptance event from the owner's words, flip SELFSYNC_E2EE, bump the version, release, re-judge E4 clause 7. Blocker: the acceptance, which only the owner gives."; }
    // RAN: Standup for Sprint 6, 2026-11-11. Plan in order: record st010, st011, us015 and D0115 with its edges. Set KDF_DEFAULT and the core test. Update the perf protocol and the design spec. Record the task with its DoD and its result. Commit. Then present D0115 to the owner. After acceptance: record the acceptance event from the owner's words, flip SELFSYNC_E2EE, bump the version, release, re-judge E4 clause 7. Blocker: the acceptance, which only the owner gives. Verdict PASS.
    part e2eeKdfDefaultStandupGateR1 : TestResult { :>> id = "c217a796-3280-4856-a76c-c0022b1d41cd"; :>> outcome = VerdictKind::proposed; :>> judgedAgainst = "d412d0e"; :>> judgedAt = "2026-11-11"; :>> judgedBy = "ai"; }
    verification e2eeKdfDefaultImplementGate : Test { :>> id = "de1f8793-8569-4350-9c57-d005af4abcca"; :>> title = "Sprint 6 implement gate"; :>> createdAt = "2026-11-11"; :>> createdBy = "ai"; :>> method = VerificationMethod::test; :>> procedureText = "Implement gate for Sprint 6: npx vitest run test/e2ee green with the new KDF_DEFAULT, keel gate validate and guard green, D0115 present with the literal and the edges, the docs updated. Evidence: the vitest pass count and the gate output at the sprint commit."; }
    // RAN: RAN 2026-11-11 at d412d0e plus the working tree: cd client, npx vitest run test/e2ee test/e2ee-ui.dom.test.ts: 15 files passed, 1 skipped, 101 tests passed, 1 skipped. The define test needed one fix: its different-cost case had hard-coded 32768, which is now the default, so it derives the other cost from KDF_DEFAULT. npm run build passes with the literal false. keel gate validate: 31 files clean. keel gate guard: no FAIL after the retro text and the task result were recorded. D0115 holds the literal m_kib=32768, t=3, p=1 in its decision field and the DependsOn edge to d0112. KDF_DEFAULT equals it. The perf protocol, the design spec diagram, the open-fork list and the threat row name the new default. Verdict PASS.
    part e2eeKdfDefaultImplementGateR1 : TestResult { :>> id = "ab44ba14-6207-453b-b1c7-6052bf1815ea"; :>> outcome = VerdictKind::pass; :>> judgedAgainst = "d412d0e"; :>> judgedAt = "2026-11-11"; :>> judgedBy = "ai"; }
    verification e2eeKdfDefaultReviewGate : Test { :>> id = "b00e6b7b-b969-4827-b2e6-95dee5d4aa4f"; :>> title = "Sprint 6 review gate — three passes per D0172"; :>> createdAt = "2026-11-11"; :>> createdBy = "ai"; :>> method = VerificationMethod::inspect; :>> procedureText = "Three review passes for Sprint 6. (1) D0115 against D0112: does it state the literal in the decision field, depend on d0112, and say honestly what was and was not measured. (2) The build check: does acceptedKdfDecisions match D0115 once its status is accepted, and does KDF_DEFAULT equal it. (3) The docs: no doc still names 64 MiB as the shipped default. Every finding becomes a fix in this sprint or a tracked Issue."; }
    // RAN: Three review passes for Sprint 6, 2026-11-11, by the AI with the checks named. (1) D0115 against D0112: grep of the decision file shows the literal m_kib=32768, t=3, p=1 in the decision field. The DependsOn edge to d0112 sits at line 22. The context field says what was measured and what was not, with the owner statements cited. (2) The build check: a node run of acceptedKdfDecisions over the D0115 text gives an empty list while proposed. With the status replaced by accepted it gives one entry, 32768, 3, 1. checkE2eeDefine with the true literal and that text answers ok. (3) The docs: grep for 64 MiB across docs, README and client/src leaves only history lines, the desktop measurement and the comparison table. No finding. Verdict PASS.
    part e2eeKdfDefaultReviewGateR1 : TestResult { :>> id = "5596ceef-7485-4bc9-8780-24d99bfabad6"; :>> outcome = VerdictKind::proposed; :>> judgedAgainst = "d412d0e"; :>> judgedAt = "2026-11-11"; :>> judgedBy = "ai"; }
    verification e2eeKdfDefaultCloseOutGate : Test { :>> id = "fa19c308-a652-4e36-a61f-9969de376bc8"; :>> title = "Sprint 6 closeOut gate (autonomous, D0049)"; :>> createdAt = "2026-11-11"; :>> createdBy = "ai"; :>> method = VerificationMethod::inspect; :>> procedureText = "Autonomous closeOut for Sprint 6: the implement gate and the review gate pass, the e2eeKdfDefault result is recorded, the commits are on main, CI is green on the sprint commit. If the owner accepted D0115 in this sitting the release evidence is recorded too. No human sign-off at sprint end (D0049)."; }
    // RAN: Autonomous closeOut 2026-11-11 for Sprint 6 (e2eeKdfDefault), per D0049. The implement gate and the review gate pass. The e2eeKdfDefault result R2 passes on all six clauses. The owner accepted D0115 in this sitting, so the release evidence is recorded. Plugin 1.34.0 from 80094eb, run 43028163537, assets verified. Server image 1.34.0 run 43028208136, CI green. The E4 task and the Sprint 5 story re-judged PASS. No human sign-off at sprint end. The per-sitting review covers sprints 1 to 6. Verdict PASS.
    part e2eeKdfDefaultCloseOutGateR1 : TestResult { :>> id = "ecd24cf7-df4e-4eff-b7e5-75bb4c8d294a"; :>> outcome = VerdictKind::proposed; :>> judgedAgainst = "80094eb"; :>> judgedAt = "2026-11-11"; :>> judgedBy = "ai"; }
    verification e2eeKdfDefaultRetroGate : Test { :>> id = "3d5b2fff-5202-4d72-bfb0-ae18f3371ce3"; :>> title = "Sprint 6 retro gate (autonomous, D0049)"; :>> createdAt = "2026-11-11"; :>> createdBy = "ai"; :>> method = VerificationMethod::analyze; :>> procedureText = "Not yet run. No new item at refine: the protocol gap that surfaced before this sprint was tracked in the previous commit, and the sprint work is the task e2eeKdfDefault under d0112. At sprint end the retro names what the Measurement step cost and which avoidable issue becomes a tracked item or a guard, or why none is needed. It records wall time against the 2-point guideline."; }
    // RAN: Retro 2026-11-11 for Sprint 6 (e2eeKdfDefault). What worked: the owner timed the real derivation in minutes through a browser page, and one honest datapoint was enough to pick a default. The build check did its job twice. It refused the true literal until D0115 was accepted, and the define test now proves a drifted default still fails. What cost time: the Measurement protocol asked the owner to use a feature the same policy hid. That gap was tracked as an Issue with its resolver task before this sprint started, not in it. No new tracked item is needed: the sprint surfaced no other avoidable issue, and the one it inherited already has a resolver. Wall time: under one sitting against the 2-point guideline. The estimate held.
    part e2eeKdfDefaultRetroGateR1 : TestResult { :>> id = "b587e341-a155-4de8-84b7-c4faf0fa095e"; :>> outcome = VerdictKind::proposed; :>> judgedAgainst = "80094eb"; :>> judgedAt = "2026-11-11"; :>> judgedBy = "ai"; }
}
